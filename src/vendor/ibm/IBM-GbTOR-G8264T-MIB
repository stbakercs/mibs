-- ----------------------------------------------------------------------------
-- File Main Owner: 
-- File Peer Owner:   
-- File Description:  Main entry point to build private MIBs.
--                    
--
-- { COPYRIGHT / HISTORY
--
--
--
-- PORTING HISTORY
--
-- } COPYRIGHT / HISTORY (end)
--

-- ----------------------------------------------------------------------------
-- { INSERT:  blade
-- ----------------------------------------------------------------------------

IBM-GbTOR-G8264T-MIB DEFINITIONS ::= BEGIN

IMPORTS
    OBJECT-TYPE, Integer32, Unsigned32, Counter32, Gauge32, Counter64,
    TimeTicks, IpAddress
        FROM SNMPv2-SMI
    DisplayString, PhysAddress, MacAddress, TruthValue, RowStatus
        FROM SNMPv2-TC
    BridgeId
        FROM BRIDGE-MIB
    sysName, sysLocation, sysContact, ifIndex
        FROM RFC1213-MIB
    enterprises 
        FROM RFC1155-SMI
    InetAddressType, InetAddress, InetAddressIPv6
        FROM INET-ADDRESS-MIB
    OBJECT-TYPE, MODULE-IDENTITY, NOTIFICATION-TYPE, OBJECT-IDENTITY,
    Integer32, Unsigned32, Counter32, Gauge32, Counter64,
    TimeTicks, IpAddress, mib-2
        FROM SNMPv2-SMI
    TEXTUAL-CONVENTION, TruthValue, DisplayString, PhysAddress,
    MacAddress, RowStatus, TimeInterval, TimeStamp, RowPointer,
    AutonomousType, StorageType, TDomain, TAddress
        FROM SNMPv2-TC
    MODULE-COMPLIANCE, OBJECT-GROUP, NOTIFICATION-GROUP
        FROM SNMPv2-CONF
    BridgeId, dot1dTp, dot1dTpPort, dot1dBridge, dot1dBasePortEntry,
    dot1dBasePort
        FROM BRIDGE-MIB
    EnabledStatus
        FROM P-BRIDGE-MIB
    PortList
        FROM Q-BRIDGE-MIB
    SnmpAdminString, SnmpEngineID,SnmpMessageProcessingModel,
     SnmpSecurityModel,SnmpSecurityLevel  FROM SNMP-FRAMEWORK-MIB
    usmNoAuthProtocol, usmNoPrivProtocol  FROM SNMP-USER-BASED-SM-MIB
    sysName, sysLocation, sysContact, ifIndex
        FROM RFC1213-MIB
    InterfaceIndex, InterfaceIndexOrZero
        FROM IF-MIB
    InetAddressType, InetAddress
        FROM INET-ADDRESS-MIB
    ;

-- ----------------------------------------------------------------------------
-- { INSERT: module identity 
-- ----------------------------------------------------------------------------

ibmGbTORG8264TMIB MODULE-IDENTITY
         LAST-UPDATED "201504271937Z"    -- Apr 27, 2015 07:37:36 PM
         ORGANIZATION "IBM/System Networking"
         CONTACT-INFO "
                IBM/System Networking 
                4400 North First Street
                San Jose, CA 95134
                408-956-3239
                "             
         DESCRIPTION " 
         MIB for IBM Networking Operating System RackSwitch G8264-T 
         All Rights reserved
         DEVICE VERSION: 7.9.13.0
                "
          ::= { ibmnetwork 3 }

-- ----------------------------------------------------------------------------
-- } INSERT: module identity 
-- ----------------------------------------------------------------------------


-- ----------------------------------------------------------------------------
-- { INSERT:  textual conventions
-- ----------------------------------------------------------------------------

PortNumber ::= TEXTUAL-CONVENTION
    STATUS        current
    DESCRIPTION
                  "Represents a port number of a switch."
    SYNTAX        Unsigned32

VlanId ::= TEXTUAL-CONVENTION
    DISPLAY-HINT  "d"
    STATUS      current
    DESCRIPTION
        "A 12-bit VLAN ID used in the VLAN Tag header."
    SYNTAX      Integer32 (1..4094)


Timeout ::= TEXTUAL-CONVENTION
    DISPLAY-HINT "d4"
    STATUS       current
    DESCRIPTION
                " Time out value in 4 byte"
    SYNTAX       Integer32


-- ----------------------------------------------------------------------------
-- } INSERT:  textual conventions
-- ----------------------------------------------------------------------------


-- blade OID reference  http://www.iana.org/assignments/enterprise-numbers
-- defined in /vobs/webos/src/lib/epi/target/h/wrn/wm/snmp/engine/mib.h

ibmnetwork                   OBJECT IDENTIFIER ::= { enterprises 20301 }

-- Groups in blade
registration            OBJECT IDENTIFIER ::= { ibmnetwork 1 }
private-mibs            OBJECT IDENTIFIER ::= { ibmnetwork 2 }




-- Access Switch for BNT Private MIBs
-- bnt-switch           OBJECT IDENTIFIER ::= { private-mibs 7 }
-- ----------------------------------------------------------------------------
-- { INSERT:  bntRoot
-- ----------------------------------------------------------------------------

-- Access Web Switch Module for Private MIBs
ibm-switch-mgmt  OBJECT IDENTIFIER
    ::= { private-mibs 7 }

g8264T-mgmt  OBJECT IDENTIFIER
    ::= { ibm-switch-mgmt 13 }








-------------------------------------------------------------------------------
-- Platform Dependent Registration sysObjectID
-- Must correspond to g_sysobjid in /vobs/webos/src/<bert>/ts/mp/sys/config.c
-- and defined in /vobs/webos/src/lib/epi/target/h/wrn/wm/snmp/engine/mib.h.
-- Careful when re-numbering sysObjectIDs due to hard coded references in
-- /vobs/webos/src/<bert>/ts/mp/epi/trap.c
-------------------------------------------------------------------------------

-- Top of Rack Switch
ibm-switch  OBJECT IDENTIFIER
    ::= { registration 7 }

g8264T  OBJECT IDENTIFIER
    ::= { ibm-switch 13 } -- G8264T switch





-------------------------------------------------------------------------------
-- Platform Common Private MIBs for g8264T-mgmt
-------------------------------------------------------------------------------
agent                   OBJECT IDENTIFIER ::= { g8264T-mgmt 1 }
-- ----------------------------------------------------------------------------
-- { INSERT:  agent
-- ----------------------------------------------------------------------------

agentConfig       OBJECT IDENTIFIER ::= { agent 1 }
agentStats        OBJECT IDENTIFIER ::= { agent 2 }
agentInfo         OBJECT IDENTIFIER ::= { agent 3 }
agentOper         OBJECT IDENTIFIER ::= { agent 4 }

agSystem          OBJECT IDENTIFIER ::= { agentConfig 1 }
agPortConfig      OBJECT IDENTIFIER ::= { agentConfig 2 }
agRadiusConfig    OBJECT IDENTIFIER ::= { agentConfig 3 }
agNTP             OBJECT IDENTIFIER ::= { agentConfig 4 }
agSyslog          OBJECT IDENTIFIER ::= { agentConfig 5 }
agTransfer        OBJECT IDENTIFIER ::= { agentConfig 7 }
agApply           OBJECT IDENTIFIER ::= { agentConfig 8 }
agTacacsConfig    OBJECT IDENTIFIER ::= { agentConfig 11 }
agMgmtNetConfig   OBJECT IDENTIFIER ::= { agentConfig 12 }
agBoot            OBJECT IDENTIFIER ::= { agentConfig 13 }
agAccess          OBJECT IDENTIFIER ::= { agentConfig 19 }
agLdapConfig      OBJECT IDENTIFIER ::= { agentConfig 21 }
agSSHConfig       OBJECT IDENTIFIER ::= { agentConfig 22 }
agsFlowConfig     OBJECT IDENTIFIER ::= { agentConfig 24 }
agUSBCopy         OBJECT IDENTIFIER ::= { agentConfig 25 }
agQsfp40GConfig   OBJECT IDENTIFIER ::= { agentConfig 26 }




pktStats          OBJECT IDENTIFIER ::= { agentStats 1 }
mpCpuStats        OBJECT IDENTIFIER ::= { agentStats 2 }
portStats         OBJECT IDENTIFIER ::= { agentStats 3 }
agClearStats      OBJECT IDENTIFIER ::= { agentStats 7 }
ntpStats          OBJECT IDENTIFIER ::= { agentStats 9 }
aclStats          OBJECT IDENTIFIER ::= { agentStats 11 }
memoryStats       OBJECT IDENTIFIER ::= { agentStats 12 }
snmpStats         OBJECT IDENTIFIER ::= { agentStats 20 }
mpTcbStats        OBJECT IDENTIFIER ::= { agentStats 21 }
mpUdpStats        OBJECT IDENTIFIER ::= { agentStats 22 }

hardware          OBJECT IDENTIFIER ::= { agentInfo 1 }
portInfo          OBJECT IDENTIFIER ::= { agentInfo 2 }
agDiff            OBJECT IDENTIFIER ::= { agentInfo 4 }
agCfgDump         OBJECT IDENTIFIER ::= { agentInfo 5 }
geaportInfo       OBJECT IDENTIFIER ::= { agentInfo 9 }
sfpInfo           OBJECT IDENTIFIER ::= { agentInfo 11 }


accessInfo        OBJECT IDENTIFIER ::= { agentInfo 13 }

agNTPOper         OBJECT IDENTIFIER ::= { agentOper 2 }

-- There are two configuration blocks.
-- The "current_config" reflects the configuration parameters that the
-- switch is operating on and it is read-only.  The objects with "CurCfg"
-- in the name are reflect to this configuration block.
--
-- The "new_config" accepts user configurations on set.  The objects with
-- "NewCfg" in the name are reflect to this configuration block.
--
-- The newly set configurations will not take effect until a "apply"
-- command has been issued (See agApplyConfiguration object)
--
-- The newly set configurations will not be saved through next restarting
-- of the switch unless a "save" command has been issued (See
-- agSaveConfiguration object).

-- Hardware Information

hwPartNumber OBJECT-TYPE
    SYNTAX  DisplayString (SIZE(0..16))
    MAX-ACCESS  read-only
    STATUS  current
    DESCRIPTION
        "The hardware part number of the Switch."
    ::= { hardware 1 }

hwRevision OBJECT-TYPE
    SYNTAX DisplayString (SIZE(0..16))
    MAX-ACCESS read-only
    STATUS current
    DESCRIPTION
	"The hardware revision.  If the revision is not
	 available, a zero length string should be returned."
    ::= { hardware 2 }


hwFanStatus OBJECT-TYPE
    SYNTAX DisplayString (SIZE(0..255))
    MAX-ACCESS read-only
    STATUS current
    DESCRIPTION
        "The fan status on the system."
    ::= { hardware 12 }

hwFanSpeed OBJECT-TYPE
    SYNTAX DisplayString (SIZE(0..255))
    MAX-ACCESS read-only
    STATUS current
    DESCRIPTION
        "The fan speed on the system."
    ::= { hardware 13 }
hwTempSensors OBJECT-TYPE
    SYNTAX DisplayString (SIZE(0..255))
    MAX-ACCESS read-only
    STATUS current
    DESCRIPTION
        "The temperature sensors on the system."
    ::= { hardware 14 }
hwGlobalHealthStatus OBJECT-TYPE
    SYNTAX INTEGER {
        ok(1),
        noncritical(2),
        critical(3)
        }
    MAX-ACCESS read-only
    STATUS current
    DESCRIPTION
       "
       This variable summarizes the status of several key elements of the device.
       OK:
          - All temperature sensors are below the warning threshold (eg. < 85 C);
          - All fans are running at >= 100 RPMs;
          - Both power supplies are on;
          - No panic dump exists in flash.
       Non-critical:
          - One or more temperature sensors is in the warning range (eg. >= 85 and < 100 C);
          - A panic dump exists in flash.
       Critical:
          - One or more temperature sensors is in the failure range (eg. >= 100 C);
          - One or more fans are running < 100 RPM;
          - One power supply is off.
         "
    ::= { hardware 15 }



hwESN OBJECT-TYPE
    SYNTAX DisplayString (SIZE(0..12))
    MAX-ACCESS read-only
    STATUS current
    DESCRIPTION
	"The ESN of the switch."
    ::= { hardware 40 }



    -- Port operation table
    agPortOperTable OBJECT-TYPE
	SYNTAX  SEQUENCE OF AgPortOperTableEntry
	MAX-ACCESS  not-accessible
	STATUS  current
	DESCRIPTION
	    "The table of port operations."
	::= { agentOper 1 }

    agPortOperTableEntry OBJECT-TYPE
	SYNTAX  AgPortOperTableEntry
	MAX-ACCESS  not-accessible
	STATUS  current
	DESCRIPTION
	    "A row in the port operations table."
	INDEX   { portOperIdx }
	::= { agPortOperTable 1 }

    AgPortOperTableEntry ::=
	SEQUENCE {
	    portOperIdx	    PortNumber,
	    portOperRmon	    INTEGER,
	    portOperLearning    INTEGER,
	    portOperState	    INTEGER
	}

    portOperIdx OBJECT-TYPE
	SYNTAX  PortNumber
	MAX-ACCESS  read-only
	STATUS  current
	DESCRIPTION
	    "The port index."
	::= { agPortOperTableEntry 1 }

    portOperState OBJECT-TYPE
	SYNTAX  INTEGER {
	    enabled(1),
	    disabled(2)
	    }
	MAX-ACCESS  read-write
	STATUS  current
	DESCRIPTION
	    "Enable/Disable port."
	::= { agPortOperTableEntry 2 }

    portOperRmon OBJECT-TYPE
	SYNTAX  INTEGER {
	    enabled(1),
	    disabled(2)
	    }
	MAX-ACCESS  read-write
	STATUS  current
	DESCRIPTION
	    "Enable/Disable RMON for port."
	::= { agPortOperTableEntry 3 }

    portOperLearning OBJECT-TYPE
	SYNTAX  INTEGER {
	    enabled(1),
	    disabled(2)
	    }
	MAX-ACCESS  read-write
	STATUS  current
	DESCRIPTION
	    "Enable/Disable L2 (FDB) Learning for this port."
	::= { agPortOperTableEntry 4 }


    --portOperDot1x	    OBJECT IDENTIFIER ::= { agPortOperTableEntry 4 }

    portOperDot1xTable OBJECT-TYPE
	SYNTAX  SEQUENCE OF PortOperDot1xTableEntry
	MAX-ACCESS  not-accessible
	STATUS  current
	DESCRIPTION
	    "The table of port operations."
	::= { agentOper 4 }

    portOperDot1xTableEntry OBJECT-TYPE
	SYNTAX  PortOperDot1xTableEntry
	MAX-ACCESS  not-accessible
	STATUS  current
	DESCRIPTION
	    "A row in the port 802.1x operation table."
	INDEX   { portOperDot1xIndx }
	::= { portOperDot1xTable 1 }

    PortOperDot1xTableEntry ::= SEQUENCE {
	portOperDot1xIndx        	PortNumber,
	portOperDot1xReset		INTEGER,
	portOperDot1xReauth		INTEGER
	}

    portOperDot1xIndx OBJECT-TYPE
	SYNTAX  PortNumber
	MAX-ACCESS  read-only
	STATUS  current
	DESCRIPTION
	    "The port index."
	::= { portOperDot1xTableEntry 1 }

    portOperDot1xReset OBJECT-TYPE
	SYNTAX  INTEGER {
	    no(1),
	    yes(2)
	    }
	MAX-ACCESS  read-write
	STATUS  current
	DESCRIPTION
	    "Reinitialize 802.1x access control on port."
	::= { portOperDot1xTableEntry 2 }

    portOperDot1xReauth OBJECT-TYPE
	SYNTAX  INTEGER {
	    no(1),
	    yes(2)
	    }
	MAX-ACCESS  read-write
	STATUS  current
	DESCRIPTION
	    "Initiate reauthentication on port."
	::= { portOperDot1xTableEntry 3 }

    ntpOperSendReq OBJECT-TYPE
	SYNTAX  INTEGER {
	    no(1),
	    yes(2)
	    }
	MAX-ACCESS  read-write
	STATUS  current
	DESCRIPTION
	    "Allows the user to send requests to the NTP server."
	::= { agNTPOper 1 }

-- Oper PRM settings


agSrvLedOper         OBJECT IDENTIFIER ::= { agentOper 5 }

srvLedOper OBJECT-TYPE
	SYNTAX  INTEGER {
	    enabled(0),
	    disabled(1)
	    }
	MAX-ACCESS  read-write
	STATUS  current
	DESCRIPTION
	    "Enable/disable Service Required LED."
	::= { agSrvLedOper 1 }

-- Port information table

portInfoTable OBJECT-TYPE
    SYNTAX  SEQUENCE OF PortInfoTableEntry
    MAX-ACCESS  not-accessible
    STATUS  current
    DESCRIPTION
        "The table of port information."
    ::= { portInfo 1 }

portInfoTableEntry OBJECT-TYPE
    SYNTAX  PortInfoTableEntry
    MAX-ACCESS  not-accessible
    STATUS  current
    DESCRIPTION
        "A row in the port information table."
    INDEX   { portInfoIndx }
    ::= { portInfoTable 1 }

PortInfoTableEntry ::= SEQUENCE {
    portInfoIndx                PortNumber,
    portInfoSpeed               INTEGER,
    portInfoMode                INTEGER,
    portInfoFlowCtrl            INTEGER,
    portInfoLink                INTEGER,
    portInfoPhyIfDescr          DisplayString,
    portInfoPhyIfType           INTEGER,
    portInfoPhyIfMtu            Integer32,
    portInfoPhyIfPhysAddress    PhysAddress,
    portInfoPhyIfOperStatus     INTEGER,
    portInfoPhyIfLastChange     TimeTicks,
    portInfoLearning            INTEGER,
    portInfoBpduGuard           INTEGER,
    portInfoPvid                Unsigned32,
    portInfoVlanTag             INTEGER
   ,portInfoErrDisableRecovery  INTEGER
   ,portInfoErrDisableTimeLeft  INTEGER
   ,portInfoExtGuard            INTEGER
   ,portInfoLFDState            INTEGER
    }

portInfoIndx OBJECT-TYPE
    SYNTAX  PortNumber
    MAX-ACCESS  read-only
    STATUS  current
    DESCRIPTION
        "The port index."
    ::= { portInfoTableEntry 1 }

portInfoSpeed OBJECT-TYPE
    SYNTAX  INTEGER {
        mbs10(2),
        mbs100(3),
        mbs1000(4),
        any(5)
	,
        mbs10000(6)
        ,
        mbs40000(7)
        }
    MAX-ACCESS  read-only
    STATUS  current
    DESCRIPTION
        "The current operational speed of the port."
    ::= { portInfoTableEntry 2 }

portInfoMode OBJECT-TYPE
    SYNTAX  INTEGER {
        full-duplex(2),
        half-duplex(3)
        }
    MAX-ACCESS  read-only
    STATUS  current
    DESCRIPTION
        "The current operational mode of the port."
    ::= { portInfoTableEntry 3 }

portInfoFlowCtrl OBJECT-TYPE
    SYNTAX  INTEGER {
        transmit(2),
        receive(3),
        both(4),
        none(5)
        }
    MAX-ACCESS  read-only
    STATUS  current
    DESCRIPTION
        "The current operational flow control of the port."
    ::= { portInfoTableEntry 4 }

portInfoLink OBJECT-TYPE
    SYNTAX  INTEGER {
        up(1),
        down(2),
        disabled(3),
        inoperative(4), -- unrecognized PCI device
        errdisabled(5)
        }
     MAX-ACCESS  read-only
     STATUS  current
     DESCRIPTION
         "The current operational link status of the port."
     ::= { portInfoTableEntry 5 }

portInfoPhyIfDescr OBJECT-TYPE
    SYNTAX  DisplayString (SIZE (0..255))
    MAX-ACCESS  read-only
    STATUS  current
    DESCRIPTION
	    "A textual string containing information about the
	    interface.  This string should include the name of
	    the manufacturer, the product name and the version
	    of the hardware interface."
    ::= { portInfoTableEntry 6 }

portInfoPhyIfType OBJECT-TYPE
    SYNTAX  INTEGER {
		other(1),          -- none of the following
		regular1822(2),
		hdh1822(3),
		ddn-x25(4),
		rfc877-x25(5),
		ethernet-csmacd(6),
		iso88023-csmacd(7),
		iso88024-tokenBus(8),
		iso88025-tokenRing(9),
		iso88026-man(10),
		starLan(11),
		proteon-10Mbit(12),
		proteon-80Mbit(13),
		hyperchannel(14),
		fddi(15),
		lapb(16),
		sdlc(17),
		ds1(18),           -- T-1
		e1(19),            -- european equiv. of T-1
		basicISDN(20),
		primaryISDN(21),   -- proprietary serial
		propPointToPointSerial(22),
		ppp(23),
		softwareLoopback(24),
		eon(25),            -- CLNP over IP [11]
		ethernet-3Mbit(26),
		nsip(27),           -- XNS over IP
		slip(28),           -- generic SLIP
		ultra(29),          -- ULTRA technologies
		ds3(30),            -- T-3
		sip(31),            -- SMDS
		frame-relay(32)
	    }
    MAX-ACCESS  read-only
    STATUS  current
    DESCRIPTION
	    "The type of interface, distinguished according to
	    the physical/link protocol(s) immediately `below'
	    the network layer in the protocol stack."
    ::= { portInfoTableEntry 7 }

portInfoPhyIfMtu OBJECT-TYPE
    SYNTAX  Integer32
    MAX-ACCESS  read-only
    STATUS  current
    DESCRIPTION
	    "The size of the largest datagram which can be
	    sent/received on the interface, specified in
	    octets.  For interfaces that are used for
	    transmitting network datagrams, this is the size
	    of the largest network datagram that can be sent
	    on the interface."
    ::= { portInfoTableEntry 8 }

portInfoPhyIfPhysAddress OBJECT-TYPE
    SYNTAX  PhysAddress
    MAX-ACCESS  read-only
    STATUS  current
    DESCRIPTION
	    "The interface's address at the protocol layer
	    immediately `below' the network layer in the
	    protocol stack. For interfaces which do not have
	    such an address (e.g., a serial line), this object
	    should contain an octet string of zero length."
    ::= { portInfoTableEntry 9 }

portInfoPhyIfOperStatus OBJECT-TYPE
    SYNTAX  INTEGER {
	up(1),       -- ready to pass packets
	down(2),
	testing(3)   -- in some test mode
	}
    MAX-ACCESS  read-only
    STATUS  current
    DESCRIPTION
	    "The current operational state of the interface.
	    The testing(3) state indicates that no operational
	    packets can be passed."
    ::= { portInfoTableEntry 10 }

portInfoPhyIfLastChange OBJECT-TYPE
    SYNTAX  TimeTicks
    MAX-ACCESS  read-only
    STATUS  current
    DESCRIPTION
	    "The value of sysUpTime at the time the interface
	    entered its current operational state.  If the
	    current state was entered prior to the last re-
	    initialization of the local network management
	    subsystem, then this object contains a zero
	    value."
    ::= { portInfoTableEntry 11 }


portInfoLearning OBJECT-TYPE
    SYNTAX  INTEGER {
		enabled(1),
		disabled(2)
	    }
    MAX-ACCESS  read-only
    STATUS  current
    DESCRIPTION
	    "The port L2 (FDB) Learning state."
    ::= { portInfoTableEntry 18 }

portInfoBpduGuard OBJECT-TYPE
    SYNTAX INTEGER {
        enabled(1),
        disabled(2)
        }
    MAX-ACCESS read-only
    STATUS current
    DESCRIPTION
        "The operational status of BPDU Guard on the port."
    ::= { portInfoTableEntry 20 }

portInfoPvid    OBJECT-TYPE
    SYNTAX  Unsigned32
    MAX-ACCESS  read-only
    STATUS  current
    DESCRIPTION
        "This is the operational port vlan-id of the port. Typically,
         the value of this object is the same as the value of the
         agPortCurCfgPVID object. But if, for example, 802.1x is
         enabled on the port and the port is assigned a vlan-id via
         802.1x, this port will be moved to the assigned vlan even
         when the port is configured with a different PVID."
    ::= { portInfoTableEntry 21}

portInfoVlanTag OBJECT-TYPE
    SYNTAX  INTEGER {
        untagged(0),
        tagged(1)
        }
    MAX-ACCESS  read-only
    STATUS  current
    DESCRIPTION
        "This is the operational VLAN tag state of the port. Typically,
         the value of this object is the same as the value of the
         agPortCurCfgVlanTag objec. But if, for example, 802.1x is
         enabled on the port and if the port is assigned a vlan via
         802.1x, the port will be operationally untagged even when the
         port is configured to be tagged."
    ::= { portInfoTableEntry 22}

portInfoErrDisableRecovery OBJECT-TYPE
    SYNTAX      INTEGER {
                    enable(1),
                    disable(2)
                }
    MAX-ACCESS  read-only
    STATUS      current
    DESCRIPTION
        "This object indicates whether the system will automatically
         re-enable an error-disabled port after the time interval
         indicated by agCurCfgErrDisableTimeout has elapsed. A port
         is in error-disabled state when it has been operationally
         disabled by the system due to an error condition.

         The value of this object is 'enable' if the values of both
         the global agCurCfgErrDisableRecovery object and the port's
         agPortCurCfgErrDisableRecovery object are 'enable'."
    ::= { portInfoTableEntry 23 }

portInfoErrDisableTimeLeft OBJECT-TYPE
    SYNTAX      INTEGER (0 .. 86400)
    MAX-ACCESS  read-only
    STATUS      current
    DESCRIPTION
        "If the portInfoErrDisableRecovery object has a value of 'enable'
         and the portInfoLink object has a value of 'errdisabled', the
         value of this object indicates the remaining time, in seconds,
         before the system automatically re-enables this port."
    ::= { portInfoTableEntry 24 }

portInfoExtGuard OBJECT-TYPE
    SYNTAX INTEGER {
        loop(1),
        root(2),
        global-loop(3),
        no-guard(0)
        }
    MAX-ACCESS read-only
    STATUS current
    DESCRIPTION
        "The operational status of STP Loop/Root Guard on the port."
    ::= { portInfoTableEntry 25 }


portInfoLFDState OBJECT-TYPE
    SYNTAX      INTEGER {
                    yes(1),
                    no(2)
                }
    MAX-ACCESS  read-only
    STATUS      current
    DESCRIPTION
        "This object indicates whether the port is error-disabled due
         to excessive link flaps.  The value of this object is 'yes'
         if the port is error-disabled due to excessive link flaps,
         otherwise the value is 'no'."
    ::= { portInfoTableEntry 26 }








-- Agent System Group
-- This group of objects take effect on the 'SET' request.
-- There is no need to 'apply' or 'save'.

agApplyConfiguration OBJECT-TYPE
    SYNTAX  INTEGER {
        other(1),
        apply(2)
        }
    MAX-ACCESS  read-write
    STATUS  current
    DESCRIPTION
        "This is an action object to apply the changes made to configuration
         of the switch. By setting the value to apply(2), all the changes
         made since the last apply are written to the new configuration block.

         other(1) is returned when this object ie read. "
    ::= { agSystem 2 }

agSavePending OBJECT-TYPE
    SYNTAX  INTEGER {
        saveNeeded(1),
        noSaveNeeded(2)
        }
    MAX-ACCESS  read-only
    STATUS  current
    DESCRIPTION
        "This object, when read, gives the user information
         whether an save action is needed and that the configuration
         has been applied but not saved to the flash."
    ::= { agSystem 3 }

agSaveConfiguration OBJECT-TYPE
    SYNTAX  INTEGER {
        ok(1),
        saveActive(2),
        notSaveActive(3)
        }
    MAX-ACCESS  read-write
    STATUS  current
    DESCRIPTION
        "This is an action object to write current configuration to
         nonvolatile storage.

         When issued with the saveActive, the active configuration
         in flash is saved to backup in flash and then the new
         configuration is saved to the active configuration in flash.

         When issued with notSaveActive, the active configuration
         is NOT saved to the flash and the active configuration is
         overwritten with the new configuration.

         ok(1) is returned always when read."
    ::= { agSystem 4 }

agRevert OBJECT-TYPE
    SYNTAX  INTEGER {
        other(1),
        revert(2)
        }
    MAX-ACCESS  read-write
    STATUS  current
    DESCRIPTION
        "This is an action object to revert the unapplied changes
         made to the switch. By setting the value to revert(2),
         all the unapplied changes will be reverted. This action
         will copy the current_config to the new configuration block.

         other(1) is returned when this object is read. "
    ::= { agSystem 5 }


agReset OBJECT-TYPE
    SYNTAX  INTEGER {
        other(1),
        reset(2)
        }
    MAX-ACCESS  read-write
    STATUS  current
    DESCRIPTION
        "This is an action object to reboot the agent.
         other(1) is returned always when read."
    ::= { agSystem 7 }

agConfigForNxtReset OBJECT-TYPE
    SYNTAX  INTEGER {
        active(2),
        backup(3),
        default(4)
        }
    MAX-ACCESS  read-write
    STATUS  current
    DESCRIPTION
        "The configuration information to be loaded from at next reset.

          The following values are writable:
              active(2)...active configuration block
              backup(3)...backup configuration block
              default(4)..default configuration block"
    ::= { agSystem 8 }

agImageForNxtReset OBJECT-TYPE
    SYNTAX  INTEGER {
        image1(2),
        image2(3)
        }
    MAX-ACCESS  read-write
    STATUS  current
    DESCRIPTION
        "The software image to be booted from at next reset.

         The following values are writable:
             image1(2)...image 1
             image2(3)...image 2"
    ::= { agSystem 9 }

agSoftwareVersion OBJECT-TYPE
    SYNTAX  DisplayString (SIZE(0..16))
    MAX-ACCESS  read-only
    STATUS  current
    DESCRIPTION
        "The version of the software image that is currently running on the
         system in the form of 'major.minor.maintenance.bugfix'.  A zero
         length string is returned if version is not available."
    ::= { agSystem 10 }

agBootVer OBJECT-TYPE
    SYNTAX  DisplayString (SIZE(0..16))
    MAX-ACCESS  read-only
    STATUS  current
    DESCRIPTION
        "The version of the boot code in the form of 'major.minor.bugfix'.
         A zero length string is returned if version is not available."
    ::= { agSystem 11 }

agImage1Ver OBJECT-TYPE
    SYNTAX  DisplayString (SIZE(0..128))
    MAX-ACCESS  read-only
    STATUS  current
    DESCRIPTION
        "The version of the software image stored in image 1 storage in the
         form of 'major.minor.bugfix'.  A zero length string is returned if
         version is not available or there is no valid software image."
    ::= { agSystem 12 }

agImage2Ver OBJECT-TYPE
    SYNTAX  DisplayString (SIZE(0..128))
    MAX-ACCESS  read-only
    STATUS  current
    DESCRIPTION
        "The version of the software image stored in image 2 storage in the
         form of 'major.minor.bugfix'.  A zero length string is returned if
         version is not available or there is no valid software image."
    ::= { agSystem 13 }

agRtcDate OBJECT-TYPE
    SYNTAX  DisplayString (SIZE(0..16))
    MAX-ACCESS  read-write
    STATUS  current
    DESCRIPTION
        "The date on the real time clock in the form of 'mm/dd/yy'.
         A zero length string is returned if date is not available."
    ::= { agSystem 14 }

agRtcTime OBJECT-TYPE
    SYNTAX  DisplayString (SIZE(0..16))
    MAX-ACCESS  read-write
    STATUS  current
    DESCRIPTION
        "The time on the real time clock in the form of 'hh:mm:ss'.
         A zero length string is returned if time is not available."
    ::= { agSystem 15 }

agLastSetErrorReason   OBJECT-TYPE
    SYNTAX  DisplayString (SIZE(0..255))
    MAX-ACCESS  read-only
    STATUS  current
    DESCRIPTION
        "The error reason of the last SET failure."
    ::= { agSystem 16 }

agCurCfgHttpServerPort OBJECT-TYPE
    SYNTAX  INTEGER (1..65535)
    MAX-ACCESS  read-only
    STATUS  current
    DESCRIPTION
        "The TCP port number that the HTTP server is listening to
         in the current configuration block."
    ::= { agSystem 17 }

agNewCfgHttpServerPort OBJECT-TYPE
    SYNTAX  INTEGER (1..65535)
    MAX-ACCESS  read-write
    STATUS  current
    DESCRIPTION
        "The TCP port number that the HTTP server is listening to
         in the new configuration block."
    ::= { agSystem 18 }

agCurCfgLoginBanner OBJECT-TYPE
    SYNTAX  DisplayString (SIZE(0..80))
    MAX-ACCESS  read-only
    STATUS  current
    DESCRIPTION
        "The user defined login banner."
    ::= { agSystem 19 }

agNewCfgLoginBanner OBJECT-TYPE
    SYNTAX  DisplayString (SIZE(0..80))
    MAX-ACCESS  read-write
    STATUS  current
    DESCRIPTION
        "The user defined login banner."
    ::= { agSystem 20 }

agCurCfgLoginNotice OBJECT-TYPE
    SYNTAX  DisplayString (SIZE(0..80))
    MAX-ACCESS  read-only
    STATUS  current
    DESCRIPTION
        "The user defined login notice."
    ::= { agSystem 78 }

agNewCfgLoginNotice OBJECT-TYPE
    SYNTAX  DisplayString (SIZE(0..80))
    MAX-ACCESS  read-write
    STATUS  current
    DESCRIPTION
        "The user defined login notice."
    ::= { agSystem 79 }


agCurCfgConsole OBJECT-TYPE
    SYNTAX  INTEGER {
        enabled(1),
        disabled(2)
        }
    MAX-ACCESS  read-only
    STATUS  current
    DESCRIPTION
        "Enable or disable console output of syslog messages."
    ::= { agSystem 23 }

agNewCfgConsole OBJECT-TYPE
    SYNTAX  INTEGER {
        enabled(1),
        disabled(2)
        }
    MAX-ACCESS  read-write
    STATUS  current
    DESCRIPTION
        "Enable or disable console output of syslog messages."
    ::= { agSystem 24 }


agCurCfgBootp OBJECT-TYPE
    SYNTAX  INTEGER {
        enabled(2),
        disabled(3)
        }
    MAX-ACCESS  read-only
    STATUS  current
    DESCRIPTION
        "Enable or disable the use of BootP, as currently configured in the
         current configuration block."
    ::= { agSystem 29 }

agNewCfgBootp OBJECT-TYPE
    SYNTAX  INTEGER {
        enabled(2),
        disabled(3)
        }
    MAX-ACCESS  read-write
    STATUS  current
    DESCRIPTION
        "Enable or disable the use of BootP, in the new configuration block."
    ::= { agSystem 30 }

agSlotNumber OBJECT-TYPE
    SYNTAX INTEGER (1..10)
    MAX-ACCESS read-only
    STATUS current
    DESCRIPTION
	"Identifies the slot in which this switch is installed. If the
         agent implementing this MIB is not a blade in a chassis this
         value has no meaning."
    ::= { agSystem 31 }

agCurCfgSnmpTimeout OBJECT-TYPE
    SYNTAX  INTEGER (1..30)
    MAX-ACCESS  read-only
    STATUS  current
    DESCRIPTION
        "Once SNMP operations like agApplyConfig, agDiffState and
         agDumpState, which use the state machine are done the resources
         used by these operations need to be freed by setting the state
         back to 'idle' so others can issue the commands via SNMP.
         agSnmpTimeout indicates the number of minutes before the resources
         are freed and the state set back to 'idle' if this operation is not
         performed by the user."
    ::= { agSystem 32 }

agNewCfgSnmpTimeout OBJECT-TYPE
    SYNTAX  INTEGER (1..30)
    MAX-ACCESS  read-write
    STATUS  current
    DESCRIPTION
        "Once SNMP operations like agApplyConfig, agDiffState and
         agDumpState, which use the state machine are done the resources
         used by these operations need to be freed by setting the state
         back to 'idle' so others can issue the commands via SNMP.
         agSnmpTimeout indicates the number of minutes before the resources
         are freed and the state set back to 'idle' if this operation is not
         performed by the user."
    ::= { agSystem 33 }

agCurCfgTelnetServerPort OBJECT-TYPE
    SYNTAX  INTEGER (1..65535)
    MAX-ACCESS  read-only
    STATUS  current
    DESCRIPTION
        "The TCP port number that the telnet server listens for telnet
         sessions."
    ::= { agSystem 34 }

agNewCfgTelnetServerPort OBJECT-TYPE
    SYNTAX  INTEGER (1..65535)
    MAX-ACCESS  read-write
    STATUS  current
    DESCRIPTION
        "The TCP port number that the telnet server listens for telnet
         sessions."
    ::= { agSystem 35 }

agClearFlashDump OBJECT-TYPE
    SYNTAX  INTEGER {
        ok(1),
        clear(2)
        }
    MAX-ACCESS  read-write
    STATUS  current
    DESCRIPTION
        "This is an action object to clear the FLASH dump.
         ok(1) is returned when this object is read. "
    ::= { agSystem 36 }




agCurCfgTrapSrcIf OBJECT-TYPE
    SYNTAX  Integer32
    MAX-ACCESS  read-only
    STATUS  current
    DESCRIPTION
        "The SNMP trap source interface number."
    ::= { agSystem 39 }

agNewCfgTrapSrcIf OBJECT-TYPE
    SYNTAX  Integer32
    MAX-ACCESS  read-write
    STATUS  current
    DESCRIPTION
        "The SNMP trap source interface number."
    ::= { agSystem 40 }




agCurCfgHttpsServerPort OBJECT-TYPE
    SYNTAX  INTEGER (1..65535)
    MAX-ACCESS  read-only
    STATUS  current
    DESCRIPTION
        "The TCP port number that the HTTPS server is listening to
         in the current configuration block."
    ::= { agSystem 49 }

agNewCfgHttpsServerPort OBJECT-TYPE
    SYNTAX  INTEGER (1..65535)
    MAX-ACCESS  read-write
    STATUS  current
    DESCRIPTION
        "The TCP port number that the HTTPS server is listening to
         in the new configuration block."
    ::= { agSystem 50 }

agCurCfgTftpServerPort OBJECT-TYPE
    SYNTAX  INTEGER (1..65535)
    MAX-ACCESS  read-only
    STATUS  current
    DESCRIPTION
        "The TCP port number that the TFTP server is listening to
         in the current configuration block."
    ::= { agSystem 51 }

agNewCfgTftpServerPort OBJECT-TYPE
    SYNTAX  INTEGER (1..65535)
    MAX-ACCESS  read-write
    STATUS  current
    DESCRIPTION
        "The TCP port number that the TFTP server is listening to
         in the new configuration block."
    ::= { agSystem 52 }

agRackId OBJECT-TYPE
    SYNTAX  DisplayString (SIZE(0..127))
    MAX-ACCESS  read-only
    STATUS  current
    DESCRIPTION
        "The rack unique identifier."
    ::= { agSystem 53 }

agChassis OBJECT-TYPE
    SYNTAX  DisplayString (SIZE(0..127))
    MAX-ACCESS  read-only
    STATUS  current
    DESCRIPTION
        "Chassis serial number."
    ::= { agSystem 54 }

agCurTimeZone   OBJECT-TYPE
    SYNTAX  INTEGER {
    none(0),
    africa-Algeria(1),
    africa-Angola(2),
    africa-Benin(3),
    africa-Botswana(4),
    africa-Burkina-Faso(5),
    africa-Burundi(6),
    africa-Cameroon(7),
    africa-Central-African-Rep(8),
    africa-Chad(9),
    africa-Congo-WestDemRepCongo(10),
    africa-Congo-EastDemRepCongo(11),
    africa-Congo-Rep(12),
    africa-Cote-dIvoire(13),
    africa-Djibouti(14),
    africa-Egypt(15),
    africa-Equatorial-Guinea(16),
    africa-Eritrea(17),
    africa-Ethiopia(18),
    africa-Gabon(19),
    africa-Gambia(20),
    africa-Ghana(21),
    africa-Guinea(22),
    africa-Guinea-Bissau(23),
    africa-Kenya(24),
    africa-Lesotho(25),
    africa-Liberia(26),
    africa-Libya(27),
    africa-Malawi(28),
    africa-Mali-SouthWestMali(29),
    africa-Mali-NorthEastMali(30),
    africa-Mauritania(31),
    africa-Morocco(32),
    africa-Mozambique(33),
    africa-Namibia(34),
    africa-Niger(35),
    africa-Nigeria(36),
    africa-Rwanda(37),
    africa-SaoTome-And-Principe(38),
    africa-Senegal(39),
    africa-SierraLeone(40),
    africa-Somalia(41),
    africa-SouthAfrica(42),
    africa-Spain-Mainland(43),
    africa-Spain-CeutaMelilla(44),
    africa-Spain-CanaryIslands(45),
    africa-Sudan(46),
    africa-Swaziland(47),
    africa-Tanzania(48),
    africa-Togo(49),
    africa-Tunisia(50),
    africa-Uganda(51),
    africa-Western-Sahara(52),
    africa-Zambia(53),
    africa-Zimbabwe(54),
    americas-Anguilla(55),
    americas-Antigua-Barbuda(56),
    americas-Argentina-EArgentina(57),
    americas-Argentina-MostLocations(58),
    americas-Argentina-Jujuy(59),
    americas-Argentina-Catamarca(60),
    americas-Argentina-Mendoza(61),
    americas-Aruba(62),
    americas-Bahamas(63),
    americas-Barbados(64),
    americas-Belize(65),
    americas-Bolivia(66),
    americas-Brazil-AtlanticIslands(67),
    americas-Brazil-AmapaEPara(68),
    americas-Brazil-NEBrazil(69),
    americas-Brazil-Pernambuco(70),
    americas-Brazil-Tocantins(71),
    americas-Brazil-AlagoasSergipe(72),
    americas-Brazil-SSEBrazil(73),
    americas-Brazil-MatoGrossoDoSul(74),
    americas-Brazil-WParaRondonia(75),
    americas-Brazil-Roraima(76),
    americas-Brazil-EAmazonas(77),
    americas-Brazil-WAmazonas(78),
    americas-Brazil-Acre(79),
    americas-Canada-NewfoundlandIsland(80),
    americas-Canada-AtlanTime-NovaScotia(81),
    americas-Canada-AtlanTime-ELabrador(82),
    americas-Canada-EastTime-OntarioMostlocation(83),
    americas-Canada-EastTime-ThunderBay(84),
    americas-Canada-EastStdTime-PangnirtungNunavut(85),
    americas-Canada-EastStdTime-EastNunavut(86),
    americas-Canada-EastStdTime-CenNunavut(87),
    americas-Canada-CenTime-ManitobaWestOntario(88),
    americas-Canada-CenTime-RainyRiver(89),
    americas-Canada-CenTime-WestNunavut(90),
    americas-Canada-CenStdTime-SaskatchewanMostlocation(91),
    americas-Canada-CenStdTime-SaskatchewanMidwest(92),
    americas-Canada-MountTime-AlbertaEastBritishColumbia(93),
    americas-Canada-MountTime-CentralNorthwestTerritories(94),
    americas-Canada-MountTime-WestNorthwestTerritories(95),
    americas-Canada-MountStdTime-DawsonCrkStJohnBritColumbia(96),
    americas-Canada-PacificTime-WestBritishColumbia(97),
    americas-Canada-PacificTime-SouthYukon(98),
    americas-Canada-PacificTime-NorthYukon(99),
    americas-CaymanIslands(100),
    americas-Chile-MostLocation(101),
    americas-Chile-EasterIsland(102),
    americas-Colombia(103),
    americas-CostaRica(104),
    americas-Cuba(105),
    americas-Dominica(106),
    americas-DominicanRepublic (107),
    americas-Ecuador(108),
    americas-ElSalvado(109),
    americas-FrenchGuiana(110),
    americas-Greenland-MostLocation(111),
    americas-Greenland-EastCoastNorthScoresbysund(112),
    americas-Greenland-ScoresbysundIttoqqortoormiit(113),
    americas-Greenland-ThulePituffik(114),
    americas-Grenada(115),
    americas-Guadeloupe(116),
    americas-Guatemala(117),
    americas-Guyana(118),
    americas-Haiti(119),
    americas-Honduras(120),
    americas-Jamaica(121),
    americas-Martinique(122),
    americas-Mexico-CentTime-Mostlocations(123),
    americas-Mexico-CentTime-QuintanaRoo(124),
    americas-Mexico-CentTime-CampecheYucatan(125),
    americas-Mexico-CentTime-CoahuilaDurNuevoLeonTam(126),
    americas-Mexico-MountTime-SBajaNayaritSinaloa(127),
    americas-Mexico-MountTime-Chihuahua(128),
    americas-Mexico-MountStdTime-Sonora(129),
    americas-Mexico-PacificTime(130),
    americas-Montserrat(131),
    americas-NetherlandsAntilles(132),
    americas-Nicaragua(133),
    americas-Panama(134),
    americas-Paraguay(135),
    americas-Peru(136),
    americas-PuertoRico(137),
    americas-StKittsAndNevis(138),
    americas-StLucia(139),
    americas-StPierreAndMiquelon(140),
    americas-StVincent(141),
    americas-Suriname(142),
    americas-TrinidadAndTobago(143),
    americas-TurksAndCaicosIs(144),
    americas-USA-EastTime(145),
    americas-USA-EastTime-MichiganMostLocation(146),
    americas-USA-EastTime-KentuckyLouisvilleArea(147),
    americas-USA-EastTime-KentuckyWayneCounty(148),
    americas-USA-EastStdTime-IndianaMostLocations(149),
    americas-USA-EastStdTime-IndianaCrawfordCounty(150),
    americas-USA-EastStdTime-IndianaStarkeCounty(151),
    americas-USA-EastStdTime-IndianaSwitzerlandCounty(152),
    americas-USA-CentTime(153),
    americas-USA-CentTime-MichiganWisconsinborder(154),
    americas-USA-CentTime-NorthDakotaOliverCounty(155),
    americas-USA-MountTime(156),
    americas-USA-MountTime-SouthIdahoAndEastOregon(157),
    americas-USA-MountTime-Navajo(158),
    americas-USA-MountStdTime-Arizona(159),
    americas-USA-PacificTime(160),
    americas-USA-AlaskaTime(161),
    americas-USA-AlaskaTime-AlaskaPanhandle(162),
    americas-USA-AlaskaTime-AlaskaPanhandleNeck(163),
    americas-USA-AlaskaTime-WestAlaska(164),
    americas-USA-AleutianIslands(165),
    americas-USA-Hawaii(166),
    americas-Uruguay(167),
    americas-Venezuela(168),
    americas-VirginIslands-UK(169),
    americas-VirginIslands-US(170),
    antarctica-McMurdoStationRossIsland(171),
    antarctica-Amundsen-ScottStationSouthPole(172),
    antarctica-PalmerStationAnversIsland(173),
    antarctica-MawsonStationHolmeBay(174),
    antarctica-DavisStationVestfoldHills(175),
    antarctica-CaseyStationBaileyPeninsula(176),
    antarctica-VostokStationSMagneticPole(177),
    antarctica-Dumont-dUrvilleBaseTerreAdelie(178),
    antarctica-SyowaStationEOngulI(179),
    arcticOcean-Svalbard(180),
    arcticOcean-JanMayen(181),
    asia-Afghanistan(182),
    asia-Armenia(183),
    asia-Azerbaijan(184),
    asia-Bahrain(185),
    asia-Bangladesh(186),
    asia-Bhutan(187),
    asia-Brunei(188),
    asia-Cambodia(189),
    asia-China-EastChinaBeijingGuangdongShanghai(190),
    asia-China-Heilongjiang(191),
    asia-China-CentralChinaGansuGuizhouSichuanYunnan(192),
    asia-China-TibetmostofXinjiangUyghur(193),
    asia-China-SouthwestXinjiangUyghur(194),
    asia-Cyprus(195),
    asia-EastTimor(196),
    asia-Georgia(197),
    asia-HongKong(198),
    asia-India(199),
    asia-Indonesia-JavaAndSumatra(200),
    asia-Indonesia-WestCentralBorneo(201),
    asia-Indonesia-ESBorneoCelebesBaliNusaTengaWTimor(202),
    asia-Indonesia-IrianJayaAndMoluccas(203),
    asia-Iran(204),
    asia-Iraq(205),
    asia-Israel(206),
    asia-Japan(207),
    asia-Jordan(208),
    asia-Kazakhstan-MostLocations(209),
    asia-Kazakhstan-QyzylordaKyzylorda(210),
    asia-Kazakhstan-Aqtobe(211),
    asia-Kazakhstan-AtyrauMangghystau(212),
    asia-Kazakhstan-WestKazakhstan(213),
    asia-Korea-North(214),
    asia-Korea-South(215),
    asia-Kuwait(216),
    asia-Kyrgyzstan(217),
    asia-Laos(218),
    asia-Lebanon(219),
    asia-Macau(220),
    asia-Malaysia-PeninsularMalaysia(221),
    asia-Malaysia-SabahSarawak(222),
    asia-Mongolia-MostLocations(223),
    asia-Mongolia-BayanOlgiyGoviAltaiHovdUvsZavkhan(224),
    asia-Mongolia-DornodSukhbaatar(225),
    asia-Myanmar(226),
    asia-Nepal(227),
    asia-Oman(228),
    asia-Pakistan(229),
    asia-Palestine(230),
    asia-Philippines(231),
    asia-Qatar(232),
    asia-Russia-Moscow-01Kaliningrad(233),
    asia-Russia-Moscow00WestRussia(234),
    asia-Russia-Moscow01CaspianSea(235),
    asia-Russia-Moscow02Urals(236),
    asia-Russia-Moscow03WestSiberia(237),
    asia-Russia-Moscow03Novosibirsk(238),
    asia-Russia-Moscow04YeniseiRiver(239),
    asia-Russia-Moscow05LakeBaikal(240),
    asia-Russia-Moscow06LenaRiver(241),
    asia-Russia-Moscow07AmurRiver(242),
    asia-Russia-Moscow07SakhalinIsland(243),
    asia-Russia-Moscow08Magadan(244),
    asia-Russia-Moscow09Kamchatka(245),
    asia-Russia-Moscow10BeringSea(246),
    asia-SaudiArabia(247),
    asia-Singapore(248),
    asia-SriLanka(249),
    asia-Syria(250),
    asia-Taiwan(251),
    asia-Tajikistan(252),
    asia-Thailand(253),
    asia-Turkmenistan(254),
    asia-UnitedArabEmirates(255),
    asia-Uzbekistan-WestUzbekistan(256),
    asia-Uzbekistan-EastUzbekistan(257),
    asia-Vietnam(258),
    asia-Yemen(259),
    atlanticOcean-Bermuda(260),
    atlanticOcean-CapeVerde(261),
    atlanticOcean-FaeroeIslands(262),
    atlanticOcean-FalklandIslands(263),
    atlanticOcean-Iceland(264),
    atlanticOcean-Portugal-Mainland(265),
    atlanticOcean-Portugal-MadeiraIslands(266),
    atlanticOcean-Portugal-Azores(267),
    atlanticOcean-SouthGeorgia-SouthSandwichIslands(268),
    atlanticOcean-Spain-Mainland(269),
    atlanticOcean-Spain-CeutaMelilla(270),
    atlanticOcean-Spain-CanaryIslands(271),
    atlanticOcean-StHelena(272),
    atlanticOcean-Svalbard-JanMayen(273),
    australia-LordHoweIsland(274),
    australia-Tasmania(275),
    australia-Victoria(276),
    australia-NewSouthWales-MostLocations(277),
    australia-NewSouthWales-Yancowinna(278),
    australia-Queensland-MostLocations(279),
    australia-Queensland-HolidayIslands(280),
    australia-SouthAustralia(281),
    australia-NorthernTerritory(282),
    australia-WesternAustralia(283),
    europe-Albania(284),
    europe-Andorra(285),
    europe-Austria(286),
    europe-Belarus(287),
    europe-Belgium(288),
    europe-BosniaHerzegovina(289),
    europe-Britain-UKGreatBritain(290),
    europe-Britain-UKNorthernIreland(291),
    europe-Bulgaria(292),
    europe-Croatia(293),
    europe-CzechRepublic(294),
    europe-Denmark(295),
    europe-Estonia(296),
    europe-Finland(297),
    europe-France(298),
    europe-Germany(299),
    europe-Gibraltar(300),
    europe-Greece(301),
    europe-Hungary(302),
    europe-Ireland(303),
    europe-Italy(304),
    europe-Latvia(305),
    europe-Liechtenstein(306),
    europe-Lithuania(307),
    europe-Luxembourg(308),
    europe-Macedonia(309),
    europe-Malta(310),
    europe-Moldova(311),
    europe-Monaco(312),
    europe-Montenegro(421),
    europe-Netherlands(313),
    europe-Norway(314),
    europe-Poland(315),
    europe-Portugal-Mainland(316),
    europe-Portugal-MadeiraIslands(317),
    europe-Portugal-Azores(318),
    europe-Romania(319),
    europe-Russia-Moscow-01Kaliningrad(320),
    europe-Russia-Moscow00WestRussia(321),
    europe-Russia-Moscow01CaspianSea(322),
    europe-Russia-Moscow02Urals(323),
    europe-Russia-Moscow03WestSiberia(324),
    europe-Russia-Moscow03Novosibirsk(325),
    europe-Russia-Moscow04YeniseiRiver(326),
    europe-Russia-Moscow05LakeBaikal(327),
    europe-Russia-Moscow06LenaRiver(328),
    europe-Russia-Moscow07AmurRiver(329),
    europe-Russia-Moscow07SakhalinIsland(330),
    europe-Russia-Moscow08Magadan(331),
    europe-Russia-Moscow09Kamchatka(332),
    europe-Russia-Moscow10BeringSea(333),
    europe-SanMarino(334),
    europe-Serbia(348),
    europe-Slovakia(335),
    europe-Slovenia(336),
    europe-Spain-Mainland(337),
    europe-Spain-CeutaAndMelilla(338),
    europe-Spain-CanaryIslands(339),
    europe-Sweden(340),
    europe-Switzerland(341),
    europe-Turkey(342),
    europe-Ukraine-MostLocations(343),
    europe-Ukraine-Ruthenia(344),
    europe-Ukraine-Zaporozhye-ELugansk(345),
    europe-Ukraine-CentralCrimea(346),
    europe-VaticanCity(347),
    indianOcean-BritishIndianOceanTerritory(349),
    indianOcean-ChristmasIsland(350),
    indianOcean-CocosOrKeelingIslands(351),
    indianOcean-Comoros(352),
    indianOcean-FrenchSouthernAndAntarcticLands(353),
    indianOcean-Madagascar(354),
    indianOcean-Maldives(355),
    indianOcean-Mauritius(356),
    indianOcean-Mayotte(357),
    indianOcean-Reunion(358),
    indianOcean-Seychelles(359),
    pacificOcean-Chile-MostLocations(360),
    pacificOcean-Chile-EasterIslandSalayGomez(361),
    pacificOcean-CookIslands(362),
    pacificOcean-Ecuador(363),
    pacificOcean-Fiji(364),
    pacificOcean-FrenchPolynesia-SocietyIslands(365),
    pacificOcean-FrenchPolynesia-MarquesasIslands(366),
    pacificOcean-FrenchPolynesia-GambierIslands(367),
    pacificOcean-Guam(368),
    pacificOcean-Kiribati-GilbertIslands(369),
    pacificOcean-Kiribati-PhoenixIslands(370),
    pacificOcean-Kiribati-LineIslands(371),
    pacificOcean-MarshallIslands-MostLocations(372),
    pacificOcean-MarshallIslands-Kwajalein(373),
    pacificOcean-Micronesia-Yap(374),
    pacificOcean-Micronesia-TrukOrChuuk(375),
    pacificOcean-Micronesia-PonapeOrPohnpei(376),
    pacificOcean-Micronesia-Kosrae(377),
    pacificOcean-Nauru(378),
    pacificOcean-NewCaledonia(379),
    pacificOcean-NewZealand-MostLocations(380),
    pacificOcean-NewZealand-ChathamIslands(381),
    pacificOcean-Niue(382),
    pacificOcean-NorfolkIsland(383),
    pacificOcean-NorthernMarianaIslands(384),
    pacificOcean-Palau(385),
    pacificOcean-PapuaNewGuinea(386),
    pacificOcean-Pitcairn(387),
    pacificOcean-SamoaAmerican(388),
    pacificOcean-SamoaWestern(389),
    pacificOcean-SolomonIslands(390),
    pacificOcean-Tokelau(391),
    pacificOcean-Tonga(392),
    pacificOcean-Tuvalu(393),
    pacificOceanUSA-EastTime(394),
    pacificOceanUSA-EastTime-MichiganMostLocations(395),
    pacificOceanUSA-EastTime-KentuckyLouisvilleArea(396),
    pacificOceanUSA-EastTime-KentuckyWayneCounty(397),
    pacificOceanUSA-EastStdTime-IndianaMostLocations(398),
    pacificOceanUSA-EastStdTime-IndianaCrawfordCounty(399),
    pacificOceanUSA-EastStdTime-IndianaStarkeCounty(400),
    pacificOceanUSA-EastStdTime-IndianaSwitzerlandCounty(401),
    pacificOceanUSA-CentTime(402),
    pacificOceanUSA-CentTime-MichiganWisconsinborder(403),
    pacificOceanUSA-CentTime-NorthDakotaOliverCounty(404),
    pacificOceanUSA-MountTime(405),
    pacificOceanUSA-MountTime-SouthIdahoAndEastOregon(406),
    pacificOceanUSA-MountTime-Navajo(407),
    pacificOceanUSA-MountStdTime-Arizona(408),
    pacificOceanUSA-PacificTime(409),
    pacificOceanUSA-AlaskaTime(410),
    pacificOceanUSA-AlaskaTime-AlaskaPanhandle(411),
    pacificOceanUSA-AlaskaTime-AlaskaPanhandleNeck(412),
    pacificOceanUSA-AlaskaTime-WestAlaska(413),
    pacificOceanUSA-AleutianIslands(414),
    pacificOceanUSA-Hawaii(415),
    pacificOcean-USMinorOutlyingIslands-JohnstonAtoll(416),
    pacificOcean-USMinorOutlyingIslands-MidwayIslands(417),
    pacificOcean-USMinorOutlyingIslands-WakeIsland(418),
    pacificOcean-Vanuatu(419),
    pacificOcean-WallisAndFutuna(420)
	}
    MAX-ACCESS read-only
    STATUS  current
    DESCRIPTION
        "The time zone.
         Note: Locations are alphabetically ordered and
         the corresponding code is not reflected in CLI."
    ::= { agSystem 55 }

agNewTimeZone   OBJECT-TYPE
    SYNTAX  INTEGER  {
    none(0),
    africa-Algeria(1),
    africa-Angola(2),
    africa-Benin(3),
    africa-Botswana(4),
    africa-Burkina-Faso(5),
    africa-Burundi(6),
    africa-Cameroon(7),
    africa-Central-African-Rep(8),
    africa-Chad(9),
    africa-Congo-WestDemRepCongo(10),
    africa-Congo-EastDemRepCongo(11),
    africa-Congo-Rep(12),
    africa-Cote-dIvoire(13),
    africa-Djibouti(14),
    africa-Egypt(15),
    africa-Equatorial-Guinea(16),
    africa-Eritrea(17),
    africa-Ethiopia(18),
    africa-Gabon(19),
    africa-Gambia(20),
    africa-Ghana(21),
    africa-Guinea(22),
    africa-Guinea-Bissau(23),
    africa-Kenya(24),
    africa-Lesotho(25),
    africa-Liberia(26),
    africa-Libya(27),
    africa-Malawi(28),
    africa-Mali-SouthWestMali(29),
    africa-Mali-NorthEastMali(30),
    africa-Mauritania(31),
    africa-Morocco(32),
    africa-Mozambique(33),
    africa-Namibia(34),
    africa-Niger(35),
    africa-Nigeria(36),
    africa-Rwanda(37),
    africa-SaoTome-And-Principe(38),
    africa-Senegal(39),
    africa-SierraLeone(40),
    africa-Somalia(41),
    africa-SouthAfrica(42),
    africa-Spain-Mainland(43),
    africa-Spain-CeutaMelilla(44),
    africa-Spain-CanaryIslands(45),
    africa-Sudan(46),
    africa-Swaziland(47),
    africa-Tanzania(48),
    africa-Togo(49),
    africa-Tunisia(50),
    africa-Uganda(51),
    africa-Western-Sahara(52),
    africa-Zambia(53),
    africa-Zimbabwe(54),
    americas-Anguilla(55),
    americas-Antigua-Barbuda(56),
    americas-Argentina-EArgentina(57),
    americas-Argentina-MostLocations(58),
    americas-Argentina-Jujuy(59),
    americas-Argentina-Catamarca(60),
    americas-Argentina-Mendoza(61),
    americas-Aruba(62),
    americas-Bahamas(63),
    americas-Barbados(64),
    americas-Belize(65),
    americas-Bolivia(66),
    americas-Brazil-AtlanticIslands(67),
    americas-Brazil-AmapaEPara(68),
    americas-Brazil-NEBrazil(69),
    americas-Brazil-Pernambuco(70),
    americas-Brazil-Tocantins(71),
    americas-Brazil-AlagoasSergipe(72),
    americas-Brazil-SSEBrazil(73),
    americas-Brazil-MatoGrossoDoSul(74),
    americas-Brazil-WParaRondonia(75),
    americas-Brazil-Roraima(76),
    americas-Brazil-EAmazonas(77),
    americas-Brazil-WAmazonas(78),
    americas-Brazil-Acre(79),
    americas-Canada-NewfoundlandIsland(80),
    americas-Canada-AtlanTime-NovaScotia(81),
    americas-Canada-AtlanTime-ELabrador(82),
    americas-Canada-EastTime-OntarioMostlocation(83),
    americas-Canada-EastTime-ThunderBay(84),
    americas-Canada-EastStdTime-PangnirtungNunavut(85),
    americas-Canada-EastStdTime-EastNunavut(86),
    americas-Canada-EastStdTime-CenNunavut(87),
    americas-Canada-CenTime-ManitobaWestOntario(88),
    americas-Canada-CenTime-RainyRiver(89),
    americas-Canada-CenTime-WestNunavut(90),
    americas-Canada-CenStdTime-SaskatchewanMostlocation(91),
    americas-Canada-CenStdTime-SaskatchewanMidwest(92),
    americas-Canada-MountTime-AlbertaEastBritishColumbia(93),
    americas-Canada-MountTime-CentralNorthwestTerritories(94),
    americas-Canada-MountTime-WestNorthwestTerritories(95),
    americas-Canada-MountStdTime-DawsonCrkStJohnBritColumbia(96),
    americas-Canada-PacificTime-WestBritishColumbia(97),
    americas-Canada-PacificTime-SouthYukon(98),
    americas-Canada-PacificTime-NorthYukon(99),
    americas-CaymanIslands(100),
    americas-Chile-MostLocation(101),
    americas-Chile-EasterIsland(102),
    americas-Colombia(103),
    americas-CostaRica(104),
    americas-Cuba(105),
    americas-Dominica(106),
    americas-DominicanRepublic (107),
    americas-Ecuador(108),
    americas-ElSalvado(109),
    americas-FrenchGuiana(110),
    americas-Greenland-MostLocation(111),
    americas-Greenland-EastCoastNorthScoresbysund(112),
    americas-Greenland-ScoresbysundIttoqqortoormiit(113),
    americas-Greenland-ThulePituffik(114),
    americas-Grenada(115),
    americas-Guadeloupe(116),
    americas-Guatemala(117),
    americas-Guyana(118),
    americas-Haiti(119),
    americas-Honduras(120),
    americas-Jamaica(121),
    americas-Martinique(122),
    americas-Mexico-CentTime-Mostlocations(123),
    americas-Mexico-CentTime-QuintanaRoo(124),
    americas-Mexico-CentTime-CampecheYucatan(125),
    americas-Mexico-CentTime-CoahuilaDurNuevoLeonTam(126),
    americas-Mexico-MountTime-SBajaNayaritSinaloa(127),
    americas-Mexico-MountTime-Chihuahua(128),
    americas-Mexico-MountStdTime-Sonora(129),
    americas-Mexico-PacificTime(130),
    americas-Montserrat(131),
    americas-NetherlandsAntilles(132),
    americas-Nicaragua(133),
    americas-Panama(134),
    americas-Paraguay(135),
    americas-Peru(136),
    americas-PuertoRico(137),
    americas-StKittsAndNevis(138),
    americas-StLucia(139),
    americas-StPierreAndMiquelon(140),
    americas-StVincent(141),
    americas-Suriname(142),
    americas-TrinidadAndTobago(143),
    americas-TurksAndCaicosIs(144),
    americas-USA-EastTime(145),
    americas-USA-EastTime-MichiganMostLocation(146),
    americas-USA-EastTime-KentuckyLouisvilleArea(147),
    americas-USA-EastTime-KentuckyWayneCounty(148),
    americas-USA-EastStdTime-IndianaMostLocations(149),
    americas-USA-EastStdTime-IndianaCrawfordCounty(150),
    americas-USA-EastStdTime-IndianaStarkeCounty(151),
    americas-USA-EastStdTime-IndianaSwitzerlandCounty(152),
    americas-USA-CentTime(153),
    americas-USA-CentTime-MichiganWisconsinborder(154),
    americas-USA-CentTime-NorthDakotaOliverCounty(155),
    americas-USA-MountTime(156),
    americas-USA-MountTime-SouthIdahoAndEastOregon(157),
    americas-USA-MountTime-Navajo(158),
    americas-USA-MountStdTime-Arizona(159),
    americas-USA-PacificTime(160),
    americas-USA-AlaskaTime(161),
    americas-USA-AlaskaTime-AlaskaPanhandle(162),
    americas-USA-AlaskaTime-AlaskaPanhandleNeck(163),
    americas-USA-AlaskaTime-WestAlaska(164),
    americas-USA-AleutianIslands(165),
    americas-USA-Hawaii(166),
    americas-Uruguay(167),
    americas-Venezuela(168),
    americas-VirginIslands-UK(169),
    americas-VirginIslands-US(170),
    antarctica-McMurdoStationRossIsland(171),
    antarctica-Amundsen-ScottStationSouthPole(172),
    antarctica-PalmerStationAnversIsland(173),
    antarctica-MawsonStationHolmeBay(174),
    antarctica-DavisStationVestfoldHills(175),
    antarctica-CaseyStationBaileyPeninsula(176),
    antarctica-VostokStationSMagneticPole(177),
    antarctica-Dumont-dUrvilleBaseTerreAdelie(178),
    antarctica-SyowaStationEOngulI(179),
    arcticOcean-Svalbard(180),
    arcticOcean-JanMayen(181),
    asia-Afghanistan(182),
    asia-Armenia(183),
    asia-Azerbaijan(184),
    asia-Bahrain(185),
    asia-Bangladesh(186),
    asia-Bhutan(187),
    asia-Brunei(188),
    asia-Cambodia(189),
    asia-China-EastChinaBeijingGuangdongShanghai(190),
    asia-China-Heilongjiang(191),
    asia-China-CentralChinaGansuGuizhouSichuanYunnan(192),
    asia-China-TibetmostofXinjiangUyghur(193),
    asia-China-SouthwestXinjiangUyghur(194),
    asia-Cyprus(195),
    asia-EastTimor(196),
    asia-Georgia(197),
    asia-HongKong(198),
    asia-India(199),
    asia-Indonesia-JavaAndSumatra(200),
    asia-Indonesia-WestCentralBorneo(201),
    asia-Indonesia-ESBorneoCelebesBaliNusaTengaWTimor(202),
    asia-Indonesia-IrianJayaAndMoluccas(203),
    asia-Iran(204),
    asia-Iraq(205),
    asia-Israel(206),
    asia-Japan(207),
    asia-Jordan(208),
    asia-Kazakhstan-MostLocations(209),
    asia-Kazakhstan-QyzylordaKyzylorda(210),
    asia-Kazakhstan-Aqtobe(211),
    asia-Kazakhstan-AtyrauMangghystau(212),
    asia-Kazakhstan-WestKazakhstan(213),
    asia-Korea-North(214),
    asia-Korea-South(215),
    asia-Kuwait(216),
    asia-Kyrgyzstan(217),
    asia-Laos(218),
    asia-Lebanon(219),
    asia-Macau(220),
    asia-Malaysia-PeninsularMalaysia(221),
    asia-Malaysia-SabahSarawak(222),
    asia-Mongolia-MostLocations(223),
    asia-Mongolia-BayanOlgiyGoviAltaiHovdUvsZavkhan(224),
    asia-Mongolia-DornodSukhbaatar(225),
    asia-Myanmar(226),
    asia-Nepal(227),
    asia-Oman(228),
    asia-Pakistan(229),
    asia-Palestine(230),
    asia-Philippines(231),
    asia-Qatar(232),
    asia-Russia-Moscow-01Kaliningrad(233),
    asia-Russia-Moscow00WestRussia(234),
    asia-Russia-Moscow01CaspianSea(235),
    asia-Russia-Moscow02Urals(236),
    asia-Russia-Moscow03WestSiberia(237),
    asia-Russia-Moscow03Novosibirsk(238),
    asia-Russia-Moscow04YeniseiRiver(239),
    asia-Russia-Moscow05LakeBaikal(240),
    asia-Russia-Moscow06LenaRiver(241),
    asia-Russia-Moscow07AmurRiver(242),
    asia-Russia-Moscow07SakhalinIsland(243),
    asia-Russia-Moscow08Magadan(244),
    asia-Russia-Moscow09Kamchatka(245),
    asia-Russia-Moscow10BeringSea(246),
    asia-SaudiArabia(247),
    asia-Singapore(248),
    asia-SriLanka(249),
    asia-Syria(250),
    asia-Taiwan(251),
    asia-Tajikistan(252),
    asia-Thailand(253),
    asia-Turkmenistan(254),
    asia-UnitedArabEmirates(255),
    asia-Uzbekistan-WestUzbekistan(256),
    asia-Uzbekistan-EastUzbekistan(257),
    asia-Vietnam(258),
    asia-Yemen(259),
    atlanticOcean-Bermuda(260),
    atlanticOcean-CapeVerde(261),
    atlanticOcean-FaeroeIslands(262),
    atlanticOcean-FalklandIslands(263),
    atlanticOcean-Iceland(264),
    atlanticOcean-Portugal-Mainland(265),
    atlanticOcean-Portugal-MadeiraIslands(266),
    atlanticOcean-Portugal-Azores(267),
    atlanticOcean-SouthGeorgia-SouthSandwichIslands(268),
    atlanticOcean-Spain-Mainland(269),
    atlanticOcean-Spain-CeutaMelilla(270),
    atlanticOcean-Spain-CanaryIslands(271),
    atlanticOcean-StHelena(272),
    atlanticOcean-Svalbard-JanMayen(273),
    australia-LordHoweIsland(274),
    australia-Tasmania(275),
    australia-Victoria(276),
    australia-NewSouthWales-MostLocations(277),
    australia-NewSouthWales-Yancowinna(278),
    australia-Queensland-MostLocations(279),
    australia-Queensland-HolidayIslands(280),
    australia-SouthAustralia(281),
    australia-NorthernTerritory(282),
    australia-WesternAustralia(283),
    europe-Albania(284),
    europe-Andorra(285),
    europe-Austria(286),
    europe-Belarus(287),
    europe-Belgium(288),
    europe-BosniaHerzegovina(289),
    europe-Britain-UKGreatBritain(290),
    europe-Britain-UKNorthernIreland(291),
    europe-Bulgaria(292),
    europe-Croatia(293),
    europe-CzechRepublic(294),
    europe-Denmark(295),
    europe-Estonia(296),
    europe-Finland(297),
    europe-France(298),
    europe-Germany(299),
    europe-Gibraltar(300),
    europe-Greece(301),
    europe-Hungary(302),
    europe-Ireland(303),
    europe-Italy(304),
    europe-Latvia(305),
    europe-Liechtenstein(306),
    europe-Lithuania(307),
    europe-Luxembourg(308),
    europe-Macedonia(309),
    europe-Malta(310),
    europe-Moldova(311),
    europe-Monaco(312),
    europe-Montenegro(421),
    europe-Netherlands(313),
    europe-Norway(314),
    europe-Poland(315),
    europe-Portugal-Mainland(316),
    europe-Portugal-MadeiraIslands(317),
    europe-Portugal-Azores(318),
    europe-Romania(319),
    europe-Russia-Moscow-01Kaliningrad(320),
    europe-Russia-Moscow00WestRussia(321),
    europe-Russia-Moscow01CaspianSea(322),
    europe-Russia-Moscow02Urals(323),
    europe-Russia-Moscow03WestSiberia(324),
    europe-Russia-Moscow03Novosibirsk(325),
    europe-Russia-Moscow04YeniseiRiver(326),
    europe-Russia-Moscow05LakeBaikal(327),
    europe-Russia-Moscow06LenaRiver(328),
    europe-Russia-Moscow07AmurRiver(329),
    europe-Russia-Moscow07SakhalinIsland(330),
    europe-Russia-Moscow08Magadan(331),
    europe-Russia-Moscow09Kamchatka(332),
    europe-Russia-Moscow10BeringSea(333),
    europe-SanMarino(334),
    europe-Serbia(348),
    europe-Slovakia(335),
    europe-Slovenia(336),
    europe-Spain-Mainland(337),
    europe-Spain-CeutaAndMelilla(338),
    europe-Spain-CanaryIslands(339),
    europe-Sweden(340),
    europe-Switzerland(341),
    europe-Turkey(342),
    europe-Ukraine-MostLocations(343),
    europe-Ukraine-Ruthenia(344),
    europe-Ukraine-Zaporozhye-ELugansk(345),
    europe-Ukraine-CentralCrimea(346),
    europe-VaticanCity(347),
    indianOcean-BritishIndianOceanTerritory(349),
    indianOcean-ChristmasIsland(350),
    indianOcean-CocosOrKeelingIslands(351),
    indianOcean-Comoros(352),
    indianOcean-FrenchSouthernAndAntarcticLands(353),
    indianOcean-Madagascar(354),
    indianOcean-Maldives(355),
    indianOcean-Mauritius(356),
    indianOcean-Mayotte(357),
    indianOcean-Reunion(358),
    indianOcean-Seychelles(359),
    pacificOcean-Chile-MostLocations(360),
    pacificOcean-Chile-EasterIslandSalayGomez(361),
    pacificOcean-CookIslands(362),
    pacificOcean-Ecuador(363),
    pacificOcean-Fiji(364),
    pacificOcean-FrenchPolynesia-SocietyIslands(365),
    pacificOcean-FrenchPolynesia-MarquesasIslands(366),
    pacificOcean-FrenchPolynesia-GambierIslands(367),
    pacificOcean-Guam(368),
    pacificOcean-Kiribati-GilbertIslands(369),
    pacificOcean-Kiribati-PhoenixIslands(370),
    pacificOcean-Kiribati-LineIslands(371),
    pacificOcean-MarshallIslands-MostLocations(372),
    pacificOcean-MarshallIslands-Kwajalein(373),
    pacificOcean-Micronesia-Yap(374),
    pacificOcean-Micronesia-TrukOrChuuk(375),
    pacificOcean-Micronesia-PonapeOrPohnpei(376),
    pacificOcean-Micronesia-Kosrae(377),
    pacificOcean-Nauru(378),
    pacificOcean-NewCaledonia(379),
    pacificOcean-NewZealand-MostLocations(380),
    pacificOcean-NewZealand-ChathamIslands(381),
    pacificOcean-Niue(382),
    pacificOcean-NorfolkIsland(383),
    pacificOcean-NorthernMarianaIslands(384),
    pacificOcean-Palau(385),
    pacificOcean-PapuaNewGuinea(386),
    pacificOcean-Pitcairn(387),
    pacificOcean-SamoaAmerican(388),
    pacificOcean-SamoaWestern(389),
    pacificOcean-SolomonIslands(390),
    pacificOcean-Tokelau(391),
    pacificOcean-Tonga(392),
    pacificOcean-Tuvalu(393),
    pacificOceanUSA-EastTime(394),
    pacificOceanUSA-EastTime-MichiganMostLocations(395),
    pacificOceanUSA-EastTime-KentuckyLouisvilleArea(396),
    pacificOceanUSA-EastTime-KentuckyWayneCounty(397),
    pacificOceanUSA-EastStdTime-IndianaMostLocations(398),
    pacificOceanUSA-EastStdTime-IndianaCrawfordCounty(399),
    pacificOceanUSA-EastStdTime-IndianaStarkeCounty(400),
    pacificOceanUSA-EastStdTime-IndianaSwitzerlandCounty(401),
    pacificOceanUSA-CentTime(402),
    pacificOceanUSA-CentTime-MichiganWisconsinborder(403),
    pacificOceanUSA-CentTime-NorthDakotaOliverCounty(404),
    pacificOceanUSA-MountTime(405),
    pacificOceanUSA-MountTime-SouthIdahoAndEastOregon(406),
    pacificOceanUSA-MountTime-Navajo(407),
    pacificOceanUSA-MountStdTime-Arizona(408),
    pacificOceanUSA-PacificTime(409),
    pacificOceanUSA-AlaskaTime(410),
    pacificOceanUSA-AlaskaTime-AlaskaPanhandle(411),
    pacificOceanUSA-AlaskaTime-AlaskaPanhandleNeck(412),
    pacificOceanUSA-AlaskaTime-WestAlaska(413),
    pacificOceanUSA-AleutianIslands(414),
    pacificOceanUSA-Hawaii(415),
    pacificOcean-USMinorOutlyingIslands-JohnstonAtoll(416),
    pacificOcean-USMinorOutlyingIslands-MidwayIslands(417),
    pacificOcean-USMinorOutlyingIslands-WakeIsland(418),
    pacificOcean-Vanuatu(419),
    pacificOceanWallisAndFutuna(420)
	}
    MAX-ACCESS read-write
    STATUS  current
    DESCRIPTION
        "The time zone.
         Note: Locations are alphabetically ordered and
         the corresponding code is not reflected in CLI."
    ::= { agSystem 56 }


agCurCfgIdleCLITimeout OBJECT-TYPE
    SYNTAX  Integer32
    MAX-ACCESS  read-only
    STATUS  current
    DESCRIPTION
        "Set idle CLI sessions timeout."
    ::= { agSystem 57 }

agNewCfgIdleCLITimeout OBJECT-TYPE
    SYNTAX  Integer32
    MAX-ACCESS  read-write
    STATUS  current
    DESCRIPTION
        "Set idle CLI sessions timeout."
    ::= { agSystem 58 }



-- Auto-Discovery topology table info

agCurCfgHttpsServerAccess OBJECT-TYPE
    SYNTAX  INTEGER {
        enabled(1),
        disabled(0)
        }
    MAX-ACCESS  read-only
    STATUS  current
    DESCRIPTION
        "Current HTTPS server access state."
    ::= { agSystem 62 }

agNewCfgHttpsServerAccess OBJECT-TYPE
    SYNTAX  INTEGER {
        enabled(1),
        disabled(0)
        }
    MAX-ACCESS  read-write
    STATUS  current
    DESCRIPTION
        "Enable/disable HTTPS server access."
    ::= { agSystem 63 }


agCurHttpAcces OBJECT-TYPE
   SYNTAX  INTEGER {
        enable(1),
        disable(2)
        }
    MAX-ACCESS  read-only
    STATUS  current
    DESCRIPTION
        "Current HTTP server access state."
    ::= { agSystem 66 }

agNewHttpAcces OBJECT-TYPE
   SYNTAX  INTEGER {
        enable(1),
        disable(2)
        }
    MAX-ACCESS read-write
    STATUS  current
    DESCRIPTION
        "New HTTP server access state."
    ::= { agSystem 67 }


agCurCfgDhcp OBJECT-TYPE
    SYNTAX  INTEGER {
        enabled(1),
        disabled(2)
        }
    MAX-ACCESS  read-only
    STATUS  current
    DESCRIPTION
        "Enable or disable the use of DHCP, as currently configured in the
         current configuration block."
    ::= { agSystem 68 }

agNewCfgDhcp OBJECT-TYPE
    SYNTAX  INTEGER {
        enabled(1),
        disabled(2)
        }
    MAX-ACCESS  read-write
    STATUS  current
    DESCRIPTION
        "Enable or disable the use of DHCP, in the new configuration block."
    ::= { agSystem 69 }


agCurCfgHprompt OBJECT-TYPE
    SYNTAX  INTEGER {
        enable(1),
        disable(2)
        }
    MAX-ACCESS  read-only
    STATUS  current
    DESCRIPTION
        "Current status of hprompt."
    ::= { agSystem 72 }

agNewCfgHprompt OBJECT-TYPE
    SYNTAX  INTEGER {
        enable(1),
        disable(2)
        }
    MAX-ACCESS  read-write
    STATUS  current
    DESCRIPTION
        "New status of hprompt."
    ::= { agSystem 73 }

agCurCfgUserBBI OBJECT-TYPE
    SYNTAX  INTEGER {
        enable(1),
        disable(2)
        }
    MAX-ACCESS  read-only
    STATUS  current
    DESCRIPTION
        "Current status of user configuration from BBI."
    ::= { agSystem 74 }

agNewCfgUserBBI OBJECT-TYPE
    SYNTAX  INTEGER {
        enable(1),
        disable(2)
        }
    MAX-ACCESS  read-write
    STATUS  current
    DESCRIPTION
        "New status of user configuration from BBI."
    ::= { agSystem 75 }





agCurCfgSysCustomDstState OBJECT-TYPE
    SYNTAX  INTEGER {
        enabled(1),
        disabled(2)
        }
    MAX-ACCESS  read-only
    STATUS  current
    DESCRIPTION
        "The current status of Custom DST"
    ::= { agSystem 98 }
agNewCfgSysCustomDstState OBJECT-TYPE
    SYNTAX  INTEGER {
        enabled(1),
        disabled(2)
        }
    MAX-ACCESS  read-write
    STATUS  current
    DESCRIPTION
        "Enable/disable Custom DST"
    ::= { agSystem 99 }
agCurCfgSysCustomDstStart OBJECT-TYPE
    SYNTAX  DisplayString (SIZE(0..8))
    MAX-ACCESS  read-only
    STATUS  current
    DESCRIPTION
        " The current Custom DST start rule"
    ::= { agSystem 100 }
agNewCfgSysCustomDstStart OBJECT-TYPE
    SYNTAX  DisplayString (SIZE(0..8))
    MAX-ACCESS  read-write
    STATUS  current
    DESCRIPTION
        "Set Custom DST start rule"
    ::= { agSystem 101 }
agCurCfgSysCustomDstEnd OBJECT-TYPE
    SYNTAX  DisplayString (SIZE(0..8))
    MAX-ACCESS  read-only
    STATUS  current
    DESCRIPTION
        "The current Custom DST end rule"
    ::= { agSystem 102}
agNewCfgSysCustomDstEnd OBJECT-TYPE
    SYNTAX  DisplayString (SIZE(0..8))
    MAX-ACCESS  read-write
    STATUS  current
    DESCRIPTION
        "Set Custom DST end rule"
    ::= { agSystem 103 }

agHavePanicDump OBJECT-TYPE
    SYNTAX  INTEGER {
        havePanic(1),
        noHavePanic(2)
        }
    MAX-ACCESS  read-only
    STATUS  current
    DESCRIPTION
        "The presence of a panic dump in the flash memory."
    ::= { agSystem 104 }


agCurCfgResetControl OBJECT-TYPE
    SYNTAX  INTEGER {
        enable(1),
        disable(2)
        }
    MAX-ACCESS  read-only
    STATUS  current
    DESCRIPTION
        "Current reset control state."
    ::= { agSystem 111 }

agNewCfgResetControl OBJECT-TYPE
    SYNTAX  INTEGER {
        enable(1),
        disable(2)
        }
    MAX-ACCESS  read-write
    STATUS  current
    DESCRIPTION
        "Enable/disable reset control after panic."
    ::= { agSystem 112 }

agCurCfgSysDlight OBJECT-TYPE
    SYNTAX  INTEGER {
        enabled(1),
        disabled(2)
        }
    MAX-ACCESS  read-only
    STATUS  current
    DESCRIPTION
        "Current daylight savings time status."
    ::= { agSystem 113 }

agNewCfgSysDlight OBJECT-TYPE
    SYNTAX  INTEGER {
        enabled(1),
        disabled(2)
        }
    MAX-ACCESS  read-write
    STATUS  current
    DESCRIPTION
        "Enable/disable daylight savings time."
    ::= { agSystem 114 }

agCurCfgErrDisableRecovery OBJECT-TYPE
    SYNTAX      INTEGER {
                    enable(1),
                    disable(2)
                }
    MAX-ACCESS  read-only
    STATUS      current
    DESCRIPTION
        "This object indicates whether the system will automatically
         re-enable an error-disabled port after the time interval
         indicated by agCurCfgErrDisableTimeout has elapsed. A port
         is in error-disabled state when it has been operationally
         disabled due to abnormal conditions detected on the port.

         An error-disabled port will only be automatically re-enabled
         by the system if and only if this object and the port's
         agPortCurCfgErrDisableRecovery object both have a value of
         'enable(1)'."
    DEFVAL      { disable }
    ::= { agSystem 115 }

agNewCfgErrDisableRecovery OBJECT-TYPE
    SYNTAX      INTEGER {
                    enable(1),
                    disable(2)
                }
    MAX-ACCESS  read-write
    STATUS      current
    DESCRIPTION
        "This object specifies whether the system should automatically
         re-enable an error-disabled port.  Use this object to change
         the global setting of the error-disable recovery action."
    DEFVAL      { disable }
    ::= { agSystem 116 }

agCurCfgErrDisableTimeout OBJECT-TYPE
    SYNTAX      INTEGER (30 .. 86400)
    UNITS       "seconds"
    MAX-ACCESS  read-only
    STATUS      current
    DESCRIPTION
        "This object indicates the time, in seconds, that the system
         will wait before it automatically re-enables any port that
         is in error-disabled state."
    DEFVAL      { 300 }
    ::= { agSystem 117 }

agNewCfgErrDisableTimeout OBJECT-TYPE
    SYNTAX      INTEGER (30 .. 86400)
    UNITS       "seconds"
    MAX-ACCESS  read-write
    STATUS      current
    DESCRIPTION
        "This object specifies the time, in seconds, that the system
         should wait before it automatically re-enables a port that
         is in error-disabled state.  Use this object to change the
         global error-disable timeout value."
    DEFVAL      { 300 }
    ::= { agSystem 118 }

agCurCfgTelnetAccess OBJECT-TYPE
    SYNTAX  INTEGER {
        enabled(1),
        disabled(0)
        }
    MAX-ACCESS  read-only
    STATUS  current
    DESCRIPTION
        "Current telnet access state."
    ::= { agSystem 119 }

agNewCfgTelnetAccess OBJECT-TYPE
    SYNTAX  INTEGER {
        enabled(1),
        disabled(0)
        }
    MAX-ACCESS  read-write
    STATUS  current
    DESCRIPTION
        "Enable/disable telnet access."
    ::= { agSystem 120 }

agCurCfgDcbx OBJECT-TYPE
    SYNTAX  INTEGER {
        enabled(1),
        disabled(0)
        }
    MAX-ACCESS  read-only
    STATUS  current
    DESCRIPTION
        "Current DCBX state."
    ::= { agSystem 121 }

agNewCfgDcbx OBJECT-TYPE
    SYNTAX  INTEGER {
        enabled(1),
        disabled(0)
        }
    MAX-ACCESS  read-write
    STATUS  current
    DESCRIPTION
        "Enable/disable DCBX feature."
    ::= { agSystem 122 }


serverPortsCurCfgPorts OBJECT-TYPE
    SYNTAX  OCTET STRING
    MAX-ACCESS  read-only
    STATUS  current
    DESCRIPTION
        "The current configured server port list. The ports are presented in bitmap format.
         in receiving order:

             OCTET 1  OCTET 2  .....
             xxxxxxxx xxxxxxxx .....
             ||    || |_ port 8
             ||    ||
             ||    ||___ port 7
             ||    |____ port 6
             ||      .    .   .
             ||_________ port 1
             |__________ reserved

         where x : 1 - The represented port belongs to the server ports list
                   0 - The represented port does not belong to the server ports list"
    ::= { agSystem 127 }

serverPortsNewCfgPorts OBJECT-TYPE
    SYNTAX  OCTET STRING
    MAX-ACCESS  read-only
    STATUS  current
    DESCRIPTION
        "New configuration server port list. The ports are presented in bitmap format.
         in receiving order:

             OCTET 1  OCTET 2  .....
             xxxxxxxx xxxxxxxx .....
             ||    || |_ port 8
             ||    ||
             ||    ||___ port 7
             ||    |____ port 6
             ||      .    .   .
             ||_________ port 1
             |__________ reserved

         where x : 1 - The represented port belongs to the server ports list
                   0 - The represented port does not belong to the server ports list"
    ::= { agSystem 128 }

serverPortsNewCfgAddPort OBJECT-TYPE
    SYNTAX  PortNumber
    MAX-ACCESS  read-create
    STATUS  current
    DESCRIPTION
        "The port to be added to the server ports list.  A '0' value is
         returned when read."
    ::= {agSystem 129 }

serverPortsNewCfgRemovePort OBJECT-TYPE
    SYNTAX  PortNumber
    MAX-ACCESS  read-create
    STATUS  current
    DESCRIPTION
        "The port to be removed from the server ports list.  A '0' value is
         returned when read."
    ::= { agSystem 130 }

agCurBootProfile OBJECT-TYPE
    SYNTAX  INTEGER {
        default(0)
        ,acl(7)
        ,ipmc-opt-acl-none(8)
        ,ipmc-opt-acl-128(9)
        ,ipmc-opt-acl-256(10)
        ,ipmc-opt-acl-384(11)
        }
    MAX-ACCESS  read-only
    STATUS  current
    DESCRIPTION
        "Profile that will be used by the switch after reset"
    ::= { agSystem 131 }

agNewBootProfile OBJECT-TYPE
    SYNTAX  INTEGER {
        default(0)
        ,acl(7)
        ,ipmc-opt-acl-none(8)
        ,ipmc-opt-acl-128(9)
        ,ipmc-opt-acl-256(10)
        ,ipmc-opt-acl-384(11)
        }
    MAX-ACCESS  read-write
    STATUS  current
    DESCRIPTION
        "Configure the profile that will be used by the switch after reset"
    ::= { agSystem 132 }

agNetboot OBJECT-TYPE
    SYNTAX  INTEGER {
        enabled(1),
        disabled(2)
        }
    MAX-ACCESS  read-write
    STATUS  current
    DESCRIPTION
        "Ena/dis loading of config over n/w during bootup"
    ::= { agSystem 133 }

agNetbootTftpAddr OBJECT-TYPE
    SYNTAX IpAddress
    MAX-ACCESS read-write
    STATUS current
    DESCRIPTION
        "Tftp server address from where config file needs to be downloaded"
    ::= { agSystem 134 }

agNetbootCfgFile OBJECT-TYPE
    SYNTAX  DisplayString (SIZE(0..31))
    MAX-ACCESS read-write
    STATUS current
    DESCRIPTION
        "Config file location on tftp server"
    ::= { agSystem 135 }

agCurCfgLinkscanMode OBJECT-TYPE
    SYNTAX  INTEGER {
        normal(1),
        fast(2),
        slow(3)
        }
    MAX-ACCESS  read-only
    STATUS  current
    DESCRIPTION
        "Set linkscan mode"
    ::= { agSystem 136 }

agNewCfgLinkscanMode OBJECT-TYPE
    SYNTAX  INTEGER {
        normal(1),
        fast(2),
        slow(3)
        }
    MAX-ACCESS  read-write
    STATUS  current
    DESCRIPTION
        "Set linkscan mode"
    ::= { agSystem 137 }

agUSBboot OBJECT-TYPE
    SYNTAX  INTEGER {
        enabled(1),
        disabled(2)
        }
    MAX-ACCESS  read-write
    STATUS  current
    DESCRIPTION
        "Ena/dis USB Boot capability"
    ::= { agSystem 138 }

agCurServiceLED OBJECT-TYPE
    SYNTAX  INTEGER {
        enabled(1),
        disabled(0)
        }
    MAX-ACCESS  read-only
    STATUS  current
    DESCRIPTION
        "Ena/dis Service Required LED"
    ::= { agSystem 139 }

agNewServiceLED OBJECT-TYPE
    SYNTAX  INTEGER {
        enabled(1),
        disabled(0)
        }
    MAX-ACCESS  read-write
    STATUS  current
    DESCRIPTION
        "Ena/dis Service Required LED "
    ::= { agSystem 140 }

agUSBeject OBJECT-TYPE
    SYNTAX  INTEGER {
        eject(1),
        usbready(2),
        nousb(3)
        }
    MAX-ACCESS  read-write
    STATUS  current
    DESCRIPTION
        "Eject USB - eject(1)
         Get current USB state:
            usbready(2) - USB mounted
            nousb(3)    - no USB mounted"
    ::= { agSystem 141 }

agCurRFC4741NetconfAccess OBJECT-TYPE
   SYNTAX  INTEGER {
        enable(1),
        disable(2)
        }
    MAX-ACCESS  read-only
    STATUS  current
    DESCRIPTION
        "Current NETCONF server access state."
    ::= { agSystem 142 }

agNewRFC4741NetconfAccess  OBJECT-TYPE
   SYNTAX  INTEGER {
        enable(1),
        disable(2)
        }
    MAX-ACCESS read-write
    STATUS  current
    DESCRIPTION
        "Enable/disable NETCONF server access state."
    ::= { agSystem 143 }

agCurRFC4741NetconfSessionTimeout OBJECT-TYPE
    SYNTAX  INTEGER (60..3600)
    MAX-ACCESS  read-only
    STATUS  current
    DESCRIPTION
        "Once NETCONF session setup, NETCONF server will allocate resource
        for this session.
        agCurRFC4741NetconfSessionTimeout indicates the number of seconds before
        the resources are freed if there is no operation on this session"
    ::= { agSystem 144 }

agNewRFC4741NetconfSessionTimeout OBJECT-TYPE
    SYNTAX  INTEGER (60..3600)
    MAX-ACCESS  read-write
    STATUS  current
    DESCRIPTION
        "Once NETCONF session setup, NETCONF server will allocate resource
        for this session.
        agNewRFC4741NetconfSessionTimeout specifies the number of seconds before
        the resources are freed if there is no operation on this session"
    ::= { agSystem 145 }

agCurRFC4741NetconfSshAccess OBJECT-TYPE
   SYNTAX  INTEGER {
        enable(1),
        disable(2)
        }
    MAX-ACCESS  read-only
    STATUS  current
    DESCRIPTION
        "Current NETCONF server over SSH access state."
    ::= { agSystem 146 }

agNewRFC4741NetconfSshAccess OBJECT-TYPE
   SYNTAX  INTEGER {
        enable(1),
        disable(2)
        }
    MAX-ACCESS read-write
    STATUS  current
    DESCRIPTION
        "Enable/disable NETCONF server over SSH access state."
    ::= { agSystem 147 }

agCurRFC4741NetconfSshPort OBJECT-TYPE
    SYNTAX  INTEGER (1..65535)
    MAX-ACCESS  read-only
    STATUS  current
    DESCRIPTION
        "The TCP port number that the NETCONF server over SSH is listening to
         in the current configuration block."
    ::= { agSystem 148 }

agNewRFC4741NetconfSshPort OBJECT-TYPE
    SYNTAX  INTEGER (1..65535)
    MAX-ACCESS  read-write
    STATUS  current
    DESCRIPTION
        "The TCP port number that the NETCONF server over SSH is listening to
         in the new configuration block."
    ::= { agSystem 149}



agCurCfgLFDStatus OBJECT-TYPE
    SYNTAX      INTEGER {
                    enable(1),
                    disable(2)
                }
    MAX-ACCESS  read-only
    STATUS      current
    DESCRIPTION
        "This object indicates whether the system will put any port
         in an error-disabled state due to excessive link flaps.

         A port will be put in an error-disabled state due to 
         excessive link flaps if this object and the port's
         agPortCurCfgLFDStatus object both have a value of 'enable'.
         A port has an excessive number of link flaps if the number
         of link flaps detected during a time period in seconds
         indicated by agCurCfgLFDTime exceeds the maximum number of
         allowed flaps indicated by agCurCfgLFDFlaps."
    DEFVAL      { disable }
    ::= { agSystem 158 }

agNewCfgLFDStatus OBJECT-TYPE
    SYNTAX      INTEGER {
                    enable(1),
                    disable(2)
                }
    MAX-ACCESS  read-write
    STATUS      current
    DESCRIPTION
        "This object indicates whether the system should put any port
         in an error-disabled state due to excessive link flaps.
         Use this object to change the global setting of the Link
         Flap Dampening error-disable action."
    DEFVAL      { disable }
    ::= { agSystem 159 }

agCurCfgLFDFlaps OBJECT-TYPE
    SYNTAX      INTEGER (1 .. 100)
    MAX-ACCESS  read-only
    STATUS      current
    DESCRIPTION
        "This object indicates the maximum number of flaps allowed
         in a time period set by agCurCfgLFDTime."
    DEFVAL      { 5 }
    ::= { agSystem 160 }

agNewCfgLFDFlaps OBJECT-TYPE
    SYNTAX      INTEGER (1 .. 100)
    MAX-ACCESS  read-write
    STATUS      current
    DESCRIPTION
        "This object specifies the maximum number of flaps that should
         be allowed in a time period.  Use this object to change the
         global maximum number of flaps allowed in a time period."
    DEFVAL      { 5 }
    ::= { agSystem 161 }

agCurCfgLFDTime OBJECT-TYPE
    SYNTAX      INTEGER (5 .. 500)
    UNITS       "seconds"
    MAX-ACCESS  read-only
    STATUS      current
    DESCRIPTION
        "This object indicates the length of time period in seconds
         during which link flaps are counted."
    DEFVAL      { 30 }
    ::= { agSystem 162 }

agNewCfgLFDTime OBJECT-TYPE
    SYNTAX      INTEGER (5 .. 500)
    UNITS       "seconds"
    MAX-ACCESS  read-write
    STATUS      current
    DESCRIPTION
        "This object specifies the length of time period in seconds
         that should be used to count link flaps."
    DEFVAL      { 30 }
    ::= { agSystem 163 }


agCurCfgTrapSrcLoopIf OBJECT-TYPE
    SYNTAX  INTEGER
    MAX-ACCESS  read-only
    STATUS  current
    DESCRIPTION
        "The index of the loopback interface that should be used
         for the source IP of the SNMP trap; 0 means that
         no loopback interface is used as the source of the SNMP trap."
    ::= { agSystem 164 }

agNewCfgTrapSrcLoopIf OBJECT-TYPE
    SYNTAX      INTEGER
    MAX-ACCESS  read-write
    STATUS      current
    DESCRIPTION
        "The index of the loopback interface that should be used
         for the source IP of the SNMP trap; 0 means that
         no loopback interface is used as the source of the SNMP trap."
    ::= { agSystem 165 }


agCfgMtm OBJECT-TYPE
    SYNTAX      INTEGER {
                    mtmValue1(1),
                    mtmValue2(2),
                    mtmValue3(3),
                    mtmValue4(4),
                    mtmValue5(5)
		   ,mtmValue6(6)

                }
    MAX-ACCESS  read-write
    STATUS      current
    DESCRIPTION
        "This object specifies the new value for MTM.
         The available MTM values are:
         1455-48T (1)
         7309-CF9 (2)
         7309-CR9 (3)
         7309-HCE (4)
         7309-HCD (5)
	 7120-48T (6)"

    ::= { agSystem 166 }



agNewSecurityMode OBJECT-TYPE
    SYNTAX  INTEGER {
        compatibility(0),
        strict(1),
        strictsnmpolduser(2)
        }
    MAX-ACCESS  read-write
    STATUS  current
    DESCRIPTION
        "This is an action object to change switch security mode. There are thtree
        security modes for IBM switch: strict mode, compatibility mode and strict mode
        with SNMP not comply.

        Strict mode:
        Strict mode will have higher security level. Encryption algorithms in strict
        mode will be compliance with the NIST SP 800-131A. Detailed information please
        refer NIST SP 800-131A mode Functional Specification. SSH will be enabled by
        default in strict mode for all platforms. It's strict(1) in this node.

        Compatibility mode:
        This is the default mode when switch first boot up. MD5/SHA/DES are selected as
        Hash/Encryption algorithms. It's compatibility(2) in this node.

        Strict mode with SNMP not comply:
        To provide backward compatibility option, insecure MD5/DES are supported. It's
        strictsnmpolduser(3) in this node.

        The next time reload security mode is returned when this object ie read."
    ::= { agSystem 177 }

agCurSecurityMode OBJECT-TYPE
    SYNTAX  INTEGER {
        compatibility(0),
        strict(1),
        strictsnmpolduser(2)
        }
    MAX-ACCESS  read-only
    STATUS  current
    DESCRIPTION
        "This is an action object to change switch security mode. There are thtree
        security modes for IBM switch: strict mode, compatibility mode and strict mode
        with SNMP not comply.

        Strict mode:
        Strict mode will have higher security level. Encryption algorithms in strict
        mode will be compliance with the NIST SP 800-131A. Detailed information please
        refer NIST SP 800-131A mode Functional Specification. SSH will be enabled by
        default in strict mode for all platforms. It's strict(1) in this node.

        Compatibility mode:
        This is the default mode when switch first boot up. MD5/SHA/DES are selected as
        Hash/Encryption algorithms. It's compatibility(2) in this node.

        Strict mode with SNMP not comply:
        To provide backward compatibility option, insecure MD5/DES are supported. It's
        strictsnmpolduser(3) in this node.

        The current security mode is returned when this object ie read."
    ::= { agSystem 180 }
agNewCfgSslVersionLevel OBJECT-TYPE
    SYNTAX  INTEGER {
--        sslv3(0),
        tls10(1),
        tls11(2),
        tls12(3)
        }
    MAX-ACCESS  read-write
    STATUS  current
    DESCRIPTION
        "New status of SSL Server Minimum Acceptable Protocol Version."
    ::= { agSystem 178 }


agCurCfgSslVersionLevel OBJECT-TYPE
    SYNTAX  INTEGER {
--        sslv3(0),
        tls10(1),
        tls11(2),
        tls12(3)
        }
    MAX-ACCESS  read-only
    STATUS  current
    DESCRIPTION
        "Current status of SSL Server Minimum Acceptable Protocol Version."
    ::= { agSystem 179 }


agCurCfgTrapHostTable OBJECT-TYPE
    SYNTAX  SEQUENCE OF AgCurCfgTrapHostEntry
    MAX-ACCESS  not-accessible
    STATUS  current
    DESCRIPTION
        "The table of current trap hosts configure."
    ::= { agSystem 184 }   
    
agCurCfgTrapHostEntry OBJECT-TYPE
    SYNTAX  AgCurCfgTrapHostEntry
    MAX-ACCESS  not-accessible
    STATUS  current
    DESCRIPTION
        "A trap host configuration on the switch."
    INDEX   { agCurCfgTrapHostIndex }
    ::= { agCurCfgTrapHostTable 1 }

AgCurCfgTrapHostEntry ::= SEQUENCE {
    agCurCfgTrapHostIndex          Integer32,
    agCurCfgTrapHostAddress        DisplayString ,
    agCurCfgTrapHostCommStr        DisplayString
   }

agCurCfgTrapHostIndex OBJECT-TYPE
    SYNTAX  Integer32
    MAX-ACCESS  read-only
    STATUS  current
    DESCRIPTION
        "The trap host index. Valid range is 1-16"
    ::= { agCurCfgTrapHostEntry 1 }

agCurCfgTrapHostAddress OBJECT-TYPE
    SYNTAX  DisplayString
    MAX-ACCESS  read-only
    STATUS  current
    DESCRIPTION
        "The trap host address."
    ::= { agCurCfgTrapHostEntry 2 }      
    
agCurCfgTrapHostCommStr OBJECT-TYPE
    SYNTAX  DisplayString (SIZE(0..128))
    MAX-ACCESS  read-only
    STATUS  current
    DESCRIPTION
        "The trap host community string."
    ::= { agCurCfgTrapHostEntry 3 } 

agNewCfgTrapHostTable OBJECT-TYPE
    SYNTAX  SEQUENCE OF AgNewCfgTrapHostEntry
    MAX-ACCESS  not-accessible
    STATUS  current
    DESCRIPTION
        "The table for trap host definitions in the new configuration block."
    ::= { agSystem 185 }   
    
agNewCfgTrapHostEntry OBJECT-TYPE
    SYNTAX  AgNewCfgTrapHostEntry
    MAX-ACCESS  not-accessible
    STATUS  current
    DESCRIPTION
        "A row in the trap host definition table"
    INDEX   { agNewCfgTrapHostIndex }
    ::= { agNewCfgTrapHostTable 1 }

AgNewCfgTrapHostEntry ::= SEQUENCE {
    agNewCfgTrapHostIndex          Integer32,
    agNewCfgTrapHostAddress        DisplayString ,
    agNewCfgTrapHostCommStr        DisplayString,
    agNewCfgTrapHostDelete         INTEGER
   }

agNewCfgTrapHostIndex OBJECT-TYPE
    SYNTAX  Integer32
    MAX-ACCESS  read-only
    STATUS  current
    DESCRIPTION
        "The trap host index. Valid range is 1-16"
    ::= { agNewCfgTrapHostEntry 1 }

agNewCfgTrapHostAddress OBJECT-TYPE
    SYNTAX  DisplayString
    MAX-ACCESS  read-create
    STATUS  current
    DESCRIPTION
        "The trap host address in the new configuration block. 
         Setting IPv6 value is not supported in realease 7.9.x."
    ::= { agNewCfgTrapHostEntry 2 }      
    
agNewCfgTrapHostCommStr OBJECT-TYPE
    SYNTAX  DisplayString (SIZE(0..128))
    MAX-ACCESS  read-create
    STATUS  current
    DESCRIPTION
        "The trap host community string in the new configuration block."
    ::= { agNewCfgTrapHostEntry 3 }  
    
agNewCfgTrapHostDelete OBJECT-TYPE
    SYNTAX  INTEGER {
        other(1),
        delete(2)
        }
    MAX-ACCESS  read-create
    STATUS  current
    DESCRIPTION
        "By setting the value to delete(2), the entire row is deleted."
    ::= { agNewCfgTrapHostEntry 4 }

-- if defined(WEB_UI)  removed this as it is wrongfully tied to BBI and did not allowed
--                     agent to compile without web folder (BBI)
-- Syslog Configuration
agCurCfgSyslogHost OBJECT-TYPE
    SYNTAX  DisplayString
    MAX-ACCESS  read-only
    STATUS  current
    DESCRIPTION
        "The syslog host IP address in the current configuration block."
    ::= { agSyslog 1 }

agNewCfgSyslogHost OBJECT-TYPE
    SYNTAX  DisplayString
    MAX-ACCESS  read-write
    STATUS  current
    DESCRIPTION
        "The syslog host IP address in the new configuration block."
    ::= { agSyslog 2 }

agCurCfgSyslog2Host OBJECT-TYPE
    SYNTAX  DisplayString
    MAX-ACCESS  read-only
    STATUS  current
    DESCRIPTION
        "The second syslog host IP address in the current configuration block."
    ::= { agSyslog 3 }

agNewCfgSyslog2Host OBJECT-TYPE
    SYNTAX  DisplayString
    MAX-ACCESS  read-write
    STATUS  current
    DESCRIPTION
        "The second syslog host IP address in the new configuration block."
    ::= { agSyslog 4 }

agCurCfgSyslogFac   OBJECT-TYPE
    SYNTAX  INTEGER  {
	local0(1),
	local1(2),
	local2(3),
	local3(4),
	local4(5),
	local5(6),
	local6(7),
	local7(8)
	}
    MAX-ACCESS  read-only
    STATUS  current
    DESCRIPTION
        "The facility level of syslog host in the current configuration block."
    ::= { agSyslog 5 }

agNewCfgSyslogFac   OBJECT-TYPE
    SYNTAX  INTEGER  {
	local0(1),
	local1(2),
	local2(3),
	local3(4),
	local4(5),
	local5(6),
        local6(7),
	local7(8)
	}
    MAX-ACCESS  read-write
    STATUS  current
    DESCRIPTION
        "The facility level of syslog host in the new configuration block."
    ::= { agSyslog 6 }

agCurCfgSyslog2Fac   OBJECT-TYPE
    SYNTAX  INTEGER  {
	local0(1),
	local1(2),
	local2(3),
	local3(4),
	local4(5),
	local5(6),
	local6(7),
	local7(8)
	}
    MAX-ACCESS  read-only
    STATUS  current
    DESCRIPTION
        "The facility level of second syslog host in the current
         configuration block."
    ::= { agSyslog 7 }

agNewCfgSyslog2Fac   OBJECT-TYPE
    SYNTAX  INTEGER  {
	local0(1),
	local1(2),
	local2(3),
	local3(4),
        local4(5),
	local5(6),
        local6(7),
	local7(8)
	}
    MAX-ACCESS  read-write
    STATUS  current
    DESCRIPTION
        "The facility level of second syslog host in the new
         configuration block."
    ::= { agSyslog 8 }

agCurCfgSyslogSev   OBJECT-TYPE
    SYNTAX  INTEGER  {
        emerg0(1),
	alert1(2),
	crit2(3),
	err3(4),
	warning4(5),
	notice5(6),
	info6(7),
	debug7(8)
	}
    MAX-ACCESS  read-only
    STATUS  current
    DESCRIPTION
        "The severity of syslog host in the current configuration block."
    ::= { agSyslog 13 }

agNewCfgSyslogSev   OBJECT-TYPE
    SYNTAX  INTEGER  {
        emerg0(1),
	alert1(2),
	crit2(3),
	err3(4),
	warning4(5),
	notice5(6),
	info6(7),
	debug7(8)
	}
    MAX-ACCESS  read-write
    STATUS  current
    DESCRIPTION
        "The severity of syslog host in the new configuration block."
    ::= { agSyslog 14 }

agCurCfgSyslog2Sev   OBJECT-TYPE
    SYNTAX  INTEGER  {
        emerg0(1),
	alert1(2),
	crit2(3),
	err3(4),
	warning4(5),
	notice5(6),
	info6(7),
	debug7(8)
	}
    MAX-ACCESS  read-only
    STATUS  current
    DESCRIPTION
        "The severity of syslog2 host in the current configuration block."
    ::= { agSyslog 15 }

agNewCfgSyslog2Sev   OBJECT-TYPE
    SYNTAX  INTEGER  {
        emerg0(1),
	alert1(2),
	crit2(3),
	err3(4),
	warning4(5),
	notice5(6),
	info6(7),
	debug7(8)
	}
    MAX-ACCESS  read-write
    STATUS  current
    DESCRIPTION
        "The severity of syslogs host in the new configuration block."
    ::= { agSyslog 16 }

agCurCfgSyslogConsoleSev OBJECT-TYPE
    SYNTAX  INTEGER {
        emerg0(1),
        alert1(2),
        crit2(3),
        err3(4),
        warning4(5),
        notice5(6),
        info6(7),
        debug7(8)
    }
    MAX-ACCESS  read-only
    STATUS  current
    DESCRIPTION
        "The severity of syslogs console in the current configuration block."
    ::= { agSyslog 23 }
    
agNewCfgSyslogConsoleSev   OBJECT-TYPE
    SYNTAX  INTEGER  {
        emerg0(1),
        alert1(2),
        crit2(3),
        err3(4),
        warning4(5),
        notice5(6),
        info6(7),
        debug7(8)
	}
    MAX-ACCESS  read-write
    STATUS  current
    DESCRIPTION
        "The severity of syslogs console in the new configuration block."
    ::= { agSyslog 24 }

agCurCfgSyslogFlashSev OBJECT-TYPE
    SYNTAX  INTEGER {
        emerg0(1),
        alert1(2),
        crit2(3),
        err3(4),
        warning4(5),
        notice5(6),
        info6(7),
        debug7(8)
    }
    MAX-ACCESS  read-only
    STATUS  current
    DESCRIPTION
        "The severity of syslogs flash in the current configuration block."
    ::= { agSyslog 25 }
    
agNewCfgSyslogFlashSev   OBJECT-TYPE
    SYNTAX  INTEGER  {
        emerg0(1),
        alert1(2),
        crit2(3),
        err3(4),
        warning4(5),
        notice5(6),
        info6(7),
        debug7(8)
	}
    MAX-ACCESS  read-write
    STATUS  current
    DESCRIPTION
        "The severity of syslogs flash in the new configuration block."
    ::= { agSyslog 26 }

agClrSyslogMsgs OBJECT-TYPE
    SYNTAX  INTEGER {
        other(1),
        reset(2)
        }
    MAX-ACCESS  read-write
    STATUS  current
    DESCRIPTION
        "Clears all current Syslog messages."
    ::= { agSyslog 9 }

agSyslogMsgTableMaxSize OBJECT-TYPE
    SYNTAX  Integer32
    MAX-ACCESS  read-only
    STATUS  current
    DESCRIPTION
        "The maximum number of rows in the syslog message table."
    ::= { agSyslog 10 }

agCurCfgSyslogHostPort OBJECT-TYPE
    SYNTAX  INTEGER {
        data(1),
        mgt(2)
        }
    MAX-ACCESS  read-only
    STATUS  current
    DESCRIPTION
        "Choose the port that the primary Syslog server is connected to."
    ::= { agSyslog 17 }

agNewCfgSyslogHostPort OBJECT-TYPE
    SYNTAX  INTEGER {
        data(1),
        mgt(2)
        }
    MAX-ACCESS  read-write
    STATUS  current
    DESCRIPTION
        "Choose the port that the primary Syslog server is connected to."
    ::= { agSyslog 18 }

agCurCfgSyslog2HostPort OBJECT-TYPE
    SYNTAX  INTEGER {
        data(1),
        mgt(2)
        }
    MAX-ACCESS  read-only
    STATUS  current
    DESCRIPTION
        "Choose the port that the secondary Syslog server is connected to."
    ::= { agSyslog 19 }

agNewCfgSyslog2HostPort OBJECT-TYPE
    SYNTAX  INTEGER {
        data(1),
        mgt(2)
        }
    MAX-ACCESS  read-write
    STATUS  current
    DESCRIPTION
        "Choose the port that the secondary Syslog server is connected to."
    ::= { agSyslog 20 }

agCurCfgSyslogSrcLoopIf OBJECT-TYPE
    SYNTAX  INTEGER
    MAX-ACCESS  read-only
    STATUS  current
    DESCRIPTION
        "The index of the loopback interface that should be used
         for the source IP of the syslog message; 0 means that
         no loopback interface is used as the source of the syslog message."
    ::= { agSyslog 21 }

agNewCfgSyslogSrcLoopIf OBJECT-TYPE
    SYNTAX  INTEGER
    MAX-ACCESS  read-write
    STATUS  current
    DESCRIPTION
        "The index of the loopback interface that should be used 
         for the source IP of the syslog message; 0 means that
         no loopback interface is used as the source of the syslog message."
    ::= { agSyslog 22 }

agSyslogMsgTable OBJECT-TYPE
    SYNTAX  SEQUENCE OF AgSyslogMsgTableEntry
    MAX-ACCESS  not-accessible
    STATUS  current
    DESCRIPTION
        "The table of syslog messages."
    ::= { agSyslog 11 }

agSyslogMsgTableEntry OBJECT-TYPE
    SYNTAX  AgSyslogMsgTableEntry
    MAX-ACCESS  not-accessible
    STATUS  current
    DESCRIPTION
        "A syslog message stored on the switch."
    INDEX   { agSyslogMsgIndex }
    ::= { agSyslogMsgTable 1 }

AgSyslogMsgTableEntry ::= SEQUENCE {
    agSyslogMsgIndex          Integer32,
    agSyslogMessage           DisplayString
    }

agSyslogMsgIndex OBJECT-TYPE
    SYNTAX  Integer32
    MAX-ACCESS  read-only
    STATUS  current
    DESCRIPTION
        "The syslog message table index."
    ::= { agSyslogMsgTableEntry 1 }

agSyslogMessage OBJECT-TYPE
    SYNTAX  DisplayString (SIZE(0..128))
    MAX-ACCESS  read-only
    STATUS  current
    DESCRIPTION
        "The syslog message."
    ::= { agSyslogMsgTableEntry 2 }

agLog OBJECT IDENTIFIER ::= { agSyslog 12 }

agNewCfgSyslogTrapConsole OBJECT-TYPE
    SYNTAX  INTEGER {
        enabled(1),
        disabled(2)
        }
    MAX-ACCESS  read-write
    STATUS  current
    DESCRIPTION
        "Enable or disable console syslog and SNMP trap in the
         new configuration block."
    ::= { agLog 1 }

agCurCfgSyslogTrapConsole OBJECT-TYPE
    SYNTAX  INTEGER {
        enabled(1),
        disabled(2)
        }
    MAX-ACCESS  read-only
    STATUS  current
    DESCRIPTION
        "Enable or disable console syslog and SNMP trap, as configured
         in the current configuration block."
    ::= { agLog 2 }

agNewCfgSyslogTrapSystem OBJECT-TYPE
    SYNTAX  INTEGER {
        enabled(1),
        disabled(2)
        }
    MAX-ACCESS  read-write
    STATUS  current
    DESCRIPTION
        "Enable or disable system level syslog and SNMP trap in the
         new configuration block."
    ::= { agLog 3 }

agCurCfgSyslogTrapSystem OBJECT-TYPE
    SYNTAX  INTEGER {
        enabled(1),
        disabled(2)
        }
    MAX-ACCESS  read-only
    STATUS  current
    DESCRIPTION
        "Enable or disable system level syslog and SNMP trap, as configured
         in the current configuration block."
    ::= { agLog 4 }

agNewCfgSyslogTrapMgmt OBJECT-TYPE
    SYNTAX  INTEGER {
        enabled(1),
        disabled(2)
        }
    MAX-ACCESS  read-write
    STATUS  current
    DESCRIPTION
        "Enable or disable management(flash, config, login) syslog and SNMP
         trap in the new configuration block."
    ::= { agLog 5 }

agCurCfgSyslogTrapMgmt OBJECT-TYPE
    SYNTAX  INTEGER {
        enabled(1),
        disabled(2)
        }
    MAX-ACCESS  read-only
    STATUS  current
    DESCRIPTION
        "Enable or disable management(flash, config, login) syslog and SNMP
         trap, as configured in the current configuration block."
    ::= { agLog 6 }

agNewCfgSyslogTrapCli OBJECT-TYPE
    SYNTAX  INTEGER {
        enabled(1),
        disabled(2)
        }
    MAX-ACCESS  read-write
    STATUS  current
    DESCRIPTION
        "Enable or disable CLI generated error syslog and SNMP trap in the
	     new configuration block."
    ::= { agLog 7 }

agCurCfgSyslogTrapCli OBJECT-TYPE
    SYNTAX  INTEGER {
        enabled(1),
        disabled(2)
        }
    MAX-ACCESS  read-only
    STATUS  current
    DESCRIPTION
        "Enable or disable CLI generated error syslog and SNMP trap, as
         configured in the current configuration block."
    ::= { agLog 8 }

agNewCfgSyslogTrapStg OBJECT-TYPE
    SYNTAX  INTEGER {
        enabled(1),
        disabled(2)
        }
    MAX-ACCESS  read-write
    STATUS  current
    DESCRIPTION
        "Enable or disable spanning tree syslog and SNMP trap in the
         new configuration block."
    ::= { agLog 9 }

agCurCfgSyslogTrapStg OBJECT-TYPE
    SYNTAX  INTEGER {
        enabled(1),
        disabled(2)
        }
    MAX-ACCESS  read-only
    STATUS  current
    DESCRIPTION
        "Enable or disable spanning tree syslog and SNMP trap, as
         configured in the current configuration block."
    ::= { agLog 10 }

agNewCfgSyslogTrapVlan OBJECT-TYPE
    SYNTAX  INTEGER {
        enabled(1),
        disabled(2)
        }
    MAX-ACCESS  read-write
    STATUS  current
    DESCRIPTION
        "Enable or disable VLAN syslog and SNMP trap in the new
         configuration block."
    ::= { agLog 11 }

agCurCfgSyslogTrapVlan OBJECT-TYPE
    SYNTAX  INTEGER {
        enabled(1),
        disabled(2)
        }
    MAX-ACCESS  read-only
    STATUS  current
    DESCRIPTION
        "Enable or disable VLAN syslog and SNMP trap, as configured
         in the current configuration block."
    ::= { agLog 12 }



agNewCfgSyslogTrapSsh OBJECT-TYPE
    SYNTAX  INTEGER {
        enabled(1),
        disabled(2)
        }
    MAX-ACCESS  read-write
    STATUS  current
    DESCRIPTION
        "Enable or disable SSH, RADIUS syslog and SNMP trap in the new
         configuration block."
    ::= { agLog 19 }

agCurCfgSyslogTrapSsh OBJECT-TYPE
    SYNTAX  INTEGER {
        enabled(1),
        disabled(2)
        }
    MAX-ACCESS  read-only
    STATUS  current
    DESCRIPTION
        "Enable or disable SSH, RADIUS syslog and SNMP trap, as configured
         in the current configuration block."
    ::= { agLog 20 }

agNewCfgSyslogTrapVrrp OBJECT-TYPE
    SYNTAX  INTEGER {
        enabled(1),
        disabled(2)
        }
    MAX-ACCESS  read-write
    STATUS  current
    DESCRIPTION
        "Enable or disable VRRP syslog and SNMP trap in the new
         configuration block."
    ::= { agLog 21 }

agCurCfgSyslogTrapVrrp OBJECT-TYPE
    SYNTAX  INTEGER {
        enabled(1),
        disabled(2)
        }
    MAX-ACCESS  read-only
    STATUS  current
    DESCRIPTION
        "Enable or disable VRRP syslog and SNMP trap, as configured
         in the current configuration block."
    ::= { agLog 22 }

agNewCfgSyslogTrapBgp OBJECT-TYPE
    SYNTAX  INTEGER {
        enabled(1),
        disabled(2)
        }
    MAX-ACCESS  read-write
    STATUS  current
    DESCRIPTION
        "Enable or disable BGP syslog and SNMP trap in the new
         configuration block."
    ::= { agLog 23 }

agCurCfgSyslogTrapBgp OBJECT-TYPE
    SYNTAX  INTEGER {
        enabled(1),
        disabled(2)
        }
    MAX-ACCESS  read-only
    STATUS  current
    DESCRIPTION
        "Enable or disable BGP syslog and SNMP trap, as configured
         in the current configuration block."
    ::= { agLog 24 }

agNewCfgSyslogTrapNtp OBJECT-TYPE
    SYNTAX  INTEGER {
        enabled(1),
        disabled(2)
        }
    MAX-ACCESS  read-write
    STATUS  current
    DESCRIPTION
        "Enable or disable NTP syslog and SNMP trap in the new
         configuration block."
    ::= { agLog 25 }

agCurCfgSyslogTrapNtp OBJECT-TYPE
    SYNTAX  INTEGER {
        enabled(1),
        disabled(2)
        }
    MAX-ACCESS  read-only
    STATUS  current
    DESCRIPTION
        "Enable or disable NTP syslog and SNMP trap, as configured
         in the current configuration block."
    ::= { agLog 26 }

agNewCfgSyslogTrapIp OBJECT-TYPE
    SYNTAX  INTEGER {
        enabled(1),
        disabled(2)
        }
    MAX-ACCESS  read-write
    STATUS  current
    DESCRIPTION
        "Enable or disable IP related syslog and SNMP trap in the
         new configuration block."
    ::= { agLog 31 }

agCurCfgSyslogTrapIp OBJECT-TYPE
    SYNTAX  INTEGER {
        enabled(1),
        disabled(2)
        }
    MAX-ACCESS  read-only
    STATUS  current
    DESCRIPTION
        "Enable or disable IP related syslog and SNMP trap, as configured
         in the current configuration block."
    ::= { agLog 32 }

agNewCfgSyslogTrapWeb OBJECT-TYPE
    SYNTAX  INTEGER {
        enabled(1),
        disabled(2)
        }
    MAX-ACCESS  read-write
    STATUS  current
    DESCRIPTION
        "Enable or disable WEBUI related syslog and SNMP trap in the
         new configuration block."
    ::= { agLog 35 }

agCurCfgSyslogTrapWeb OBJECT-TYPE
    SYNTAX  INTEGER {
        enabled(1),
        disabled(2)
        }
    MAX-ACCESS  read-only
    STATUS  current
    DESCRIPTION
        "Enable or disable WEBUI related syslog and SNMP trap, as configured
         in the current configuration block."
    ::= { agLog 36 }



agNewCfgSyslogTrapOspf OBJECT-TYPE
    SYNTAX  INTEGER {
        enabled(1),
        disabled(2)
        }
    MAX-ACCESS  read-write
    STATUS  current
    DESCRIPTION
        "Enable or disable OSPF related syslog and SNMP trap
         in the new configuration block."
    ::= { agLog 41 }

agCurCfgSyslogTrapOspf OBJECT-TYPE
    SYNTAX  INTEGER {
        enabled(1),
        disabled(2)
        }
    MAX-ACCESS  read-only
    STATUS  current
    DESCRIPTION
        "Enable or disable OSPF related syslog and SNMP trap,
         as configured in the current configuration block."
    ::= { agLog 42 }


agNewCfgSyslogTrapRmon OBJECT-TYPE
    SYNTAX  INTEGER {
        enabled(1),
        disabled(2)
        }
    MAX-ACCESS  read-write
    STATUS  current
    DESCRIPTION
        "Enable or disable RMON related syslog and SNMP trap
         in the new configuration block."
    ::= { agLog 45 }

agCurCfgSyslogTrapRmon OBJECT-TYPE
    SYNTAX  INTEGER {
        enabled(1),
        disabled(2)
        }
    MAX-ACCESS  read-only
    STATUS  current
    DESCRIPTION
        "Enable or disable RMON related syslog and SNMP trap,
         as configured in the current configuration block."
    ::= { agLog 46 }


agNewCfgSyslogTrap8021x OBJECT-TYPE
    SYNTAX  INTEGER {
        enabled(1),
        disabled(2)
        }
    MAX-ACCESS  read-write
    STATUS  current
    DESCRIPTION
        "Enable or disable 802.1x related syslog and SNMP trap
         in the new configuration block."
    ::= { agLog 49 }

agCurCfgSyslogTrap8021x OBJECT-TYPE
    SYNTAX  INTEGER {
        enabled(1),
        disabled(2)
        }
    MAX-ACCESS  read-only
    STATUS  current
    DESCRIPTION
        "Enable or disable 802.1x related syslog and SNMP trap,
         as configured in the current configuration block."
    ::= { agLog 50 }

-- 802.1x port stats table

dot1xPortStatsTable OBJECT-TYPE
    SYNTAX  SEQUENCE OF Dot1xPortStatsTableEntry
    MAX-ACCESS  not-accessible
    STATUS  current
    DESCRIPTION
        "The table of 802.1x port statistics."
    ::= { portStats 2 }

dot1xPortStatsTableEntry OBJECT-TYPE
    SYNTAX  Dot1xPortStatsTableEntry
    MAX-ACCESS  not-accessible
    STATUS  current
    DESCRIPTION
        "A row in the 802.1x  port stats table."
    INDEX   { dot1xPortStatsIndx }
    ::= { dot1xPortStatsTable 1 }

Dot1xPortStatsTableEntry ::=
    SEQUENCE {
	dot1xPortStatsIndx PortNumber,
	eapolFramesRx Integer32,
	eapolFramesTx Integer32,
	eapolStartFramesRx Integer32,
	eapolLogoffFramesRx  Integer32,
	eapolRespIdFramesRx Integer32,
	eapolRespFramesRx  Integer32,
	eapolReqIdFramesTx Integer32,
	eapolReqFramesTx Integer32,
	invalidEapolFramesRx Integer32,
	eapLengthErrorFramesRx Integer32,
	authEntersConnecting Integer32,
	authEapLogoffsWhileConnecting Integer32,
	authEntersAuthenticating  Integer32,
	authSuccessesWhileAuthenticating Integer32,
	authTimeoutsWhileAuthenticating Integer32,
	authFailWhileAuthenticating Integer32,
	authReauthsWhileAuthenticating 	Integer32,
	authEapStartsWhileAuthenticating Integer32,
	authEapLogoffWhileAuthenticating Integer32,
	authReauthsWhileAuthenticated 	Integer32,
	authEapStartsWhileAuthenticated  Integer32,
	authEapLogoffWhileAuthenticated  Integer32,
	backendResponses Integer32,
	backendAccessChallenges  Integer32,
	backendOtherRequestsToSupplicant Integer32,
	backendNonNakResponsesFromSupplicant Integer32,
	backendAuthSuccesses 	Integer32,
	backendAuthFails Integer32,
        lastEapolFrameVersion Integer32,
        lastEapolFrameSource MacAddress
    }

dot1xPortStatsIndx OBJECT-TYPE
    SYNTAX  PortNumber
    MAX-ACCESS  read-only
    STATUS  current
    DESCRIPTION
        "The 802.1x port stats index."
    ::= { dot1xPortStatsTableEntry 1 }

eapolFramesRx OBJECT-TYPE
    SYNTAX  Integer32
    MAX-ACCESS  read-only
    STATUS  current
    DESCRIPTION
        ""
    ::= { dot1xPortStatsTableEntry 2 }

eapolFramesTx OBJECT-TYPE
    SYNTAX  Integer32
    MAX-ACCESS  read-only
    STATUS  current
    DESCRIPTION
        ""
    ::= { dot1xPortStatsTableEntry 3 }

eapolStartFramesRx OBJECT-TYPE
    SYNTAX  Integer32
    MAX-ACCESS  read-only
    STATUS  current
    DESCRIPTION
        ""
    ::= { dot1xPortStatsTableEntry 4 }


eapolLogoffFramesRx OBJECT-TYPE
    SYNTAX  Integer32
    MAX-ACCESS  read-only
    STATUS  current
    DESCRIPTION
        ""
    ::= { dot1xPortStatsTableEntry 5 }

eapolRespIdFramesRx OBJECT-TYPE
    SYNTAX  Integer32
    MAX-ACCESS  read-only
    STATUS  current
    DESCRIPTION
        ""
    ::= { dot1xPortStatsTableEntry 6 }

eapolRespFramesRx OBJECT-TYPE
    SYNTAX  Integer32
    MAX-ACCESS  read-only
    STATUS  current
    DESCRIPTION
        ""
    ::= { dot1xPortStatsTableEntry 7 }

eapolReqIdFramesTx OBJECT-TYPE
    SYNTAX  Integer32
    MAX-ACCESS  read-only
    STATUS  current
    DESCRIPTION
        ""
    ::= { dot1xPortStatsTableEntry 8 }


eapolReqFramesTx OBJECT-TYPE
    SYNTAX  Integer32
    MAX-ACCESS  read-only
    STATUS  current
    DESCRIPTION
        ""
    ::= { dot1xPortStatsTableEntry 9 }

invalidEapolFramesRx OBJECT-TYPE
    SYNTAX  Integer32
    MAX-ACCESS  read-only
    STATUS  current
    DESCRIPTION
        ""
    ::= {dot1xPortStatsTableEntry 10  }

eapLengthErrorFramesRx OBJECT-TYPE
    SYNTAX  Integer32
    MAX-ACCESS  read-only
    STATUS  current
    DESCRIPTION
        ""
    ::= { dot1xPortStatsTableEntry 11 }

authEntersConnecting  OBJECT-TYPE
    SYNTAX  Integer32
    MAX-ACCESS  read-only
    STATUS  current
    DESCRIPTION
        ""
    ::= { dot1xPortStatsTableEntry 12 }


authEapLogoffsWhileConnecting OBJECT-TYPE
    SYNTAX  Integer32
    MAX-ACCESS  read-only
    STATUS  current
    DESCRIPTION
        ""
    ::= { dot1xPortStatsTableEntry 13 }

authEntersAuthenticating  OBJECT-TYPE
    SYNTAX  Integer32
    MAX-ACCESS  read-only
    STATUS  current
    DESCRIPTION
        ""
    ::= { dot1xPortStatsTableEntry 14 }

authSuccessesWhileAuthenticating  OBJECT-TYPE
    SYNTAX  Integer32
    MAX-ACCESS  read-only
    STATUS  current
    DESCRIPTION
        ""
    ::= { dot1xPortStatsTableEntry 15 }

authTimeoutsWhileAuthenticating OBJECT-TYPE
    SYNTAX  Integer32
    MAX-ACCESS  read-only
    STATUS  current
    DESCRIPTION
        ""
    ::= { dot1xPortStatsTableEntry 16 }

authFailWhileAuthenticating OBJECT-TYPE
    SYNTAX  Integer32
    MAX-ACCESS  read-only
    STATUS  current
    DESCRIPTION
        ""
    ::= { dot1xPortStatsTableEntry 17 }

authReauthsWhileAuthenticating  OBJECT-TYPE
    SYNTAX  Integer32
    MAX-ACCESS  read-only
    STATUS  current
    DESCRIPTION
        ""
    ::= { dot1xPortStatsTableEntry 18 }

authEapStartsWhileAuthenticating  OBJECT-TYPE
    SYNTAX  Integer32
    MAX-ACCESS  read-only
    STATUS  current
    DESCRIPTION
        ""
    ::= { dot1xPortStatsTableEntry 19 }

authEapLogoffWhileAuthenticating  OBJECT-TYPE
    SYNTAX  Integer32
    MAX-ACCESS  read-only
    STATUS  current
    DESCRIPTION
        ""
    ::= { dot1xPortStatsTableEntry 20 }


authReauthsWhileAuthenticated  OBJECT-TYPE
    SYNTAX  Integer32
    MAX-ACCESS  read-only
    STATUS  current
    DESCRIPTION
        ""
    ::= { dot1xPortStatsTableEntry 21 }

authEapStartsWhileAuthenticated  OBJECT-TYPE
    SYNTAX  Integer32
    MAX-ACCESS  read-only
    STATUS  current
    DESCRIPTION
        ""
    ::= { dot1xPortStatsTableEntry 22 }

authEapLogoffWhileAuthenticated  OBJECT-TYPE
    SYNTAX  Integer32
    MAX-ACCESS  read-only
    STATUS  current
    DESCRIPTION
        ""
    ::= { dot1xPortStatsTableEntry 23 }

backendResponses  OBJECT-TYPE
    SYNTAX  Integer32
    MAX-ACCESS  read-only
    STATUS  current
    DESCRIPTION
        ""
    ::= { dot1xPortStatsTableEntry 24 }

backendAccessChallenges  OBJECT-TYPE
    SYNTAX  Integer32
    MAX-ACCESS  read-only
    STATUS  current
    DESCRIPTION
        ""
    ::= { dot1xPortStatsTableEntry 25 }

backendOtherRequestsToSupplicant  OBJECT-TYPE
    SYNTAX  Integer32
    MAX-ACCESS  read-only
    STATUS  current
    DESCRIPTION
        ""
    ::= { dot1xPortStatsTableEntry 26 }

backendNonNakResponsesFromSupplicant  OBJECT-TYPE
    SYNTAX  Integer32
    MAX-ACCESS  read-only
    STATUS  current
    DESCRIPTION
        ""
    ::= { dot1xPortStatsTableEntry 27 }

backendAuthSuccesses  OBJECT-TYPE
    SYNTAX  Integer32
    MAX-ACCESS  read-only
    STATUS  current
    DESCRIPTION
        ""
    ::= { dot1xPortStatsTableEntry 28 }

backendAuthFails   OBJECT-TYPE
    SYNTAX  Integer32
    MAX-ACCESS  read-only
    STATUS  current
    DESCRIPTION
        ""
    ::= { dot1xPortStatsTableEntry 29 }

lastEapolFrameVersion   OBJECT-TYPE
    SYNTAX  Integer32
    MAX-ACCESS  read-only
    STATUS  current
    DESCRIPTION
        ""
    ::= { dot1xPortStatsTableEntry 30 }

lastEapolFrameSource   OBJECT-TYPE
    SYNTAX MacAddress
    MAX-ACCESS  read-only
    STATUS  current
    DESCRIPTION
        ""
    ::= { dot1xPortStatsTableEntry 31 }



agNewCfgSyslogTrapCfg OBJECT-TYPE
    SYNTAX  INTEGER {
        enabled(1),
        disabled(2)
        }
    MAX-ACCESS  read-write
    STATUS  current
    DESCRIPTION
        "Enable or disable CFG related syslog and SNMP trap in the
         new configuration block."
    ::= { agLog 53 }

agCurCfgSyslogTrapCfg OBJECT-TYPE
    SYNTAX  INTEGER {
        enabled(1),
        disabled(2)
        }
    MAX-ACCESS  read-only
    STATUS  current
    DESCRIPTION
        "Enable or disable CFG related syslog and SNMP trap,
         as configured in the current configuration block."
    ::= { agLog 54 }

agNewCfgSyslogTrapServer OBJECT-TYPE
    SYNTAX  INTEGER {
        enabled(1),
        disabled(2)
        }
    MAX-ACCESS  read-write
    STATUS  current
    DESCRIPTION
        "Enable or disable Server related syslog and SNMP trap in the
         new configuration block."
    ::= { agLog 55 }

agCurCfgSyslogTrapServer OBJECT-TYPE
    SYNTAX  INTEGER {
        enabled(1),
        disabled(2)
        }
    MAX-ACCESS  read-only
    STATUS  current
    DESCRIPTION
        "Enable or disable Server related syslog and SNMP trap,
         as configured in the current configuration block."
    ::= { agLog 56 }

agNewCfgSyslogTrapDifftrak OBJECT-TYPE
    SYNTAX  INTEGER {
        enabled(1),
        disabled(2)
        }
    MAX-ACCESS  read-write
    STATUS  current
    DESCRIPTION
        "Enable or disable Difftrak related syslog and SNMP trap in the
         new configuration block."
    ::= { agLog 57 }

agCurCfgSyslogTrapDifftrak OBJECT-TYPE
    SYNTAX  INTEGER {
        enabled(1),
        disabled(2)
        }
    MAX-ACCESS  read-only
    STATUS  current
    DESCRIPTION
        "Enable or disable Difftrak related syslog and SNMP trap,
         as configured in the current configuration block."
    ::= { agLog 58 }


agNewCfgSyslogTrapHotlinks             OBJECT-TYPE
    SYNTAX      INTEGER {
                    enabled(1),
                    disabled(2)
                }
    MAX-ACCESS  read-write
    STATUS      current
    DESCRIPTION
        "Enable or disable Hot Links related syslog and SNMP trap in the
         new configuration block."
    ::= { agLog 61 }

agCurCfgSyslogTrapHotlinks             OBJECT-TYPE
    SYNTAX      INTEGER {
                    enabled(1),
                    disabled(2)
                }
    MAX-ACCESS  read-only
    STATUS      current
    DESCRIPTION
        "Enable or disable Hot Links related syslog and SNMP trap,
         as configured in the current configuration block."
    ::= { agLog 62 }

agNewCfgSyslogTrapLldp OBJECT-TYPE
    SYNTAX  INTEGER {
        enabled(1),
        disabled(2)
        }
    MAX-ACCESS  read-write
    STATUS  current
    DESCRIPTION
        "Enable or disable LLDP related syslog and SNMP trap in the
         new configuration block."
    ::= { agLog 63 }

agCurCfgSyslogTrapLldp OBJECT-TYPE
    SYNTAX  INTEGER {
        enabled(1),
        disabled(2)
        }
    MAX-ACCESS  read-only
    STATUS  current
    DESCRIPTION
        "Enable or disable LLDP related syslog and SNMP trap,
         as configured in the current configuration block."
    ::= { agLog 64 }

agNewCfgSyslogTrapAll OBJECT-TYPE
    SYNTAX  INTEGER {
        enabled(1),
        disabled(2)
        }
    MAX-ACCESS  read-write
    STATUS  current
    DESCRIPTION
        "Enable or disable all syslog and SNMP traps in the
         new configuration block."
    ::= { agLog 65 }

agCurCfgSyslogTrapAll OBJECT-TYPE
    SYNTAX  INTEGER {
        enabled(1),
        disabled(2)
        }
    MAX-ACCESS  read-only
    STATUS  current
    DESCRIPTION
        "Enable or disable all syslog and SNMP traps, as configured
         in the current configuration block."
    ::= { agLog 66 }
agNewCfgSyslogTrapIpv6 OBJECT-TYPE
    SYNTAX  INTEGER {
        enabled(1),
        disabled(2)
        }
    MAX-ACCESS  read-write
    STATUS  current
    DESCRIPTION
        "Enable or disable IPv6 related syslog and SNMP trap in the
         new configuration block."
    ::= { agLog 67 }

agCurCfgSyslogTrapIpv6 OBJECT-TYPE
    SYNTAX  INTEGER {
        enabled(1),
        disabled(2)
        }
    MAX-ACCESS  read-only
    STATUS  current
    DESCRIPTION
        "Enable or disable IPv6 related syslog and SNMP trap,
         as configured in the current configuration block."
    ::= { agLog 68 }

agNewCfgSyslogTrapFailover OBJECT-TYPE
    SYNTAX  INTEGER {
        enabled(1),
        disabled(2)
        }
    MAX-ACCESS  read-write
    STATUS  current
    DESCRIPTION
        "Enable or disable failover related syslog and SNMP trap in the
         new configuration block."
    ::= { agLog 73 }

agCurCfgSyslogTrapFailover OBJECT-TYPE
    SYNTAX  INTEGER {
        enabled(1),
        disabled(2)
        }
    MAX-ACCESS  read-only
    STATUS  current
    DESCRIPTION
        "Enable or disable failover related syslog and SNMP trap,
         as configured in the current configuration block."
    ::= { agLog 74 }

agNewCfgSyslogTrapLacp  OBJECT-TYPE
    SYNTAX  INTEGER {
        enabled(1),
        disabled(2)
        }
    MAX-ACCESS  read-write
    STATUS  current
    DESCRIPTION
        "Enable or disable LACP syslog and SNMP trap in the
         new configuration block."
    ::= { agLog 77 }

agCurCfgSyslogTrapLacp  OBJECT-TYPE
    SYNTAX  INTEGER {
        enabled(1),
        disabled(2)
        }
    MAX-ACCESS  read-only
    STATUS  current
    DESCRIPTION
        "Enable or disable LACP syslog and SNMP trap, as configured
         in the current configuration block."
    ::= { agLog 78 }

agNewCfgSyslogTrapLink OBJECT-TYPE
    SYNTAX  INTEGER {
        enabled(1),
        disabled(2)
        }
    MAX-ACCESS  read-write
    STATUS  current
    DESCRIPTION
        "Enable or disable all syslog and SNMP traps, in link
         up/down."
    ::= { agLog 79 }

agCurCfgSyslogTrapLink OBJECT-TYPE
    SYNTAX  INTEGER {
        enabled(1),
        disabled(2)
        }
    MAX-ACCESS  read-only
    STATUS  current
    DESCRIPTION
        "Enable or disable all syslog and SNMP traps, as currently
         configured in link up/down."
    ::= { agLog 80 }

agNewCfgSyslogTrapOspfv3 OBJECT-TYPE
    SYNTAX  INTEGER {
        enabled(1),
        disabled(2)
        }
    MAX-ACCESS  read-write
    STATUS  current
    DESCRIPTION
        "Enable or disable OSPFv3 related syslog and SNMP trap
         in the new configuration block."
    ::= { agLog 81 }

agCurCfgSyslogTrapOspfv3 OBJECT-TYPE
    SYNTAX  INTEGER {
        enabled(1),
        disabled(2)
        }
    MAX-ACCESS  read-only
    STATUS  current
    DESCRIPTION
        "Enable or disable OSPFv3 related syslog and SNMP trap,
         as configured in the current configuration block."
    ::= { agLog 82 }

agNewCfgSyslogTrapDcbx OBJECT-TYPE
    SYNTAX  INTEGER {
        enabled(1),
        disabled(2)
        }
    MAX-ACCESS  read-write
    STATUS  current
    DESCRIPTION
        "Enable or disable all DCBX-related syslog and SNMP traps."
    ::= { agLog 85 }

agCurCfgSyslogTrapDcbx OBJECT-TYPE
    SYNTAX  INTEGER {
        enabled(1),
        disabled(2)
        }
    MAX-ACCESS  read-only
    STATUS  current
    DESCRIPTION
        "Enable or disable all DCBX-related syslog and SNMP traps."
    ::= { agLog 86 }

agNewCfgSyslogTrapFcoe OBJECT-TYPE
    SYNTAX  INTEGER {
        enabled(1),
        disabled(2)
        }
    MAX-ACCESS  read-write
    STATUS  current
    DESCRIPTION
        "Enable or disable all FCOE-related syslog and SNMP traps."
    ::= { agLog 87 }

agCurCfgSyslogTrapFcoe OBJECT-TYPE
    SYNTAX  INTEGER {
        enabled(1),
        disabled(2)
        }
    MAX-ACCESS  read-only
    STATUS  current
    DESCRIPTION
        "Enable or disable all FCOE-related syslog and SNMP traps."
    ::= { agLog 88 }

agNewCfgSyslogTrapVm OBJECT-TYPE
    SYNTAX  INTEGER {
        enabled(1),
        disabled(2)
        }
    MAX-ACCESS  read-write
    STATUS  current
    DESCRIPTION
        "Enable or disable all VM-related syslog and SNMP traps."
    ::= { agLog 89 }

agCurCfgSyslogTrapVm OBJECT-TYPE
    SYNTAX  INTEGER {
        enabled(1),
        disabled(2)
        }
    MAX-ACCESS  read-only
    STATUS  current
    DESCRIPTION
        "Enable or disable all VM-related syslog and SNMP traps."
    ::= { agLog 90 }

agNewCfgSyslogTrapVnic OBJECT-TYPE
    SYNTAX  INTEGER {
        enabled(1),
        disabled(2)
        }
    MAX-ACCESS  read-write
    STATUS  current
    DESCRIPTION
        "Enable or disable all VNIC-related syslog and SNMP traps."
    ::= { agLog 91 }

agCurCfgSyslogTrapVnic OBJECT-TYPE
    SYNTAX  INTEGER {
        enabled(1),
        disabled(2)
        }
    MAX-ACCESS  read-only
    STATUS  current
    DESCRIPTION
        "Enable or disable all VNIC-related syslog and SNMP traps."
    ::= { agLog 92 }

agNewCfgSyslogTrapCfgchg OBJECT-TYPE
    SYNTAX  INTEGER {
        enabled(1),
        disabled(2)
        }
    MAX-ACCESS  read-write
    STATUS  current
    DESCRIPTION
        "Enable or disable configuration change related syslog and SNMP trap
         in the new configuration block." 
    ::= { agLog 93 }

agCurCfgSyslogTrapCfgchg OBJECT-TYPE
    SYNTAX  INTEGER {
        enabled(1),
        disabled(2)
        }
    MAX-ACCESS  read-only
    STATUS  current
    DESCRIPTION
        "Enable or disable configuration change related syslog and SNMP trap, 
         as configured in the current configuration block." 
    ::= { agLog 94 }

agNewCfgSyslogTrapVlag OBJECT-TYPE
    SYNTAX  INTEGER {
        enabled(1),
        disabled(2)
        }
    MAX-ACCESS  read-write
    STATUS  current
    DESCRIPTION
        "Enable or disable Vlag related syslog and SNMP trap." 
    ::= { agLog 95 }

agCurCfgSyslogTrapVlag OBJECT-TYPE
    SYNTAX  INTEGER {
        enabled(1),
        disabled(2)
        }
    MAX-ACCESS  read-only
    STATUS  current
    DESCRIPTION
        "Enable or disable Vlag related syslog and SNMP trap." 
    ::= { agLog 96 }


agNewCfgSyslogTrapIgmpGroup OBJECT-TYPE
    SYNTAX  INTEGER {
        enabled(1),
        disabled(2)
        }
    MAX-ACCESS  read-write
    STATUS  current
    DESCRIPTION
        "Enable or disable all IGMP GROUP-related syslog and SNMP traps."
    ::= { agLog 99 }

agCurCfgSyslogTrapIgmpGroup OBJECT-TYPE
    SYNTAX  INTEGER {
        enabled(1),
        disabled(2)
        }
    MAX-ACCESS  read-only
    STATUS  current
    DESCRIPTION
        "Enable or disable all IGMP GROUP-related syslog and SNMP traps."
    ::= { agLog 100 }

agNewCfgSyslogTrapIgmpMrouter OBJECT-TYPE
    SYNTAX  INTEGER {
        enabled(1),
        disabled(2)
        }
    MAX-ACCESS  read-write
    STATUS  current
    DESCRIPTION
        "Enable or disable all IGMP MROUTER-related syslog and SNMP traps."
    ::= { agLog 101 }

agCurCfgSyslogTrapIgmpMrouter OBJECT-TYPE
    SYNTAX  INTEGER {
        enabled(1),
        disabled(2)
        }
    MAX-ACCESS  read-only
    STATUS  current
    DESCRIPTION
        "Enable or disable all IGMP MROUTER-related syslog and SNMP traps."
    ::= { agLog 102 }

agNewCfgSyslogTrapIgmpQuerier OBJECT-TYPE
    SYNTAX  INTEGER {
        enabled(1),
        disabled(2)
        }
    MAX-ACCESS  read-write
    STATUS  current
    DESCRIPTION
        "Enable or disable all IGMP QUERIER-related syslog and SNMP traps."
    ::= { agLog 103 }

agCurCfgSyslogTrapIgmpQuerier OBJECT-TYPE
    SYNTAX  INTEGER {
        enabled(1),
        disabled(2)
        }
    MAX-ACCESS  read-only
    STATUS  current
    DESCRIPTION
        "Enable or disable all IGMP QUERIER-related syslog and SNMP traps."
    ::= { agLog 104 }

agNewCfgSyslogTrapMld OBJECT-TYPE
    SYNTAX  INTEGER {
        enabled(1),
        disabled(2)
        }
    MAX-ACCESS  read-write
    STATUS  current
    DESCRIPTION
        "Enable or disable all MLD-related syslog and SNMP traps."
    ::= { agLog 105 }

agCurCfgSyslogTrapMld OBJECT-TYPE
    SYNTAX  INTEGER {
        enabled(1),
        disabled(2)
        }
    MAX-ACCESS  read-only
    STATUS  current
    DESCRIPTION
        "Enable or disable all MLD-related syslog and SNMP traps."
    ::= { agLog 106 }

agNewCfgSyslogTrapPrivateVlan OBJECT-TYPE
    SYNTAX  INTEGER {
        enabled(1),
        disabled(2)
        }
    MAX-ACCESS  read-write
    STATUS  current
    DESCRIPTION
        "Enable or disable all Private VLAN-related syslog and SNMP traps,
         as configured in the new configuration block."
    ::= { agLog 107 }

agCurCfgSyslogTrapPrivateVlan OBJECT-TYPE
    SYNTAX  INTEGER {
        enabled(1),
        disabled(2)
        }
    MAX-ACCESS  read-only
    STATUS  current
    DESCRIPTION
        "Enable or disable all Private VLAN-related syslog and SNMP traps,
         as configured in the current configuration block."
    ::= { agLog 108 }

agNewCfgSyslogTrapSlp OBJECT-TYPE
    SYNTAX  INTEGER {
        enabled(1),
        disabled(2)
        }
    MAX-ACCESS  read-write
    STATUS  current
    DESCRIPTION
        "Enable or disable all SLP-related syslog and SNMP traps,
         as configured in the new configuration block."
    ::= { agLog 109 }

agCurCfgSyslogTrapSlp OBJECT-TYPE
    SYNTAX  INTEGER {
        enabled(1),
        disabled(2)
        }
    MAX-ACCESS  read-only
    STATUS  current
    DESCRIPTION
        "Enable or disable all SLP-related syslog and SNMP traps,
         as configured in the current configuration block."
    ::= { agLog 110 }


-- TFTP Config
agTransferServer OBJECT-TYPE
    SYNTAX  DisplayString (SIZE(0..128))
    MAX-ACCESS  read-write
    STATUS  current
    DESCRIPTION
        "The FTP/TFTP server IP address or domain name."
    ::= { agTransfer 1 }

agTransferImage OBJECT-TYPE
    SYNTAX  INTEGER {
        image1(2),
        image2(3),
        boot(4)
        }
    MAX-ACCESS  read-write
    STATUS  current
    DESCRIPTION
        "Whether the image file should be loaded in image1 or image2 in flash."
    ::= { agTransfer 2 }

agTransferImageFileName OBJECT-TYPE
    SYNTAX  DisplayString (SIZE(0..128))
    MAX-ACCESS  read-write
    STATUS  current
    DESCRIPTION
        "The image file name to be transferred."
    ::= { agTransfer 3 }

agTransferCfgFileName OBJECT-TYPE
    SYNTAX  DisplayString (SIZE(0..128))
    MAX-ACCESS  read-write
    STATUS  current
    DESCRIPTION
        "The configuration file name."
    ::= { agTransfer 4 }

agTransferDumpFileName OBJECT-TYPE
    SYNTAX  DisplayString (SIZE(0..128))
    MAX-ACCESS  read-write
    STATUS  current
    DESCRIPTION
        "The core dump file name."
    ::= { agTransfer 5 }

agTransferAction OBJECT-TYPE
    SYNTAX  INTEGER {
        other(1),
        img-get(2),
        cfg-get(3),
        cfg-put(4),
        dump-put(5),
        img-put(7),
        tsdump-put(8)
        ,ca-get(14)
        ,hostcert-get(15)
        ,hostkey-get(16)
        ,pubkey-get(17)
        }
    MAX-ACCESS  read-write
    STATUS  current
    DESCRIPTION
        "This is an action object to perform various FTP/TFTP Get or Put functions.
         The FTP/TFTP sever is specified in agTransferServer object.
	 img-get(2)    - Download switch image from a specified image
                         file(agTransferImageFileName) on the FTP/TFTP server to
	                 the destinated storage(agTransferImage).
                         The duration of the action will depend on the image 
                         downloading and writting time on the network element.
                         Sugguest 150 seconds timeout setting in MIB Browser to get 
                         the correct response for this action.
	 cfg-get(3)    - Download switch configuration from a specified
                         file(agTransferCfgFileName) on the FTP/TFTP server.
	 cfg-put(4)    - Upload switch configuration to a specified
                         file(agTransferCfgFileName) on the FTP/TFTP server.
	 dump-put(5)   - Download switch core dump to a specified
                         file(agTransferDumpFileName) on the FTP/TFTP server.
	 bkpdump-put(6)- Download switch backup core dump to a specified
                         file(agTransferDumpFileName) on the FTP/TFTP server.
         img-put(7)    - Upload specified switch image to a specified image
                         file(agTransferImageFileName) on the FTP/TFTP server.
         tsdump-put(8) - Download switch tech support dump to a specified
                         file(agTransferTSDumpFileName) on the FTP/TFTP server.
	 bogon-get(9)  - Download bogon config file from a specified bogon
                         file(uses agTransferImageFileName) on the FTP/TFTP server.
    ca-get(14)         - Download CA root certificate from a specified
                         file(agTransferCaFileName) on the TFTP server. 
                         This command did not support FTP.
    hostcert-get(15)   - Download host certificate from a specified
                         file(agTransferHostCertFileName) on the TFTP server.
                         This command did not support FTP.
    hostkey-get(16)    - Download host private key from a specified
                         file(agTransferHostKeyFileName) on the TFTP server.
                         This command did not support FTP.
    pubkey-get(17)     - Download SSH client public key from a specified
                         file(agTransferPublicKeyFileName) on the TFTP/SFTP server.
                         This command did not support FTP.
         other(1) is returned always when read."
    ::= { agTransfer 6 }

agTransferLastActionStatus OBJECT-TYPE
    SYNTAX  DisplayString (SIZE(0..128))
    MAX-ACCESS  read-only
    STATUS  current
    DESCRIPTION
        "The recorded status of the previous FTP/TFTP activity."
    ::= { agTransfer 7 }

agTransferPort OBJECT-TYPE
    SYNTAX  INTEGER {
        data(1),
        mgt(2)
        }
    MAX-ACCESS  read-write
    STATUS  current
    DESCRIPTION
        "Specify whether the FTP/TFTP operation should be performed over the
         data port or the management port."
    ::= { agTransfer 8 }

agTransferUserName OBJECT-TYPE
    SYNTAX  DisplayString (SIZE(0..128))
    MAX-ACCESS  read-write
    STATUS  current
    DESCRIPTION
        "The username for the FTP server or blank for TFTP server."
    ::= { agTransfer 9 }

agTransferPassword OBJECT-TYPE
    SYNTAX  DisplayString (SIZE(0..128))
    MAX-ACCESS  read-write
    STATUS  current
    DESCRIPTION
        "The password for the FTP server. For security reason, an empty string will be returned when the OID is read."
    ::= { agTransfer 10 }

agTransferTSDumpFileName OBJECT-TYPE
    SYNTAX  DisplayString (SIZE(0..128))
    MAX-ACCESS  read-write
    STATUS  current
    DESCRIPTION
        "The TS dump file name."
    ::= { agTransfer 11 }


agTransferLastConfigurationActionStatus OBJECT-TYPE
    SYNTAX INTEGER {
        successfully(1),
        failed(2)
        }
    MAX-ACCESS  read-only
    STATUS  current
    DESCRIPTION
        "The status of the last configuration action using the file ftp/tftp'd
         from server."
    ::= { agTransfer 14 }

agTransferCaFileName OBJECT-TYPE
    SYNTAX  DisplayString (SIZE(0..128))
    MAX-ACCESS  read-write
    STATUS  current
    DESCRIPTION
        "The CA certificate file name."
    ::= { agTransfer 15 }
    
agTransferHostCertFileName OBJECT-TYPE
    SYNTAX  DisplayString (SIZE(0..128))
    MAX-ACCESS  read-write
    STATUS  current
    DESCRIPTION
        "The Host certificate file name."
    ::= { agTransfer 16 }
    
agTransferHostKeyFileName OBJECT-TYPE
    SYNTAX  DisplayString (SIZE(0..128))
    MAX-ACCESS  read-write
    STATUS  current
    DESCRIPTION
        "The Host private key file name."
    ::= { agTransfer 17 }

agTransferProtocol OBJECT-TYPE
    SYNTAX INTEGER {
        tftp(1),
        ftp(2),
        sftp(3)
        }
    MAX-ACCESS  read-write
    STATUS  current
    DESCRIPTION
        "The protocol used by this transfer."
    ::= { agTransfer 18 }

agServerPort OBJECT-TYPE
    SYNTAX INTEGER {
        tftp(69),
        ftp(21),
        sftp(22)
        }
    MAX-ACCESS  read-write
    STATUS  current
    DESCRIPTION
        "The port is listened on the server."
    ::= { agTransfer 19 }


agTransferPublicKeyUserName  OBJECT-TYPE
    SYNTAX  DisplayString (SIZE(0..64))
    MAX-ACCESS  read-write
	STATUS  current
	DESCRIPTION
	    "The user of the public key file."
	::= { agTransfer 21 }
	
agTransferPublicKeyFileName  OBJECT-TYPE
    SYNTAX  DisplayString (SIZE(0..128))
    MAX-ACCESS  read-write
    STATUS  current
    DESCRIPTION
        "The client pulic key file name."
    ::= { agTransfer 22 }



-- Agent Port Table

agPortTableMaxEnt OBJECT-TYPE
    SYNTAX  Integer32
    MAX-ACCESS  read-only
    STATUS  current
    DESCRIPTION
        "The maximum number of rows in the port configuration host table."
    ::= { agPortConfig 1 }

agPortCurCfgTable OBJECT-TYPE
    SYNTAX  SEQUENCE OF AgPortCurCfgTableEntry
    MAX-ACCESS  not-accessible
    STATUS  current
    DESCRIPTION
        "The table of port configuration in the current configuration block."
    ::= { agPortConfig 2 }

agPortCurCfgTableEntry OBJECT-TYPE
    SYNTAX  AgPortCurCfgTableEntry
    MAX-ACCESS  not-accessible
    STATUS  current
    DESCRIPTION
        "A row in the port table in the current configuration block."
    INDEX   { agPortCurCfgIndx }
    ::= { agPortCurCfgTable 1 }

AgPortCurCfgTableEntry ::= SEQUENCE {
    agPortCurCfgIndx             PortNumber,
    agPortCurCfgState            INTEGER,
    agPortCurCfgVlanTag          INTEGER,
    agPortCurCfgRmon             INTEGER,
    agPortCurCfgPVID             Integer32,
    agPortCurCfgGigEthAutoNeg    INTEGER,
    agPortCurCfgGigEthFctl       INTEGER,
    agPortCurCfgLinkTrap         INTEGER,
    agPortCurCfgGigEthSpeed      INTEGER,
    agPortCurCfgGigEthMode       INTEGER,

    agPortCurCfgDscpRemarking    INTEGER,
    agPortCurCfgTagPVID          INTEGER,
    agPortCurCfgMulticastThreshold         INTEGER,
    agPortCurCfgMulticastThresholdRate     INTEGER,
    agPortCurCfgBroadcastThreshold         INTEGER,
    agPortCurCfgBroadcastThresholdRate     INTEGER,
    agPortCurCfgDLFThreshold               INTEGER,
    agPortCurCfgDLFThresholdRate           INTEGER,
    agPortCurCfgPortAlias        DisplayString,
    agPortCurCfgPortName         DisplayString
   ,agPortCurCfgLearning         INTEGER
   ,agPortCurCfgFloodBlocking    INTEGER
   ,agPortCurCfgType             DisplayString
   ,agPortCurCfgLinkType         INTEGER
   ,agPortCurCfgEdge             INTEGER
   ,agPortCurCfgErrDisableRecovery        INTEGER
   ,agPortCurCfgUdld             INTEGER
   ,agPortCurCfgUdldMode         INTEGER
   ,agPortCurCfgOam              INTEGER
   ,agPortCurCfgOamMode          INTEGER
   ,agPortCurCfgBpduGuard        INTEGER
   ,agPortCurCfgMacAddrNotif     INTEGER
   ,agPortCurCfgStpExtGuard      INTEGER
   ,agPortCurCfgLFDStatus       INTEGER
	,agPortCurCfgPrivateVlanStatus       INTEGER
	,agPortCurCfgMappedPrimaryVlans      OCTET STRING
	,agPortCurCfgAssociatedSecondaryVlans OCTET STRING
    }

agPortCurCfgIndx OBJECT-TYPE
    SYNTAX  PortNumber
    MAX-ACCESS  read-only
    STATUS  current
    DESCRIPTION
        "The index of the row in port configurations table."
    ::= { agPortCurCfgTableEntry 1 }

agPortCurCfgState OBJECT-TYPE
    SYNTAX  INTEGER {
        enabled(2),
        disabled(3)
	}
    MAX-ACCESS  read-only
    STATUS  current
    DESCRIPTION
        "This is the state of the port."
    ::= { agPortCurCfgTableEntry 2 }

agPortCurCfgVlanTag OBJECT-TYPE
    SYNTAX  INTEGER {
        tagged(2),
        untagged(3)
        }
    MAX-ACCESS  read-only
    STATUS  current
    DESCRIPTION
        "This is VLAN tag state of the port"
    ::= { agPortCurCfgTableEntry 3 }


agPortCurCfgRmon OBJECT-TYPE
    SYNTAX  INTEGER {
        on(2),
        off(3)
        }
    MAX-ACCESS  read-only
    STATUS  current
    DESCRIPTION
        "This object is used to turn RMON on or off on the port."
   ::= { agPortCurCfgTableEntry 5 }

agPortCurCfgPVID OBJECT-TYPE
    SYNTAX  Integer32
    MAX-ACCESS  read-only
    STATUS  current
    DESCRIPTION
        "The default VLAN ID for the port.
        "
    ::= { agPortCurCfgTableEntry 6 }


agPortCurCfgGigEthAutoNeg OBJECT-TYPE
    SYNTAX  INTEGER {
        on(2),
        off(3)
        }
    MAX-ACCESS  read-only
    STATUS  current
    DESCRIPTION
        "This object is used to turn the autonegotiation on or off
         for gigabit Ethernet connection."
    ::= { agPortCurCfgTableEntry 11 }

agPortCurCfgGigEthFctl OBJECT-TYPE
    SYNTAX  INTEGER {
        transmit(2),
        receive(3),
        both(4),
        none(5)
        }
    MAX-ACCESS  read-only
    STATUS  current
    DESCRIPTION
        "This object is used to select port flow control for
         gigabit Ethernet connection."
    ::= { agPortCurCfgTableEntry 12 }

agPortCurCfgPortName	OBJECT-TYPE
    SYNTAX  DisplayString (SIZE(0..63))
    MAX-ACCESS  read-only
    STATUS  current
    DESCRIPTION
        "The switch port name."
    ::= { agPortCurCfgTableEntry 13 }



agPortCurCfgLinkTrap OBJECT-TYPE
    SYNTAX  INTEGER {
	enabled(1),
	disabled(2)
    }
    MAX-ACCESS  read-only
    STATUS  current
    DESCRIPTION
        "Indicates whether linkUp/linkDown traps should be
        generated for this interface.

        By default, this object should have the value
        enabled(1) for interfaces which do not operate on
        'top' of any other interface (as defined in the
        ifStackTable), and disabled(2) otherwise."
    ::= { agPortCurCfgTableEntry 16 }




agPortCurCfgGigEthSpeed OBJECT-TYPE
    SYNTAX  INTEGER {
        mbs10(2),
        mbs100(3),
        any(4),
        mbs1000(5)
	,
        mbs10000(6)
        ,
        mbs40000(7)
        }
    MAX-ACCESS  read-only
    STATUS  current
    DESCRIPTION
        "Selects the port speed for Gigabit Ethernet connection."
    ::= { agPortCurCfgTableEntry 21 }

agPortCurCfgGigEthMode OBJECT-TYPE
    SYNTAX  INTEGER {
        full-duplex(2),
        half-duplex(3),
        any(4)
        }
    MAX-ACCESS  read-only
    STATUS  current
    DESCRIPTION
        "This object is used to select port mode for Gigabit Ethernet connection."
    ::= { agPortCurCfgTableEntry 22 }

agPortCurCfgDscpRemarking OBJECT-TYPE
    SYNTAX  INTEGER {
        enabled(1),
        disabled(2)
        }
    MAX-ACCESS  read-only
    STATUS  current
    DESCRIPTION
        "Enable or disable Dscp remarking for the switch port."
    ::= { agPortCurCfgTableEntry 23 }

agPortCurCfgPortAlias    OBJECT-TYPE
    SYNTAX  DisplayString (SIZE(0..15))
    MAX-ACCESS  read-only
    STATUS  current
    DESCRIPTION
        "The switch port alias."
    ::= { agPortCurCfgTableEntry 24 }

agPortCurCfgTagPVID OBJECT-TYPE
    SYNTAX  INTEGER {
        tagged(2),
        untagged(3)
        }
    MAX-ACCESS  read-only
    STATUS  current
    DESCRIPTION
        "This is PVID tag state of the port"
    ::= { agPortCurCfgTableEntry 25 }

agPortCurCfgLearning OBJECT-TYPE
    SYNTAX  INTEGER {
        enabled(1),
        disabled(2)
        }
    MAX-ACCESS  read-only
    STATUS  current
    DESCRIPTION
        "Enable or disable L2 (FDB) Learning for the switch port."
    ::= { agPortCurCfgTableEntry 26 }

agPortCurCfgFloodBlocking OBJECT-TYPE
    SYNTAX  INTEGER {
        enabled(1),
        disabled(2)
        }
    MAX-ACCESS  read-only
    STATUS  current
    DESCRIPTION
        "Enable or disable flood blocking for the switch port."
    ::= { agPortCurCfgTableEntry 27 }


agPortCurCfgType OBJECT-TYPE
    SYNTAX  DisplayString (SIZE(0..7))
    MAX-ACCESS  read-only
    STATUS  current
    DESCRIPTION
        "The switch port type."
    ::= { agPortCurCfgTableEntry 29 }


agPortCurCfgLinkType OBJECT-TYPE
    SYNTAX INTEGER {
        auto(1),
        p2p(2),
        shared(3)
        }
    MAX-ACCESS read-only
    STATUS current
    DESCRIPTION
        "The type of port connection. (for PVRST only)"
    ::= { agPortCurCfgTableEntry 30 }

agPortCurCfgEdge OBJECT-TYPE
    SYNTAX INTEGER {
        enabled(1),
        disabled(2)
        }
    MAX-ACCESS read-only
    STATUS current
    DESCRIPTION
        "The state of port edge."
    ::= { agPortCurCfgTableEntry 31 }





agPortCurCfgErrDisableRecovery OBJECT-TYPE
    SYNTAX      INTEGER {
                    enable(1),
                    disable(2)
                }
    MAX-ACCESS  read-only
    STATUS      current
    DESCRIPTION
        "This object indicates whether the system will automatically
         re-enable this port if it becomes error-disabled. This port
         will be re-enabled after the time interval specified by the
         agCurCfgErrDisableTimeout object has elapsed.

         A port is in error-disabled state when it is operationally
         disabled due to abnormal conditions detected on the port.

         If this port is error-disabled, it will only be re-enabled
         by the system if the agCurCfgErrDisableRecovery object and
         this object both have a value of 'enable(1)'."
    DEFVAL      { enable }
    ::= { agPortCurCfgTableEntry 35 }


agPortCurCfgUdld OBJECT-TYPE
    SYNTAX  INTEGER {
        enabled(1),
        disabled(2)
        }
    MAX-ACCESS  read-only
    STATUS  current
    DESCRIPTION
        "Enable or disable UDLD for the switch port."
    ::= { agPortCurCfgTableEntry 37 }

agPortCurCfgUdldMode OBJECT-TYPE
    SYNTAX  INTEGER {
        normal(1),
        aggressive(2)
        }
    MAX-ACCESS  read-only
    STATUS  current
    DESCRIPTION
        "Enable or disable UDLD mode for the switch port."
    ::= { agPortCurCfgTableEntry 38 }


agPortCurCfgOam OBJECT-TYPE
    SYNTAX  INTEGER {
        enabled(1),
        disabled(2)
        }
    MAX-ACCESS  read-only
    STATUS  current
    DESCRIPTION
        "Enable or disable OAM Discovery process for the switch port."
    ::= { agPortCurCfgTableEntry 39 }

agPortCurCfgOamMode OBJECT-TYPE
    SYNTAX  INTEGER {
        active(1),
        passive(2)
        }
    MAX-ACCESS  read-only
    STATUS  current
    DESCRIPTION
        "Enable or disable OAM mode for the switch port."
    ::= { agPortCurCfgTableEntry 40 }


agPortCurCfgBpduGuard OBJECT-TYPE
    SYNTAX INTEGER {
        enabled(1),
        disabled(2)
        }
    MAX-ACCESS read-only
    STATUS current
    DESCRIPTION
        "Enable or disable BPDU guard for the switch port."
    ::= { agPortCurCfgTableEntry 41 }


agPortCurCfgMulticastThreshold OBJECT-TYPE
    SYNTAX  INTEGER {
        enabled(1),
        disabled(2)
        }
    MAX-ACCESS  read-only
    STATUS  current
    DESCRIPTION
        "Current status of the port's Multicast Threshold."
    ::= { agPortCurCfgTableEntry 42 }

agPortCurCfgMulticastThresholdRate OBJECT-TYPE
    SYNTAX  INTEGER
    MAX-ACCESS  read-only
    STATUS  current
    DESCRIPTION
        "Current port's Multicast Threshold Rate."
    ::= { agPortCurCfgTableEntry 43 }

agPortCurCfgBroadcastThreshold OBJECT-TYPE
    SYNTAX  INTEGER {
        enabled(1),
        disabled(2)
        }
    MAX-ACCESS  read-only
    STATUS  current
    DESCRIPTION
        "Current status of the port's Broadcast Threshold."
    ::= { agPortCurCfgTableEntry 44 }

agPortCurCfgBroadcastThresholdRate OBJECT-TYPE
    SYNTAX  INTEGER
    MAX-ACCESS  read-only
    STATUS  current
    DESCRIPTION
        "Current port's Broadcast Threshold Rate."
    ::= { agPortCurCfgTableEntry 45 }

agPortCurCfgDLFThreshold OBJECT-TYPE
    SYNTAX  INTEGER {
        enabled(1),
        disabled(2)
        }
    MAX-ACCESS  read-only
    STATUS  current
    DESCRIPTION
        "Current status of the port's Destination Lookup Fail Threshold."
    ::= { agPortCurCfgTableEntry 46 }

agPortCurCfgDLFThresholdRate OBJECT-TYPE
    SYNTAX  INTEGER
    MAX-ACCESS  read-only
    STATUS  current
    DESCRIPTION
        "Current port's Destination Lookup Fail Threshold Rate."
    ::= { agPortCurCfgTableEntry 47 }

agPortCurCfgMacAddrNotif OBJECT-TYPE
    SYNTAX  INTEGER{
        enabled(2),
        disabled(3)
	}
    MAX-ACCESS  read-only
    STATUS  current
    DESCRIPTION
        "This is the state of the MAC address notification
         syslog messages on the port."
    ::= { agPortCurCfgTableEntry 48 }




agPortCurCfgStpExtGuard OBJECT-TYPE
    SYNTAX  INTEGER {
        loop(1),
        root(2),
        none(3),
        default(0)
        }
    MAX-ACCESS  read-only
    STATUS  current
    DESCRIPTION
        "Current state for spanning tree guard type"
    ::= { agPortCurCfgTableEntry 52 }
    
agPortCurCfgLFDStatus OBJECT-TYPE
    SYNTAX      INTEGER {
                    enable(1),
                    disable(2)
                }
    MAX-ACCESS  read-only
    STATUS      current
    DESCRIPTION
        "This object indicates whether the system will put this port
         in an error-disabled state due to excessive link flaps.

         A port will be put in an error-disabled state due to 
         excessive link flaps if this object and the global
         agCurCfgLFDStatus object both have a value of 'enable'.
         A port has an excessive number of link flaps if the number
         of link flaps detected during a time period in seconds
         indicated by agCurCfgLFDTime exceeds the maximum number of
         allowed flaps indicated by agCurCfgLFDFlaps."
    DEFVAL      { enable }
    ::= { agPortCurCfgTableEntry 53 }






agPortCurCfgPrivateVlanStatus  OBJECT-TYPE
	SYNTAX  INTEGER {
		enable(1),
		disable(2)
	    }
	MAX-ACCESS  read-only
	STATUS  current
	DESCRIPTION
		"Current state of Private VLAN on this port"
	::= { agPortCurCfgTableEntry  61 }
	
agPortCurCfgMappedPrimaryVlans  OBJECT-TYPE
	SYNTAX  OCTET STRING
	MAX-ACCESS  read-only
	STATUS  current
        DESCRIPTION
	"Primary VLAN list mapped to port.
	in receiving order:
	     OCTET 1  OCTET 2  .....
             xxxxxxxx xxxxxxxx ..... 
             ||    || |_ vlan 8
             ||    ||  
             ||    ||___ vlan 7
             ||    |____ vlan 6
             ||      .    .   .
             ||_________ vlan 1
             |__________ reserved

         where x : 1 - The represented primary VLAN associated to the port
		   0 - The represented primary VLAN does not associated to the port"
	::= { agPortCurCfgTableEntry  62 }
	
agPortCurCfgAssociatedSecondaryVlans  OBJECT-TYPE
	SYNTAX  OCTET STRING
	MAX-ACCESS  read-only
	STATUS  current
        DESCRIPTION
	"Secondary VLAN list associated to port.
	in receiving order:
	     OCTET 1  OCTET 2  .....
             xxxxxxxx xxxxxxxx ..... 
             ||    || |_ vlan 8
             ||    ||  
             ||    ||___ vlan 7
             ||    |____ vlan 6
             ||      .    .   .
             ||_________ vlan 1
             |__________ reserved

         where x : 1 - The represented secondary VLAN associated to the port
		   0 - The represented secondary VLAN does not be associated to the port"
	::= { agPortCurCfgTableEntry  63 }

agPortNewCfgTable OBJECT-TYPE
    SYNTAX  SEQUENCE OF AgPortNewCfgTableEntry
    MAX-ACCESS  not-accessible
    STATUS  current
    DESCRIPTION
        "The table of port configuration in the new configuration block."
    ::= { agPortConfig 3 }

agPortNewCfgTableEntry OBJECT-TYPE
    SYNTAX  AgPortNewCfgTableEntry
    MAX-ACCESS  not-accessible
    STATUS  current
    DESCRIPTION
        "A row in the port configuration table in the new configuration block."
    INDEX   { agPortNewCfgIndx }
    ::= { agPortNewCfgTable 1 }

AgPortNewCfgTableEntry ::= SEQUENCE {
    agPortNewCfgIndx             PortNumber,
    agPortNewCfgState            INTEGER,
    agPortNewCfgVlanTag          INTEGER,
    agPortNewCfgRmon             INTEGER,
    agPortNewCfgPVID             Integer32,
    agPortNewCfgGigEthAutoNeg    INTEGER,
    agPortNewCfgGigEthFctl       INTEGER,
    agPortNewCfgLinkTrap         INTEGER,
    agPortNewCfgGigEthSpeed      INTEGER,
    agPortNewCfgGigEthMode       INTEGER,
    agPortNewCfgDscpRemarking    INTEGER,
    agPortNewCfgTagPVID          INTEGER,
    agPortNewCfgMulticastThreshold        INTEGER,
    agPortNewCfgMulticastThresholdRate     INTEGER,
    agPortNewCfgBroadcastThreshold         INTEGER,
    agPortNewCfgBroadcastThresholdRate     INTEGER,
    agPortNewCfgDLFThreshold               INTEGER,
    agPortNewCfgDLFThresholdRate           INTEGER,
    agPortNewCfgPortName         DisplayString
   ,agPortNewCfgLearning         INTEGER
   ,agPortNewCfgFloodBlocking    INTEGER
   ,agPortNewCfgType             DisplayString
   ,agPortNewCfgLinkType         INTEGER
   ,agPortNewCfgEdge             INTEGER
   ,agPortNewCfgErrDisableRecovery INTEGER
   ,agPortNewCfgUdld             INTEGER
   ,agPortNewCfgUdldMode         INTEGER
   ,agPortNewCfgOam              INTEGER
   ,agPortNewCfgOamMode          INTEGER
   ,agPortNewCfgBpduGuard        INTEGER
   ,agPortNewCfgMacAddrNotif     INTEGER

   ,agPortNewCfgStpExtGuard      INTEGER
   ,agPortNewCfgLFDStatus        INTEGER
	,agPortNewCfgPrivateVlanStatus  INTEGER
	,agPortNewCfgMappedPrimaryVlans      OCTET STRING
        ,agPortNewCfgAddPrimaryVlan     Unsigned32
        ,agPortNewCfgDelPrimaryVlan     Unsigned32
	,agPortNewCfgAssociatedSecondaryVlans OCTET STRING
        ,agPortNewCfgAddSecondaryVlan   Unsigned32
        ,agPortNewCfgDelSecondaryVlan   Unsigned32
    }

agPortNewCfgIndx OBJECT-TYPE
    SYNTAX  PortNumber
    MAX-ACCESS  read-only
    STATUS  current
    DESCRIPTION
        "The index of the row in port configurations table."
    ::= { agPortNewCfgTableEntry 1 }

agPortNewCfgState OBJECT-TYPE
    SYNTAX  INTEGER {
        enabled(2),
        disabled(3)
        }
    MAX-ACCESS  read-write
    STATUS  current
    DESCRIPTION
        "This is the state of the port."
    ::= { agPortNewCfgTableEntry 2 }

agPortNewCfgVlanTag OBJECT-TYPE
    SYNTAX  INTEGER {
        tagged(2),
        untagged(3)
        }
    MAX-ACCESS  read-write
    STATUS  current
    DESCRIPTION
        "This is VLAN tag state of the port"
    ::= { agPortNewCfgTableEntry 3 }


agPortNewCfgRmon OBJECT-TYPE
    SYNTAX  INTEGER {
        on(2),
        off(3)
        }
    MAX-ACCESS  read-write
    STATUS  current
    DESCRIPTION
        "This object is used to turn RMON on or off on the port."
    ::= { agPortNewCfgTableEntry 5 }

agPortNewCfgPVID OBJECT-TYPE
    SYNTAX  Integer32
    MAX-ACCESS  read-write
    STATUS  current
    DESCRIPTION
        "The default VLAN ID for the port.
        "
    ::= { agPortNewCfgTableEntry 6 }


agPortNewCfgGigEthAutoNeg OBJECT-TYPE
    SYNTAX  INTEGER {
        on(2),
        off(3)
        }
    MAX-ACCESS  read-write
    STATUS  current
    DESCRIPTION
        "This object is used to turn the autonegotiation on or off
         for gigabit Ethernet connection."
    ::= { agPortNewCfgTableEntry 11 }

agPortNewCfgGigEthFctl OBJECT-TYPE
    SYNTAX  INTEGER {
        transmit(2),
        receive(3),
        both(4),
        none(5)
       }
    MAX-ACCESS  read-write
    STATUS  current
    DESCRIPTION
        "This object is used to select port flow control for
         gigabit Ethernet connection."
    ::= { agPortNewCfgTableEntry 12 }

agPortNewCfgPortName	OBJECT-TYPE
    SYNTAX  DisplayString (SIZE(0..64))
    MAX-ACCESS  read-write
    STATUS  current
    DESCRIPTION
        "The switch port name."
    ::= { agPortNewCfgTableEntry 13 }



agPortNewCfgLinkTrap OBJECT-TYPE
    SYNTAX  INTEGER {
	enabled(1),
	disabled(2)
    }
    MAX-ACCESS  read-write
    STATUS  current
    DESCRIPTION
        "Indicates whether linkUp/linkDown traps should be
        generated for this interface.

        By default, this object should have the value
        enabled(1) for interfaces which do not operate on
        'top' of any other interface (as defined in the
        ifStackTable), and disabled(2) otherwise."
    ::= { agPortNewCfgTableEntry 16 }




agPortNewCfgGigEthSpeed OBJECT-TYPE
    SYNTAX  INTEGER {
        mbs10(2),
        mbs100(3),
        any(4),
        mbs1000(5)
	,
        mbs10000(6)
        ,
        mbs40000(7)
        }
    MAX-ACCESS  read-write
    STATUS  current
    DESCRIPTION
        "Selects the port speed for Gigabit Ethernet connection."
    ::= { agPortNewCfgTableEntry 21 }

agPortNewCfgGigEthMode OBJECT-TYPE
    SYNTAX  INTEGER {
        full-duplex(2),
        half-duplex(3),
        any(4)
        }
    MAX-ACCESS  read-write
    STATUS  current
    DESCRIPTION
        "This object is used to select port mode for Gigabit Ethernet connection.
        "
    ::= { agPortNewCfgTableEntry 22 }

agPortNewCfgDscpRemarking OBJECT-TYPE
    SYNTAX  INTEGER {
        enabled(1),
        disabled(2)
        }
    MAX-ACCESS  read-write
    STATUS  current
    DESCRIPTION
        "Enable or disable Dscp remarking for the switch port."
    ::= { agPortNewCfgTableEntry 23 }


agPortNewCfgTagPVID OBJECT-TYPE
    SYNTAX  INTEGER {
        tagged(2),
        untagged(3)
        }
    MAX-ACCESS  read-write
    STATUS  current
    DESCRIPTION
        "This is PVID tag state of the port"
    ::= { agPortNewCfgTableEntry 25 }

agPortNewCfgLearning OBJECT-TYPE
    SYNTAX  INTEGER {
        enabled(1),
        disabled(2)
        }
    MAX-ACCESS  read-write
    STATUS  current
    DESCRIPTION
        "Enable or disable L2 (FDB) Learning for the switch port."
    ::= { agPortNewCfgTableEntry 26 }

agPortNewCfgFloodBlocking OBJECT-TYPE
    SYNTAX INTEGER {
	enabled(1),
	disabled(2)
	}
    MAX-ACCESS read-write
    STATUS current
    DESCRIPTION
	"Enable or disable flood blocking for the switch port."
    ::= { agPortNewCfgTableEntry 27 }


agPortNewCfgType OBJECT-TYPE
    SYNTAX  DisplayString (SIZE(0..7))
    MAX-ACCESS  read-only
    STATUS  current
    DESCRIPTION
        "The switch port type."
    ::= { agPortNewCfgTableEntry 29 }


agPortNewCfgLinkType OBJECT-TYPE
    SYNTAX INTEGER {
        auto(1),
        p2p(2),
        shared(3)
        }
    MAX-ACCESS read-create
    STATUS current
    DESCRIPTION
        "The type of port connection. (for PVRST only)"
    ::= { agPortNewCfgTableEntry 30 }

agPortNewCfgEdge OBJECT-TYPE
    SYNTAX INTEGER {
        enabled(1),
        disabled(2)
        }
    MAX-ACCESS read-create
    STATUS current
    DESCRIPTION
        "The state of port edge."
    ::= { agPortNewCfgTableEntry 31 }




agPortNewCfgErrDisableRecovery OBJECT-TYPE
    SYNTAX      INTEGER {
                    enable(1),
                    disable(2)
                }
    MAX-ACCESS  read-write
    STATUS      current
    DESCRIPTION
        "This object specifies whether the system should automatically
         re-enable this port when it becomes error-disabled.  Use this
         object to change the port-level setting of the error-disable
         recovery action."
    DEFVAL      { enable }
    ::= { agPortNewCfgTableEntry 35 }


agPortNewCfgUdld OBJECT-TYPE
    SYNTAX  INTEGER {
        enabled(1),
        disabled(2)
        }
    MAX-ACCESS  read-write
    STATUS  current
    DESCRIPTION
        "Enable or disable UDLD for the switch port."
    ::= { agPortNewCfgTableEntry 37 }

agPortNewCfgUdldMode OBJECT-TYPE
    SYNTAX  INTEGER {
        normal(1),
        aggressive(2)
        }
    MAX-ACCESS  read-write
    STATUS  current
    DESCRIPTION
        "Enable or disable UDLD mode for the switch port."
    ::= { agPortNewCfgTableEntry 38 }


agPortNewCfgOam OBJECT-TYPE
    SYNTAX  INTEGER {
        enabled(1),
        disabled(2)
        }
    MAX-ACCESS  read-write
    STATUS  current
    DESCRIPTION
        "Enable or disable OAM Discovery process for the switch port."
    ::= { agPortNewCfgTableEntry 39 }

agPortNewCfgOamMode OBJECT-TYPE
    SYNTAX  INTEGER {
        active(1),
        passive(2)
        }
    MAX-ACCESS  read-write
    STATUS  current
    DESCRIPTION
        "Enable or disable OAM mode for the switch port."
    ::= { agPortNewCfgTableEntry 40 }


agPortNewCfgBpduGuard OBJECT-TYPE
    SYNTAX INTEGER {
        enabled(1),
        disabled(2)
        }
    MAX-ACCESS read-write
    STATUS current
    DESCRIPTION
        "Enable or disable BPDU guard for the switch port."
    ::= { agPortNewCfgTableEntry 41 }


agPortNewCfgMulticastThreshold OBJECT-TYPE
    SYNTAX  INTEGER {
        enabled(1),
        disabled(2)
        }
    MAX-ACCESS  read-write
    STATUS  current
    DESCRIPTION
        "New status of the port's Multicast Threshold."
    ::= { agPortNewCfgTableEntry 42 }

agPortNewCfgMulticastThresholdRate OBJECT-TYPE
    SYNTAX  INTEGER
    MAX-ACCESS  read-write
    STATUS  current
    DESCRIPTION
        "New port's Multicast Threshold Rate."
    ::= { agPortNewCfgTableEntry 43 }

agPortNewCfgBroadcastThreshold OBJECT-TYPE
    SYNTAX  INTEGER {
        enabled(1),
        disabled(2)
        }
    MAX-ACCESS  read-write
    STATUS  current
    DESCRIPTION
        "New status of the port's Broadcast Threshold."
    ::= { agPortNewCfgTableEntry 44 }

agPortNewCfgBroadcastThresholdRate OBJECT-TYPE
    SYNTAX  INTEGER
    MAX-ACCESS  read-write
    STATUS  current
    DESCRIPTION
        "New port's Broadcast Threshold Rate."
    ::= { agPortNewCfgTableEntry 45 }

agPortNewCfgDLFThreshold OBJECT-TYPE
    SYNTAX  INTEGER {
        enabled(1),
        disabled(2)
        }
    MAX-ACCESS  read-write
    STATUS  current
    DESCRIPTION
        "New status of the port's Destination Lookup Fail Threshold."
    ::= { agPortNewCfgTableEntry 46 }

agPortNewCfgDLFThresholdRate OBJECT-TYPE
    SYNTAX  INTEGER
    MAX-ACCESS  read-write
    STATUS  current
    DESCRIPTION
        "New port's Destination Lookup Fail Threshold Rate."
    ::= { agPortNewCfgTableEntry 47 }

agPortNewCfgMacAddrNotif OBJECT-TYPE
    SYNTAX  INTEGER {
        enabled(2),
        disabled(3)
        }
    MAX-ACCESS  read-write
    STATUS  current
    DESCRIPTION
        "Enables or Disables the MAC address notification
         syslog messages on the port."
    ::= { agPortNewCfgTableEntry 48 }




agPortNewCfgStpExtGuard OBJECT-TYPE
    SYNTAX  INTEGER {
        loop(1),
        root(2),
        none(3),
        default(0)
        }
    MAX-ACCESS  read-write
    STATUS  current
    DESCRIPTION
        "Set spanning tree guard type"
    ::= { agPortNewCfgTableEntry 52 }

agPortNewCfgLFDStatus OBJECT-TYPE
    SYNTAX      INTEGER {
                    enable(1),
                    disable(2)
                }
    MAX-ACCESS  read-write
    STATUS      current
    DESCRIPTION
        "This object indicates whether the system should put this port
         in an error-disabled state due to excessive link flaps.
         Use this object to change the port setting of the Link Flap
         Dampening error-disable action."
    DEFVAL      { enable }
    ::= { agPortNewCfgTableEntry 53 }






agPortNewCfgPrivateVlanStatus  OBJECT-TYPE
	SYNTAX  INTEGER {
		enable(1),
		disable(2)
}
	MAX-ACCESS  read-write
	STATUS  current
	DESCRIPTION
		"Enable or disable the Private VLAN on this port"
	::= { agPortNewCfgTableEntry  61 }
	
agPortNewCfgMappedPrimaryVlans  OBJECT-TYPE
	SYNTAX  OCTET STRING
	MAX-ACCESS  read-only
	STATUS  current
        DESCRIPTION
	"Primary VLAN list mapped to port.
	in receiving order:
	     OCTET 1  OCTET 2  .....
             xxxxxxxx xxxxxxxx ..... 
             ||    || |_ vlan 8
             ||    ||  
             ||    ||___ vlan 7
             ||    |____ vlan 6
             ||      .    .   .
             ||_________ vlan 1
             |__________ reserved

         where x : 1 - The represented primary VLAN associate to the port
		   0 - The represented primary VLAN does not associate to the port"
	::= { agPortNewCfgTableEntry  62 }

agPortNewCfgAddPrimaryVlan OBJECT-TYPE
     SYNTAX  Unsigned32
     MAX-ACCESS  read-write
     STATUS  current
     DESCRIPTION
         "Adds the port to the specified primary VLAN.  A '0' value is 
          returned when read."
     ::= { agPortNewCfgTableEntry 63 }

agPortNewCfgDelPrimaryVlan OBJECT-TYPE
     SYNTAX  Unsigned32
     MAX-ACCESS  read-write
     STATUS  current
     DESCRIPTION
         "Removes the port from the specified primary VLAN.  A '0' value is 
          returned when read."
     ::= { agPortNewCfgTableEntry 64 }
	
agPortNewCfgAssociatedSecondaryVlans  OBJECT-TYPE
	SYNTAX  OCTET STRING
	MAX-ACCESS  read-only
	STATUS  current
        DESCRIPTION
	"Secondary VLAN list associated to port.
	in receiving order:
	     OCTET 1  OCTET 2  .....
             xxxxxxxx xxxxxxxx ..... 
             ||    || |_ vlan 8
             ||    ||  
             ||    ||___ vlan 7
             ||    |____ vlan 6
             ||      .    .   .
             ||_________ vlan 1
             |__________ reserved

         where x : 1 - The represented secondary VLAN associated to the port
		   0 - The represented secondary VLAN does not be associated to the port"
	::= { agPortNewCfgTableEntry  65 }

agPortNewCfgAddSecondaryVlan OBJECT-TYPE
     SYNTAX  Unsigned32
     MAX-ACCESS  read-write
     STATUS  current
     DESCRIPTION
         "Adds the port to the specified secondary VLAN.  A '0' value is 
          returned when read."
     ::= { agPortNewCfgTableEntry 66 }

agPortNewCfgDelSecondaryVlan OBJECT-TYPE
     SYNTAX  Unsigned32
     MAX-ACCESS  read-write
     STATUS  current
     DESCRIPTION
         "Removes the port from the secondary VLAN.  A '0' value is 
          returned when read."
     ::= { agPortNewCfgTableEntry 67 }

-- Agent Fast Forwarding Port Table

-- Agent Fast Forwarding Port Table


-- SSH Configuration
sshCurCfgScpAdm OBJECT-TYPE
    SYNTAX DisplayString(SIZE(0..128))
    MAX-ACCESS  read-only
    STATUS  current
    DESCRIPTION
        "SCP-only admin password."
    ::= { agSSHConfig 3 }

sshNewCfgScpAdm OBJECT-TYPE
    SYNTAX DisplayString(SIZE(0..128))
    MAX-ACCESS  read-write
    STATUS  current
    DESCRIPTION
        "Set SCP-only admin password."
    ::= { agSSHConfig 4 }

sshNewCfgHKeyGen OBJECT-TYPE
    SYNTAX INTEGER {
        generate(1),
        other(2)
        }
    MAX-ACCESS  read-write
    STATUS  current
    DESCRIPTION
        "This is an action object to generate the RSA host key.
         other(2) is returned always when read.
         The following values are writable: generate(1).. Generate the RSA host key."
    ::= { agSSHConfig 5 }

sshCurCfgSSHPort OBJECT-TYPE
    SYNTAX INTEGER (1..65535)
    MAX-ACCESS  read-only
    STATUS  current
    DESCRIPTION
        "SSH server port number."
    ::= { agSSHConfig 7 }

sshNewCfgSSHPort OBJECT-TYPE
    SYNTAX INTEGER (1..65535)
    MAX-ACCESS  read-write
    STATUS  current
    DESCRIPTION
        "Set SSH server port number."
    ::= { agSSHConfig 8 }

sshCurCfgScpApplySave OBJECT-TYPE
    SYNTAX INTEGER {
        enabled(1),
        disabled(2)
        }
    MAX-ACCESS  read-only
    STATUS  current
    DESCRIPTION
        "SCP apply and save."
    ::= { agSSHConfig 9 }

sshNewCfgScpApplySave OBJECT-TYPE
    SYNTAX INTEGER {
        enabled(1),
        disabled(2)
        }
    MAX-ACCESS  read-write
    STATUS  current
    DESCRIPTION
        "Enable/Disable the SCP apply and save."
    ::= { agSSHConfig 10 }

sshCurCfgStatus OBJECT-TYPE
    SYNTAX INTEGER {
        on(1),
        off(2)
        }
    MAX-ACCESS  read-only
    STATUS  current
    DESCRIPTION
        "SSH server status."
    ::= { agSSHConfig 11 }

sshNewCfgStatus OBJECT-TYPE
    SYNTAX INTEGER {
        on(1),
        off(2)
        }
    MAX-ACCESS  read-write
    STATUS  current
    DESCRIPTION
        "Turn SSH server ON/OFF."
    ::= { agSSHConfig 12 }
	

sshPubKeyRemAll OBJECT-TYPE
    SYNTAX INTEGER {
        other(1),
        delete(2)
        }
    MAX-ACCESS  read-write
    STATUS  current
    DESCRIPTION
        "Remove all the public key entries on switch."
    ::= { agSSHConfig 13 }
	
sshPubKeyRemUser OBJECT-TYPE
    SYNTAX DisplayString(SIZE(0..64))
    MAX-ACCESS  read-write
    STATUS  current
    DESCRIPTION
        "Remove a specific username from the public key database."
    ::= { agSSHConfig 14 }

sshPubKeyConfigTable OBJECT-TYPE
    SYNTAX  SEQUENCE OF SshPubKeyConfigEntry
    MAX-ACCESS  not-accessible
    STATUS  current
    DESCRIPTION
        "The table for ssh public keys and its users."
    ::= { agSSHConfig 15 }

sshPubKeyConfigEntry OBJECT-TYPE
    SYNTAX  SshPubKeyConfigEntry
    MAX-ACCESS  not-accessible
    STATUS  current
    DESCRIPTION
         "A row in the ssh public keys tables."
    INDEX    { sshPubKeyConfigIndex }
    ::= { sshPubKeyConfigTable 1 }

SshPubKeyConfigEntry ::= SEQUENCE {
    sshPubKeyConfigIndex     Integer32,
    sshPubKeyType            INTEGER,
    sshPubKeyHashValue       OCTET STRING,
    sshPubkeyUserBmap        OCTET STRING,
    sshPubKeyAddUser         DisplayString (SIZE(0..64)),
    sshPubKeyDelUser         DisplayString (SIZE(0..64)),
    sshPubKeyRemEntry        INTEGER
}

sshPubKeyConfigIndex OBJECT-TYPE
    SYNTAX Integer32
    MAX-ACCESS  read-only
    STATUS  current
    DESCRIPTION
        "The index of the ssh public key entry."
    ::= { sshPubKeyConfigEntry 1 }

sshPubKeyType OBJECT-TYPE
    SYNTAX INTEGER{
        rsa(1),
        dsa(2)
	}
	MAX-ACCESS  read-only
    STATUS  current
    DESCRIPTION
        "Specify the type of the public key."
    ::= { sshPubKeyConfigEntry 2 }

sshPubKeyHashValue OBJECT-TYPE
    SYNTAX OCTET STRING
    MAX-ACCESS  read-only
    STATUS  current
    DESCRIPTION
        "The hash value of a specific public key."
    ::= { sshPubKeyConfigEntry 3 }
	
sshPubkeyUserBmap OBJECT-TYPE
    SYNTAX  OCTET STRING
    MAX-ACCESS  read-only
    STATUS  current
    DESCRIPTION
        "The user list in the key entry. The user are presented in bitmap format.
        as follows:
        
        OCTET 1    OCTET 2    OCTET 3   OCTET 4
        xxxx xxxx xxxx xxxx   xxxx xxxx xxxx xxxx 
        ||   |                   | |||| ||________    oper
        ||   |                   | |||| |_________    user
        ||   |                   | ||||___________    admin
        ||   |                   | |||____________    maint
        ||   |                   | ||_____________    scpadmin
        ||   |                   | |______________    support
        ||   |                   |
        ||   |                   |________________ user defined 20
        ||   |
        ||   |   ...................
        ||   |______ user defined 5
        ||..........
        ||..........
        ||_________ user defined 2
        |__________ default user defined 1: USERID
        
        Bit On  - The represented user belongs to the key entry
        Bit Off - The represented user does not belong to the key entry
        Bit 0-19  represent the 20 user-defined users(uid=BitNUM+1),
                  more details can be found in agAccess->agAccessUserCurCfgTable.
        Bit 20-25  represent the 6 pre-defined user(from support to oper)."
    ::= { sshPubKeyConfigEntry 4 }
	
sshPubKeyAddUser OBJECT-TYPE
    SYNTAX  DisplayString (SIZE(0..64))
    MAX-ACCESS  read-write
    STATUS  current
    DESCRIPTION
        "Add a new user to a particular public key.
         Reminder: The user must be a valid system user."
    ::= { sshPubKeyConfigEntry 5 }

sshPubKeyDelUser OBJECT-TYPE
    SYNTAX  DisplayString (SIZE(0..64))
    MAX-ACCESS  read-write
    STATUS  current
    DESCRIPTION
        "Remove a user from the user list of the public key entry."
    ::= { sshPubKeyConfigEntry 6 }
	
sshPubKeyRemEntry OBJECT-TYPE
    SYNTAX  INTEGER{
        other(1),
        delete(2)
	}
    MAX-ACCESS  read-write
    STATUS  current
    DESCRIPTION
        "Remove a public key entry."
    ::= { sshPubKeyConfigEntry 7 }

sshCurCfgSSHAttempts OBJECT-TYPE
    SYNTAX INTEGER (1..20)
    MAX-ACCESS  read-only
    STATUS  current
    DESCRIPTION
        "SSH server maximum authentication attempts."
    ::= { agSSHConfig 16 }

sshNewCfgSSHAttempts OBJECT-TYPE
    SYNTAX INTEGER (1..20)
    MAX-ACCESS  read-write
    STATUS  current
    DESCRIPTION
        "Set SSH server maximum authentication attempts."
    ::= { agSSHConfig 17 }



-- RADIUS Configuration

radCurCfgPrimaryServer OBJECT-TYPE
    SYNTAX  IpAddress
    MAX-ACCESS  read-only
    STATUS  current
    DESCRIPTION
        "The IP address of the Primary RADIUS server."
    ::= { agRadiusConfig 1 }

radNewCfgPrimaryServer OBJECT-TYPE
    SYNTAX  IpAddress
    MAX-ACCESS  read-write
    STATUS  current
    DESCRIPTION
        "The IP address of the Primary RADIUS server."
    ::= { agRadiusConfig 2 }

radCurCfgSecondaryServer OBJECT-TYPE
    SYNTAX  IpAddress
    MAX-ACCESS  read-only
    STATUS  current
    DESCRIPTION
        "The IP address of the Secondary RADIUS server."
    ::= { agRadiusConfig 3 }

radNewCfgSecondaryServer OBJECT-TYPE
    SYNTAX  IpAddress
    MAX-ACCESS  read-write
    STATUS  current
    DESCRIPTION
        "The IP address of the Secondary RADIUS server."
    ::= { agRadiusConfig 4 }

radCurCfgPort OBJECT-TYPE
    SYNTAX  INTEGER  (1500..3000)
    MAX-ACCESS  read-only
    STATUS  current
    DESCRIPTION
        "Specify the RADIUS port number."
    ::= { agRadiusConfig 5 }

radNewCfgPort OBJECT-TYPE
    SYNTAX  INTEGER  (1500..3000)
    MAX-ACCESS  read-write
    STATUS  current
    DESCRIPTION
        "Specify the RADIUS port number."
    ::= { agRadiusConfig 6 }

radCurCfgTimeout OBJECT-TYPE
    SYNTAX  INTEGER  (1..10)
    MAX-ACCESS  read-only
    STATUS  current
    DESCRIPTION
        "The maximum number of seconds before resending authentication
         to RADIUS server."
    ::= { agRadiusConfig 7 }

radNewCfgTimeout OBJECT-TYPE
    SYNTAX  INTEGER  (1..10)
    MAX-ACCESS  read-write
    STATUS  current
    DESCRIPTION
        "The maximum number of seconds before resending authentication
         to RADIUS server."
    ::= { agRadiusConfig 8 }

radCurCfgRetries OBJECT-TYPE
    SYNTAX  INTEGER  (1..3)
    MAX-ACCESS  read-only
    STATUS  current
    DESCRIPTION
        "Number of retries to the RADIUS server."
    ::= { agRadiusConfig 9 }

radNewCfgRetries OBJECT-TYPE
    SYNTAX  INTEGER  (1..3)
    MAX-ACCESS  read-write
    STATUS  current
    DESCRIPTION
        "Number of retries to the RADIUS server."
    ::= { agRadiusConfig 10 }

radCurCfgState OBJECT-TYPE
    SYNTAX  INTEGER {
        enabled(1),
        disabled(0)
        }
    MAX-ACCESS  read-only
    STATUS  current
    DESCRIPTION
        "Enable or disable RADIUS authentication."
    ::= { agRadiusConfig 11 }

radNewCfgState OBJECT-TYPE
    SYNTAX  INTEGER {
        enabled(1),
        disabled(0)
        }
    MAX-ACCESS  read-write
    STATUS  current
    DESCRIPTION
        "Enable or disable RADIUS authentication."
    ::= { agRadiusConfig 12 }

radCurCfgAuthenString OBJECT-TYPE
    SYNTAX  DisplayString (SIZE(0..32))
    MAX-ACCESS  read-only
    STATUS  current
    DESCRIPTION
        "The RADIUS authentication string."
    ::= { agRadiusConfig 13 }

radNewCfgAuthenString OBJECT-TYPE
    SYNTAX  DisplayString (SIZE(0..32))
    MAX-ACCESS  read-write
    STATUS  current
    DESCRIPTION
        "The RADIUS authentication string."
    ::= { agRadiusConfig 14 }

radCurCfgBackdoor OBJECT-TYPE
    SYNTAX  INTEGER {
        enabled(1),
        disabled(2)
        }
    MAX-ACCESS  read-only
    STATUS  current
    DESCRIPTION
        "Enable or disable RADIUS backdoor for telnet/ssh/http/https."
    ::= { agRadiusConfig 15 }

radNewCfgBackdoor OBJECT-TYPE
    SYNTAX  INTEGER {
        enabled(1),
        disabled(2)
        }
    MAX-ACCESS  read-write
    STATUS  current
    DESCRIPTION
        "Enable or disable RADIUS backdoor for telnet/ssh/http/https."
    ::= { agRadiusConfig 16 }

radCurCfgAuthenSecondString OBJECT-TYPE
    SYNTAX  DisplayString (SIZE(0..32))
    MAX-ACCESS  read-only
    STATUS  current
    DESCRIPTION
        "The second RADIUS authentication string."
    ::= { agRadiusConfig 17 }

radNewCfgAuthenSecondString OBJECT-TYPE
    SYNTAX  DisplayString (SIZE(0..32))
    MAX-ACCESS  read-write
    STATUS  current
    DESCRIPTION
        "The second RADIUS authentication string."
    ::= { agRadiusConfig 18 }

radCurCfgSecBd OBJECT-TYPE
    SYNTAX  INTEGER {
        enabled(1),
        disabled(2)
        }
    MAX-ACCESS  read-only
    STATUS  current
    DESCRIPTION
        "Enable or disable RADIUS secure backdoor for telnet."
    ::= { agRadiusConfig 19 }

radNewCfgSecBd OBJECT-TYPE
    SYNTAX  INTEGER {
        enabled(1),
        disabled(2)
        }
    MAX-ACCESS  read-write
    STATUS  current
    DESCRIPTION
        "Enable or disable RADIUS secure backdoor for telnet."
    ::= { agRadiusConfig 20 }

radCurCfgPorttoUse OBJECT-TYPE
    SYNTAX  INTEGER {
        data(1),
        mgt(2)
        }
    MAX-ACCESS  read-only
    STATUS  current
    DESCRIPTION
        "Specify whether the Radius should be performed over the
         data port or the management port."
    ::= { agRadiusConfig 21 }

radNewCfgPorttoUse OBJECT-TYPE
    SYNTAX  INTEGER {
        data(1),
        mgt(2)
        }
    MAX-ACCESS  read-write
    STATUS  current
    DESCRIPTION
        "Specify whether the Radius should be performed over the
         data port or the management port."
    ::= { agRadiusConfig 22 }

radCurCfgSecPorttoUse OBJECT-TYPE
    SYNTAX  INTEGER {
        data(1),
        mgt(2)
        }
    MAX-ACCESS  read-only
    STATUS  current
    DESCRIPTION
        "Specify whether the Radius should be performed over the
         data port or the management port."
    ::= { agRadiusConfig 23 }

radNewCfgSecPorttoUse OBJECT-TYPE
    SYNTAX  INTEGER {
        data(1),
        mgt(2)
        }
    MAX-ACCESS  read-write
    STATUS  current
    DESCRIPTION
        "Specify whether the Radius should be performed over the
         data port or the management port."
    ::= { agRadiusConfig 24 }

radCurCfgSrcLoopIf OBJECT-TYPE
    SYNTAX  INTEGER
    MAX-ACCESS  read-only
    STATUS  current
    DESCRIPTION
        "The index of the loopback interface that should be used
         for the source IP of the Radius message; 0 means that
         no loopback interface is used as the source of the Radius message."
    ::= { agRadiusConfig 25 }

radNewCfgSrcLoopIf OBJECT-TYPE
    SYNTAX  INTEGER 
    MAX-ACCESS  read-write
    STATUS  current
    DESCRIPTION
        "The index of the loopback interface that should be used
         for the source IP of the Radius message; 0 means that
         no loopback interface is used as the source of the Radius message."
    ::= { agRadiusConfig 26 }

-- NTP Configuration
agCurCfgNTPServer OBJECT-TYPE
    SYNTAX DisplayString (SIZE(0..46))
    MAX-ACCESS  read-only
    STATUS  current
    DESCRIPTION
        "The NTP Server Address."
    ::= { agNTP 1 }

agNewCfgNTPServer OBJECT-TYPE
    SYNTAX DisplayString (SIZE(0..46))
    MAX-ACCESS  read-write
    STATUS  current
    DESCRIPTION
        "The NTP Server Address."
    ::= { agNTP 2 }

agCurCfgNTPResyncInterval OBJECT-TYPE
    SYNTAX  INTEGER (5..44640)
    MAX-ACCESS  read-only
    STATUS  current
    DESCRIPTION
        "The NTP Server resync interval in minutes."
    ::= { agNTP 3 }

agNewCfgNTPResyncInterval OBJECT-TYPE
    SYNTAX  INTEGER (5..44640)
    MAX-ACCESS  read-write
    STATUS  current
    DESCRIPTION
        "The NTP Server resync interval in minutes."
    ::= { agNTP 4 }


agCurCfgNTPService OBJECT-TYPE
    SYNTAX  INTEGER {
        enabled(1),
        disabled(2)
        }
    MAX-ACCESS  read-only
    STATUS  current
    DESCRIPTION
        "Enable/disable NTP Service."
    ::= { agNTP 9 }

agNewCfgNTPService OBJECT-TYPE
    SYNTAX  INTEGER {
        enabled(1),
        disabled(2)
        }
    MAX-ACCESS  read-write
    STATUS  current
    DESCRIPTION
        "Enable/disable NTP Service."
    ::= { agNTP 10 }

agCurCfgNTPSecServer OBJECT-TYPE
    SYNTAX DisplayString (SIZE(0..46))
    MAX-ACCESS  read-only
    STATUS  current
    DESCRIPTION
        "The Secondary NTP Server Address."
    ::= { agNTP 11 }

agNewCfgNTPSecServer OBJECT-TYPE
    SYNTAX DisplayString (SIZE(0..46))
    MAX-ACCESS  read-write
    STATUS  current
    DESCRIPTION
        "The Secondary NTP Server Address."
    ::= { agNTP 12 }

agCurCfgNTPServerPort OBJECT-TYPE
    SYNTAX  INTEGER {
        data(1),
        mgt(2)
        }
    MAX-ACCESS  read-only
    STATUS  current
    DESCRIPTION
        "Choose the port that the primary server is connected to."
    ::= { agNTP 13 }

agNewCfgNTPServerPort OBJECT-TYPE
    SYNTAX  INTEGER {
        data(1),
        mgt(2)
        }
    MAX-ACCESS  read-write
    STATUS  current
    DESCRIPTION
        "Choose the port that the primary server is connected to."
    ::= { agNTP 14 }
agCurCfgNTPSecServerPort OBJECT-TYPE
    SYNTAX  INTEGER {
        data(1),
        mgt(2)
        }
    MAX-ACCESS  read-only
    STATUS  current
    DESCRIPTION
        "Choose the port that the secondary server is connected to."
    ::= { agNTP 15 }

agNewCfgNTPSecServerPort OBJECT-TYPE
    SYNTAX  INTEGER {
        data(1),
        mgt(2)
        }
    MAX-ACCESS  read-write
    STATUS  current
    DESCRIPTION
        "Choose the port that the secondary server is connected to."
    ::= { agNTP 16 }

agCurCfgNTPSrcLoopIf OBJECT-TYPE
    SYNTAX  INTEGER
    MAX-ACCESS  read-only
    STATUS  current
    DESCRIPTION
        "The index of the loopback interface that should be used
         for the source IP of the NTP packet; 0 means that
         no loopback interface is used as the source of the NTP packet."
    ::= { agNTP 17 }

agNewCfgNTPSrcLoopIf OBJECT-TYPE
    SYNTAX  INTEGER
    MAX-ACCESS  read-write
    STATUS  current
    DESCRIPTION
        "The index of the loopback interface that should be used
         for the source IP of the NTP packet; 0 means that
         no loopback interface is used as the source of the NTP packet."
    ::= { agNTP 18 }


-- APPLY Configuration
agApplyPending OBJECT-TYPE
    SYNTAX  INTEGER {
        applyNeeded(2),
        noApplyNeeded(3)
        }
    MAX-ACCESS  read-only
    STATUS  current
    DESCRIPTION
        "This object, when read, gives the user information
         whether an apply action is needed and that the configuration
         has been chaged by the user actions. The user then can
         apply the changes by setting proper value to the object
         agApplyConfiguration described above."
    ::= { agApply 1 }

agApplyConfig OBJECT-TYPE
    SYNTAX  INTEGER {
        apply(1),
        idle(2),
        inprogress(3),
        complete(4),
        failed(5)
        }
    MAX-ACCESS  read-write
    STATUS  current
    DESCRIPTION
         "When this object is read the current state is returned.
          idle(2) indicates that there is no apply in progess.
          complete(4) indicates that the last apply operation is completed.
          Setting the value to apply(1), will write all the changes made
          since the last apply to the current configuration block.
	  If the apply is successful this variable will return the state
          'complete' else it will return 'failed'. In case of failure,
          to read the reason for failure use the agApplyTable.
          Once the operation is completed or the agApplyTable is read in case
          of failure, the apply buffer needs to be freed and the agApplyState
          should be set back to 'idle' state so others can issue the apply
          command via SNMP."
    ::= { agApply 2 }

agApplyTableSize OBJECT-TYPE
    SYNTAX  Integer32
    MAX-ACCESS  read-only
    STATUS  current
    DESCRIPTION
        "The number of strings in the apply table."
    ::= { agApply 4 }

agApplyTable OBJECT-TYPE
    SYNTAX  SEQUENCE OF AgApplyTableEntry
    MAX-ACCESS  not-accessible
    STATUS  current
    DESCRIPTION
        "The table of failure reasons for an apply of current
         configuration block changes."
    ::= { agApply 5 }

agApplyTableEntry OBJECT-TYPE
    SYNTAX  AgApplyTableEntry
    MAX-ACCESS  not-accessible
    STATUS  current
    DESCRIPTION
        "A row in the table of failure reasons for an apply
         (information about a particular reason of failure)."
    INDEX   { agApplyIndex }
    ::= { agApplyTable 1 }

AgApplyTableEntry ::= SEQUENCE {
    agApplyIndex      Integer32,
    agApplyString     OCTET STRING
    }

agApplyIndex OBJECT-TYPE
    SYNTAX  Integer32
    MAX-ACCESS  read-only
    STATUS  current
    DESCRIPTION
        "The table index."
    ::= { agApplyTableEntry 1 }

agApplyString OBJECT-TYPE
    SYNTAX  OCTET STRING
    MAX-ACCESS  read-only
    STATUS  current
    DESCRIPTION
        "A string in the apply table."
    ::= { agApplyTableEntry 2 }




-- TACACS+ Configuration

tacCurCfgPrimaryServer OBJECT-TYPE
    SYNTAX  IpAddress
    MAX-ACCESS  read-only
    STATUS  current
    DESCRIPTION
        "The IP address of the Primary TACACS+ server."
    ::= { agTacacsConfig 1 }

tacNewCfgPrimaryServer OBJECT-TYPE
    SYNTAX  IpAddress
    MAX-ACCESS  read-write
    STATUS  current
    DESCRIPTION
        "The IP address of the Primary TACACS+ server."
    ::= { agTacacsConfig 2 }

tacCurCfgSecondaryServer OBJECT-TYPE
    SYNTAX  IpAddress
    MAX-ACCESS  read-only
    STATUS  current
    DESCRIPTION
        "The IP address of the Secondary TACACS+ server."
    ::= { agTacacsConfig 3 }

tacNewCfgSecondaryServer OBJECT-TYPE
    SYNTAX  IpAddress
    MAX-ACCESS  read-write
    STATUS  current
    DESCRIPTION
        "The IP address of the Secondary TACACS+ server."
    ::= { agTacacsConfig 4 }


tacCurCfgPort OBJECT-TYPE
    SYNTAX  INTEGER  (1..65000)
    MAX-ACCESS  read-only
    STATUS  current
    DESCRIPTION
        "Specify the TACACS+ port number."
    ::= { agTacacsConfig 5 }

tacNewCfgPort OBJECT-TYPE
    SYNTAX  INTEGER  (1..65000)
    MAX-ACCESS  read-write
    STATUS  current
    DESCRIPTION
        "Specify the TACACS+ port number."
    ::= { agTacacsConfig 6 }

tacCurCfgTimeout OBJECT-TYPE
    SYNTAX  INTEGER  (4..15)
    MAX-ACCESS  read-only
    STATUS  current
    DESCRIPTION
        "The maximum number of seconds before resending authentication
         to TACACS+ server."
    ::= { agTacacsConfig 7 }

tacNewCfgTimeout OBJECT-TYPE
    SYNTAX  INTEGER  (4..15)
    MAX-ACCESS  read-write
    STATUS  current
    DESCRIPTION
        "The maximum number of seconds before resending authentication
         to TACACS+ server."
    ::= { agTacacsConfig 8 }

tacCurCfgRetries OBJECT-TYPE
    SYNTAX  INTEGER  (1..3)
    MAX-ACCESS  read-only
    STATUS  current
    DESCRIPTION
        "Number of retries to the TACACS+ server."
    ::= { agTacacsConfig 9 }

tacNewCfgRetries OBJECT-TYPE
    SYNTAX  INTEGER  (1..3)
    MAX-ACCESS  read-write
    STATUS  current
    DESCRIPTION
        "Number of retries to the TACACS+ server."
    ::= { agTacacsConfig 10 }

tacCurCfgState OBJECT-TYPE
    SYNTAX  INTEGER {
        enabled(1),
        disabled(0)
        }
    MAX-ACCESS  read-only
    STATUS  current
    DESCRIPTION
        "Enable or disable TACACS+ authentication."
    ::= { agTacacsConfig 11 }

tacNewCfgState OBJECT-TYPE
    SYNTAX  INTEGER {
        enabled(1),
        disabled(0)
        }
    MAX-ACCESS  read-write
    STATUS  current
    DESCRIPTION
        "Enable or disable TACACS+ authentication."
    ::= { agTacacsConfig 12 }

tacCurCfgAuthenString OBJECT-TYPE
    SYNTAX  DisplayString (SIZE(0..32))
    MAX-ACCESS  read-only
    STATUS  current
    DESCRIPTION
        "The TACACS+ authentication string."
    ::= { agTacacsConfig 13 }

tacNewCfgAuthenString OBJECT-TYPE
    SYNTAX  DisplayString (SIZE(0..32))
    MAX-ACCESS  read-write
    STATUS  current
    DESCRIPTION
        "The TACACS+ authentication string."
    ::= { agTacacsConfig 14 }

tacCurCfgBackdoor OBJECT-TYPE
    SYNTAX  INTEGER {
        enabled(1),
        disabled(2)
        }
    MAX-ACCESS  read-only
    STATUS  current
    DESCRIPTION
        "Enable or disable TACACS+ backdoor for telnet/ssh/http/https."
    ::= { agTacacsConfig 15 }

tacNewCfgBackdoor OBJECT-TYPE
    SYNTAX  INTEGER {
        enabled(1),
        disabled(2)
        }
    MAX-ACCESS  read-write
    STATUS  current
    DESCRIPTION
        "Enable or disable TACACS+ backdoor for telnet/ssh/http/https."
    ::= { agTacacsConfig 16 }

tacCurCfgAuthenSecondString OBJECT-TYPE
    SYNTAX  DisplayString (SIZE(0..32))
    MAX-ACCESS  read-only
    STATUS  current
    DESCRIPTION
        "The second TACACS+ authentication string."
    ::= { agTacacsConfig 17 }

tacNewCfgAuthenSecondString OBJECT-TYPE
    SYNTAX  DisplayString (SIZE(0..32))
    MAX-ACCESS  read-write
    STATUS  current
    DESCRIPTION
        "The second TACACS+ authentication string."
    ::= { agTacacsConfig 18 }

tacCurCfgCmdAuthor OBJECT-TYPE
    SYNTAX  INTEGER {
        enabled(1),
        disabled(2)
        }
    MAX-ACCESS  read-only
    STATUS  current
    DESCRIPTION
        "Enable or disable TACACS+ command authorization."
    ::= { agTacacsConfig 19 }

tacNewCfgCmdAuthor OBJECT-TYPE
    SYNTAX  INTEGER {
        enabled(1),
        disabled(2)
        }
    MAX-ACCESS  read-write
    STATUS  current
    DESCRIPTION
        "Enable or disable TACACS+ command authorization."
    ::= { agTacacsConfig 20 }

tacCurCfgCmdLogging OBJECT-TYPE
    SYNTAX  INTEGER {
        enabled(1),
        disabled(2)
        }
    MAX-ACCESS  read-only
    STATUS  current
    DESCRIPTION
        "Enable or disable TACACS+ command logging."
    ::= { agTacacsConfig 21 }

tacNewCfgCmdLogging OBJECT-TYPE
    SYNTAX  INTEGER {
        enabled(1),
        disabled(2)
        }
    MAX-ACCESS  read-write
    STATUS  current
    DESCRIPTION
        "Enable or disable TACACS+ command logging."
    ::= { agTacacsConfig 22 }

tacCurCfgSecBd OBJECT-TYPE
    SYNTAX  INTEGER {
        enabled(1),
        disabled(2)
        }
    MAX-ACCESS  read-only
    STATUS  current
    DESCRIPTION
        "Enable or disable TACACS+ secure backdoor for telnet."
    ::= { agTacacsConfig 23 }

tacNewCfgSecBd OBJECT-TYPE
    SYNTAX  INTEGER {
        enabled(1),
        disabled(2)
        }
    MAX-ACCESS  read-write
    STATUS  current
    DESCRIPTION
        "Enable or disable TACACS+ secure backdoor for telnet."
    ::= { agTacacsConfig 24 }
tacCurCfgCmap OBJECT-TYPE
    SYNTAX  INTEGER {
        enabled(1),
        disabled(2)
        }
    MAX-ACCESS  read-only
    STATUS  current
    DESCRIPTION
        "Enable/Disable Tacacs+ new privilege level mapping, as
         configured in the current configuration block."
    ::= { agTacacsConfig 25 }

tacNewCfgCmap OBJECT-TYPE
    SYNTAX  INTEGER {
        enabled(1),
        disabled(2)
        }
    MAX-ACCESS  read-write
    STATUS  current
    DESCRIPTION
        "Enable/Disable Tacacs+ new privilege level mapping."
    ::= { agTacacsConfig 26 }
tacCurCfgEnaPassChange OBJECT-TYPE
    SYNTAX  INTEGER {
        enabled(1),
        disabled(2)
        }
    MAX-ACCESS  read-only
    STATUS  current
    DESCRIPTION
        " Enable/Disable Tacacs+ password change."
    ::= { agTacacsConfig 29 }

tacNewCfgEnaPassChange OBJECT-TYPE
    SYNTAX  INTEGER {
        enabled(1),
        disabled(2)
        }
    MAX-ACCESS  read-write
    STATUS  current
    DESCRIPTION
        " Enable/Disable Tacacs+ password change."
    ::= { agTacacsConfig 30 }

tacChangePassForUser OBJECT-TYPE
    SYNTAX  DisplayString (SIZE(0..32))
    MAX-ACCESS  read-write
    STATUS  current
    DESCRIPTION
        "The username for changing server password."
    ::= { agTacacsConfig 31 }

tacChangePassCurPass OBJECT-TYPE
    SYNTAX  DisplayString (SIZE(0..32))
    MAX-ACCESS  read-only
    STATUS  current
    DESCRIPTION
        "The current password for tacacs server."
    ::= { agTacacsConfig 32 }

tacChangePassNewPass OBJECT-TYPE
    SYNTAX  DisplayString (SIZE(0..32))
    MAX-ACCESS  read-write
    STATUS  current
    DESCRIPTION
        "The new password for tacacs server."
    ::= { agTacacsConfig 33 }

tacChangePassForServer OBJECT-TYPE
    SYNTAX  INTEGER {
        primary(1),
        secondary(2)
        }
    MAX-ACCESS  read-write
    STATUS  current
    DESCRIPTION
        "Change password for <1/2> Tacacs+ server."
    ::= { agTacacsConfig 34 }

tacCurCfgPorttoUse OBJECT-TYPE
    SYNTAX  INTEGER {
        data(1),
        mgt(2)
        }
    MAX-ACCESS  read-only
    STATUS  current
    DESCRIPTION
        "Specify whether the Tacacs should be performed over the
         data port or the management port."
    ::= { agTacacsConfig 35 }

tacNewCfgPorttoUse OBJECT-TYPE
    SYNTAX  INTEGER {
        data(1),
        mgt(2)
        }
    MAX-ACCESS  read-write
    STATUS  current
    DESCRIPTION
        "Specify whether the Tacacs should be performed over the
         data port or the management port."
    ::= { agTacacsConfig 36 }

tacCurCfgSecPorttoUse OBJECT-TYPE
    SYNTAX  INTEGER {
        data(1),
        mgt(2)
        }
    MAX-ACCESS  read-only
    STATUS  current
    DESCRIPTION
        "Specify whether the Tacacs should be performed over the
         data port or the management port."
    ::= { agTacacsConfig 37 }

tacNewCfgSecPorttoUse OBJECT-TYPE
    SYNTAX  INTEGER {
        data(1),
        mgt(2)
        }
    MAX-ACCESS  read-write
    STATUS  current
    DESCRIPTION
        "Specify whether the Tacacs should be performed over the
         data port or the management port."
    ::= { agTacacsConfig 38 }

agTacacsUserMapCurCfgTable OBJECT-TYPE
    SYNTAX  SEQUENCE OF AgTacacsUserMapCurCfgTableEntry
    MAX-ACCESS  not-accessible
    STATUS  current
    DESCRIPTION
        "The table of tacacs+ user map current configuration."
    ::= { agTacacsConfig 39 }

agTacacsUserMapCurCfgTableEntry OBJECT-TYPE
    SYNTAX  AgTacacsUserMapCurCfgTableEntry
    MAX-ACCESS  not-accessible
    STATUS  current
    DESCRIPTION
        "A row in the tacacs+ user mapping table."
    INDEX  { agTacacsUserMapCurCfgUId }
    ::= { agTacacsUserMapCurCfgTable 1 }

AgTacacsUserMapCurCfgTableEntry ::= SEQUENCE {
    agTacacsUserMapCurCfgUId       Integer32,
    agTacacsUserMapCurCfgMapping   INTEGER
    }

agTacacsUserMapCurCfgUId OBJECT-TYPE
    SYNTAX Integer32
    MAX-ACCESS  read-only
    STATUS  current
    DESCRIPTION
        "The current config remote privilege identifier.
         The identifier value corresponds to the remote privilege."
    ::= { agTacacsUserMapCurCfgTableEntry 1 }

agTacacsUserMapCurCfgMapping OBJECT-TYPE
    SYNTAX  INTEGER {
        none(0),
        user(1),
        oper(2),
        admin(3)
        }
    MAX-ACCESS  read-only
    STATUS  current
    DESCRIPTION
        "Current Tacacs+ user privilege mappings.
         The correspondence between the local privilege and the remote privilege is:
          - The remote privilege is the privilege identifier value
          - The local privilege is the mapped value(user, oper, admin)
         Example: For the remote privilege 15, we have the index 16:
         agTacacsUserMapCurCfgUId.16 = 15."
    ::= { agTacacsUserMapCurCfgTableEntry 2 }

agTacacsUserMapNewCfgTable OBJECT-TYPE
    SYNTAX  SEQUENCE OF AgTacacsUserMapNewCfgTableEntry
    MAX-ACCESS  not-accessible
    STATUS  current
    DESCRIPTION
        "The table of tacacs+ user map new configuration."
    ::= { agTacacsConfig 40 }

tacNewCfgDirectedRequest OBJECT-TYPE
    SYNTAX  INTEGER {
        disabled(1),
        restricted(2),
        no-truncate(3)
        }
    MAX-ACCESS  read-write
    STATUS  current
    DESCRIPTION
        "Enable/Disable tacacs directed request."
    ::= { agTacacsConfig 41 }

tacCurCfgDirectedRequest OBJECT-TYPE
    SYNTAX  INTEGER {
        disabled(1),
        restricted(2),
        no-truncate(3)
        }
    MAX-ACCESS  read-only
    STATUS  current
    DESCRIPTION
        "The current tacacs directed request state."
    ::= { agTacacsConfig 42 }

agTacacsUserMapNewCfgTableEntry OBJECT-TYPE
    SYNTAX  AgTacacsUserMapNewCfgTableEntry
    MAX-ACCESS  not-accessible
    STATUS  current
    DESCRIPTION
        "A row in the tacacs+ user mapping table."
    INDEX  { agTacacsUserMapNewCfgUId }
    ::= { agTacacsUserMapNewCfgTable 1 }

AgTacacsUserMapNewCfgTableEntry ::= SEQUENCE {
    agTacacsUserMapNewCfgUId       Integer32,
    agTacacsUserMapNewCfgMapping   INTEGER
    }

agTacacsUserMapNewCfgUId OBJECT-TYPE
    SYNTAX Integer32
    MAX-ACCESS  read-only
    STATUS  current
    DESCRIPTION
        "The new config remote privilege identifier.
         The identifier value corresponds to the remote privilege."
    ::= { agTacacsUserMapNewCfgTableEntry 1 }

agTacacsUserMapNewCfgMapping OBJECT-TYPE
    SYNTAX  INTEGER {
        none(0),
        user(1),
        oper(2),
        admin(3)
        }
    MAX-ACCESS  read-create
    STATUS  current
    DESCRIPTION
        "Set new Tacacs+ user privilege mappings.
         The correspondence between the local privilege and the remote privilege is:
          - The remote privilege is the privilege identifier value
          - The local privilege is the mapped value(user, oper, admin)
         Example: For the remote privilege 15, we have the index 16:
         agTacacsUserMapNewCfgUId.16 = 15."
    ::= { agTacacsUserMapNewCfgTableEntry 2 }
tacCurCfgAttempts OBJECT-TYPE
    SYNTAX  INTEGER  (1..10)
    MAX-ACCESS  read-only
    STATUS  current
    DESCRIPTION
        "Number of login attempts to the TACACS+ server."
    ::= { agTacacsConfig 43 }

tacNewCfgAttempts OBJECT-TYPE
    SYNTAX  INTEGER  (1..10)
    MAX-ACCESS  read-write
    STATUS  current
    DESCRIPTION
        "Number of login attempts to the TACACS+ server."
    ::= { agTacacsConfig 44 }

tacCurBypassEnable OBJECT-TYPE
    SYNTAX      INTEGER {
        disable(0),
        enable (1)
    }
    MAX-ACCESS  read-only
    STATUS  current
    DESCRIPTION
        "Status of the enable bypass.If the status of this object
         is enabled, user authenticated via TACACS+ with admin
         previllage is granted enable previllage access.If disabled,
         admin users will be provided with enable previllage access
         based on enable password configured."
    DEFVAL      { enable }
    ::= { agTacacsConfig 45 }

tacNewBypassEnable OBJECT-TYPE
    SYNTAX      INTEGER {
        disable(0),
        enable (1)
    }
    MAX-ACCESS  read-write
    STATUS  current
    DESCRIPTION
        "Status of the enable bypass.If the status of this object
         is enabled, user authenticated via TACACS+ with admin
         previllage is granted enable previllage access.If disabled,
         admin users will be provided with enable previllage access
         based on enable password configured."
    DEFVAL      { enable }
    ::= { agTacacsConfig 46 }

tacCurCfgEnableAccounting OBJECT-TYPE
    SYNTAX    INTEGER {
        enable(1),
        disable(0)
    }
    MAX-ACCESS  read-only
    STATUS  current
    DESCRIPTION
        " Current TACACS+ accounting state."
    ::= { agTacacsConfig 47 }

tacNewCfgEnableAccounting OBJECT-TYPE
    SYNTAX INTEGER  {
        enable(1),
        disable(0)
    }
    MAX-ACCESS  read-write
    STATUS      current
    DESCRIPTION
        " Enable/Disable TACACS+ accounting."
    ::= { agTacacsConfig 48 }

tacCurCfgSrcLoopIf OBJECT-TYPE
    SYNTAX  INTEGER 
    MAX-ACCESS  read-only
    STATUS  current
    DESCRIPTION
        "The index of the loopback interface that should be used
         for the source IP of the Tacacs+ message; 0 means that
         no loopback interface is used as the source of the Tacacs+ message."
    ::= { agTacacsConfig 49 }

tacNewCfgSrcLoopIf OBJECT-TYPE
    SYNTAX INTEGER
    MAX-ACCESS  read-write
    STATUS      current
    DESCRIPTION
        "The index of the loopback interface that should be used
         for the source IP of the Tacacs+ message; 0 means that
         no loopback interface is used as the source of the Tacacs+ message."
    ::= { agTacacsConfig 50 }


-- Multiple Management network MIB objects
agMgmtNetTableMaxSize OBJECT-TYPE
    SYNTAX  Integer32
    MAX-ACCESS  read-only
    STATUS  current
    DESCRIPTION
        "The maximum number of entries in the Management
         Network Table."
    ::= { agMgmtNetConfig 1 }

agCurCfgMgmtNetTable OBJECT-TYPE
    SYNTAX  SEQUENCE OF AgCurCfgMgmtNetEntry
    MAX-ACCESS  not-accessible
    STATUS  current
    DESCRIPTION
        "The table for Management Network definitions
         in the current configuration block."
    ::= { agMgmtNetConfig 2 }

agCurCfgMgmtNetEntry OBJECT-TYPE
    SYNTAX  AgCurCfgMgmtNetEntry
    MAX-ACCESS  not-accessible
    STATUS  current
    DESCRIPTION
        "A row in the management network definition table."
    INDEX   {  agCurCfgMgmtNetIndex }
    ::= { agCurCfgMgmtNetTable 1 }

AgCurCfgMgmtNetEntry ::= SEQUENCE {
    agCurCfgMgmtNetIndex  	Integer32,
    agCurCfgMgmtNetSubnet       DisplayString,
    agCurCfgMgmtNetMask         DisplayString
    }

agCurCfgMgmtNetIndex OBJECT-TYPE
    SYNTAX  Integer32
    MAX-ACCESS  read-only
    STATUS  current
    DESCRIPTION
        "The index of the Management Network Definition table."
    ::= { agCurCfgMgmtNetEntry 1 }

agCurCfgMgmtNetSubnet OBJECT-TYPE
    SYNTAX  DisplayString
    MAX-ACCESS  read-only
    STATUS  current
    DESCRIPTION
        "The Management Network Address in the current configuration
         block."
    ::= { agCurCfgMgmtNetEntry 2 }

agCurCfgMgmtNetMask OBJECT-TYPE
    SYNTAX  DisplayString
    MAX-ACCESS  read-only
    STATUS  current
    DESCRIPTION
        "The Management Network Mask/Prefix Length in the current configuration
         block."
    ::= { agCurCfgMgmtNetEntry 3 }

agNewCfgMgmtNetTable OBJECT-TYPE
    SYNTAX  SEQUENCE OF AgNewCfgMgmtNetEntry
    MAX-ACCESS  not-accessible
    STATUS  current
    DESCRIPTION
        "The table for Management Network definitions
         in the new configuration block."
    ::= { agMgmtNetConfig 3 }

agNewCfgMgmtNetEntry OBJECT-TYPE
    SYNTAX  AgNewCfgMgmtNetEntry
    MAX-ACCESS  not-accessible
    STATUS  current
    DESCRIPTION
        "A row in the management network definition table."
    INDEX   {  agNewCfgMgmtNetIndex }
    ::= { agNewCfgMgmtNetTable 1 }

AgNewCfgMgmtNetEntry ::= SEQUENCE {
    agNewCfgMgmtNetIndex  	Integer32,
    agNewCfgMgmtNetSubnet       DisplayString,
    agNewCfgMgmtNetMask         DisplayString,
    agNewCfgMgmtNetDelete       INTEGER
    }

agNewCfgMgmtNetIndex OBJECT-TYPE
    SYNTAX  Integer32
    MAX-ACCESS  read-only
    STATUS  current
    DESCRIPTION
        "The index of the Management Network Definition table."
    ::= { agNewCfgMgmtNetEntry 1 }

agNewCfgMgmtNetSubnet OBJECT-TYPE
    SYNTAX  DisplayString
    MAX-ACCESS  read-create
    STATUS  current
    DESCRIPTION
        "The Management Network Address in the new configuration
         block."
    ::= { agNewCfgMgmtNetEntry 2 }

agNewCfgMgmtNetMask OBJECT-TYPE
    SYNTAX  DisplayString
    MAX-ACCESS  read-create
    STATUS  current
    DESCRIPTION
        "The Management Network Mask/Prefix length in the new configuration
         block."
    ::= { agNewCfgMgmtNetEntry 3 }

agNewCfgMgmtNetDelete OBJECT-TYPE
    SYNTAX  INTEGER {
        other(1),
        delete(2)
        }
    MAX-ACCESS  read-create
    STATUS  current
    DESCRIPTION
        "By setting the value to delete(2), the entire row is deleted."
    ::= { agNewCfgMgmtNetEntry 4 }

agMgmtNetClear OBJECT-TYPE
    SYNTAX  INTEGER {
        other(1),
        clear(2)
        }
    MAX-ACCESS  read-write
    STATUS current
    DESCRIPTION
        "By setting the value to delete(2), the entire table is cleared."
    ::= { agMgmtNetConfig 4 }



-- Scheduled Reboot Group

agCfgBootResetParameters OBJECT-TYPE
    SYNTAX  DisplayString (SIZE(0..255))
    MAX-ACCESS  read-write
    STATUS  current
    DESCRIPTION
        "String formatated as 'weekday hour minute'
         where
         - weekday is none(0),sunday(1),monday(2),
         tuesday(3),wednesday(4),thursday(5),friday(6),
         saturday(7)
         - hour is the hour in 24-hour format for reboot
         - minutes are the minutes [00] for reboot"

     ::= { agBoot 1 }

agCfgBootReset OBJECT-TYPE
    SYNTAX  INTEGER {
        none(1),
        cancel(2)
        }
    MAX-ACCESS  read-write
    STATUS  current
    DESCRIPTION
        "Cancel pending switch reset."
    ::= { agBoot 4 }

agCfgBootNxtResetTime OBJECT-TYPE
    SYNTAX  DisplayString (SIZE(0..255))
    MAX-ACCESS  read-only
    STATUS  current
    DESCRIPTION
        "Display the next scheduled reboot time."
     ::= { agBoot 5 }

agCfgBootPendingReset OBJECT-TYPE
    SYNTAX INTEGER {
        idle(1),
        pending(2)
        }
    MAX-ACCESS  read-only
    STATUS  current
    DESCRIPTION
        "Shows if there is any pending reboot scheduled.
         You should cancel any pending reboot scheduled
         before setting another."
    ::= { agBoot 6 }





agAccessUserMaxUserID OBJECT-TYPE
    SYNTAX  Integer32
    MAX-ACCESS  read-only
    STATUS  current
    DESCRIPTION
        "The maximum number of User IDs."
    ::= { agAccess 1 }

agAccessCurStrongPassword OBJECT-TYPE
    SYNTAX  INTEGER {
        enabled(1),
        disabled(0)
        }
    MAX-ACCESS  read-only
    STATUS  current
    DESCRIPTION
        "Status of strong password."
    ::= { agAccess 4 }

agAccessNewStrongPassword OBJECT-TYPE
    SYNTAX  INTEGER {
        enabled(1),
        disabled(0)
        }
    MAX-ACCESS read-write
    STATUS current
    DESCRIPTION
        "Setting this value to enabled(1) enables strong
         password support, while disabled(0) disables it."
    ::= { agAccess 5 }

agAccessCurStrongPassValidity OBJECT-TYPE
    SYNTAX  INTEGER (1..365)
    MAX-ACCESS  read-only
    STATUS  current
    DESCRIPTION
        "Password validity in days."
    ::= { agAccess 6 }

agAccessNewStrongPassValidity OBJECT-TYPE
    SYNTAX  INTEGER (1..365)
    MAX-ACCESS read-write
    STATUS current
    DESCRIPTION
        "Get or set password validity in days."
    ::= { agAccess 7 }

agAccessCurStrongPassWarning OBJECT-TYPE
    SYNTAX  INTEGER (1..365)
    MAX-ACCESS  read-only
    STATUS  current
    DESCRIPTION
        "Warning days before password expires."
    ::= { agAccess 8 }

agAccessNewStrongPassWarning OBJECT-TYPE
    SYNTAX  INTEGER (1..365)
    MAX-ACCESS read-write
    STATUS current
    DESCRIPTION
        "Get or set warning days before password expires."
    ::= { agAccess 9 }

agAccessCurStrongPassFailLog OBJECT-TYPE
    SYNTAX  INTEGER (1..255)
    MAX-ACCESS  read-only
    STATUS  current
    DESCRIPTION
        "Number of failed logins that trigger
         security notifications."
    ::= { agAccess 10 }

agAccessNewStrongPassFailLog OBJECT-TYPE
    SYNTAX  INTEGER (1..255)
    MAX-ACCESS read-write
    STATUS current
    DESCRIPTION
        "Get or set number of failed logins that trigger
         security notifications."
    ::= { agAccess 11 }

agAccessCurDefaultAdmin OBJECT-TYPE
    SYNTAX  INTEGER {
        enabled(1),
        disabled(0)
        }
    MAX-ACCESS  read-only
    STATUS  current
    DESCRIPTION
        "Get default admin account state. (1) indicates enabled and (0) indicates
          disabled (0). Default it is enabled."
    ::= { agAccess 12 }

agAccessNewDefaultAdmin OBJECT-TYPE
    SYNTAX  INTEGER {
        enabled(1),
        disabled(0)
        }
    MAX-ACCESS  read-write
    STATUS  current
    DESCRIPTION
        "Setting this value to enabled (1) will enable the default admin account while
          disabled (0) will disable the default admin account. Default it is enabled."
    ::= { agAccess 13 }

agAccessCurStrongPassLockout OBJECT-TYPE
    SYNTAX  INTEGER  {
        enabled(1),
        disabled(0)
        }
    MAX-ACCESS  read-only
    STATUS  current
    DESCRIPTION
        "Status of Lockout"
    ::= { agAccess 14 }

agAccessNewStrongPassLockout OBJECT-TYPE
    SYNTAX  INTEGER  {
        enabled(1),
        disabled(0)
        }
    MAX-ACCESS read-write
    STATUS current
    DESCRIPTION
        "Setting this value to enabled (1) enables account locking after trying for failed login
          attempts. While disabled (0) disables account locking."
    ::= { agAccess 15 }

agAccessCurStrongPassAttemptsMaxFail OBJECT-TYPE
    SYNTAX  INTEGER (1..10)
    MAX-ACCESS  read-only
    STATUS  current
    DESCRIPTION
        "The max number of failed logins before disabling account. Default value is 6"
    ::= { agAccess 16 }

agAccessNewStrongPassAttemptsMaxFail OBJECT-TYPE
    SYNTAX  INTEGER (1..10)
    MAX-ACCESS read-write
    STATUS current
    DESCRIPTION
        "Sets Max number of failed logins before disabling account. Default value is 6"
    ::= { agAccess 17 }



agAccessUserCurCfgTable OBJECT-TYPE
    SYNTAX  SEQUENCE OF AgAccessUserCurCfgTableEntry
    MAX-ACCESS  not-accessible
    STATUS  current
    DESCRIPTION
        "The table of Access user configuration."
    ::= { agAccess 2 }

agAccessUserCurCfgTableEntry OBJECT-TYPE
    SYNTAX  AgAccessUserCurCfgTableEntry
    MAX-ACCESS  not-accessible
    STATUS  current
    DESCRIPTION
        "A row in the Access user configuration table."
    INDEX  { agAccessUserCurCfgUId }
    ::= { agAccessUserCurCfgTable 1 }

AgAccessUserCurCfgTableEntry ::= SEQUENCE {
    agAccessUserCurCfgUId 	Integer32,
    agAccessUserCurCos 		INTEGER,
    agAccessUserCurCfgName 	DisplayString,
    agAccessUserCurCfgPswd 	DisplayString,
    agAccessUserCurCfgState	INTEGER
    }

agAccessUserCurCfgUId OBJECT-TYPE
    SYNTAX Integer32
    MAX-ACCESS  read-only
    STATUS  current
    DESCRIPTION
        "The User identifier."
    ::= { agAccessUserCurCfgTableEntry 1 }

agAccessUserCurCos OBJECT-TYPE
    SYNTAX  INTEGER {
        user(0),
        oper(3),
        admin(6)
        }
    MAX-ACCESS  read-only
    STATUS  current
    DESCRIPTION
        "The user class of service."
    ::= { agAccessUserCurCfgTableEntry 2 }

agAccessUserCurCfgName OBJECT-TYPE
    SYNTAX  DisplayString (SIZE(0..64))
    MAX-ACCESS  read-only
    STATUS  current
    DESCRIPTION
        "The user name. Please note, the max length is 8 in stacking mode."
    ::= { agAccessUserCurCfgTableEntry 3 }

agAccessUserCurCfgPswd OBJECT-TYPE
    SYNTAX  DisplayString (SIZE(0..128))
    MAX-ACCESS  read-only
    STATUS  current
    DESCRIPTION
        "The character string representing the user password."
    ::= { agAccessUserCurCfgTableEntry 4 }


agAccessUserCurCfgState OBJECT-TYPE
    SYNTAX  INTEGER  {
	enabled(2),
	disabled(3)
	}
    MAX-ACCESS  read-only
    STATUS  current
    DESCRIPTION
        "User validation (enabled or disabled) in current
         configuration block."
    ::= { agAccessUserCurCfgTableEntry 6 }

agAccessUserNewCfgTable OBJECT-TYPE
    SYNTAX  SEQUENCE OF AgAccessUserNewCfgTableEntry
    MAX-ACCESS  not-accessible
    STATUS  current
    DESCRIPTION
        "The table of Access user configuration."
    ::= { agAccess 3 }

agAccessUserNewCfgTableEntry OBJECT-TYPE
    SYNTAX  AgAccessUserNewCfgTableEntry
    MAX-ACCESS  not-accessible
    STATUS  current
    DESCRIPTION
        "A row in the Access user configuration table."
    INDEX  { agAccessUserNewCfgUId }
    ::= { agAccessUserNewCfgTable 1 }

AgAccessUserNewCfgTableEntry ::= SEQUENCE {
    agAccessUserNewCfgUId 	Integer32,
    agAccessUserNewCos  	INTEGER,
    agAccessUserNewCfgName   	DisplayString,
    agAccessUserNewCfgPswd 	DisplayString,
    agAccessUserNewCfgState	INTEGER,
    agAccessUserNewCfgDelete    INTEGER
    }

agAccessUserNewCfgUId OBJECT-TYPE
    SYNTAX Integer32
    MAX-ACCESS  read-only
    STATUS  current
    DESCRIPTION
        "The User identifier."
    ::= { agAccessUserNewCfgTableEntry 1 }

agAccessUserNewCos OBJECT-TYPE
    SYNTAX  INTEGER {
        user(0),
        oper(3),
        admin(6)
        }
    MAX-ACCESS  read-create
    STATUS  current
    DESCRIPTION
        "The user class of service."
    ::= { agAccessUserNewCfgTableEntry 2 }

agAccessUserNewCfgName OBJECT-TYPE
    SYNTAX  DisplayString (SIZE(0..64))
    MAX-ACCESS  read-create
    STATUS  current
    DESCRIPTION
        "The user name. Please note, the max length is 8 in stacking mode."
    ::= { agAccessUserNewCfgTableEntry 3 }

agAccessUserNewCfgPswd OBJECT-TYPE
    SYNTAX  DisplayString (SIZE(0..128))
    MAX-ACCESS  read-create
    STATUS  current
    DESCRIPTION
        "The character string representing the user password."
    ::= { agAccessUserNewCfgTableEntry 4 }


agAccessUserNewCfgState OBJECT-TYPE
    SYNTAX  INTEGER  {
	enabled(2),
	disabled(3)
	}
    MAX-ACCESS  read-create
    STATUS  current
    DESCRIPTION
        "User validation (enabled or disabled) in new
         configuration block."
    ::= { agAccessUserNewCfgTableEntry 7 }

agAccessUserNewCfgDelete OBJECT-TYPE
    SYNTAX  INTEGER  {
        other(1),
        delete(2)
        }
    MAX-ACCESS  read-create
    STATUS  current
    DESCRIPTION
        "This is an action object to create or delete a User.
         other(1) is returned always when read.
         The following values are writable: delete(2)...to delete a User"
    ::= { agAccessUserNewCfgTableEntry 8 }

-- LDAP Configuration

ldapCurCfgPrimaryIpAddr OBJECT-TYPE
    SYNTAX  DisplayString (SIZE(0..128))
    MAX-ACCESS  read-only
    STATUS  current
    DESCRIPTION
        "The IP address of the Primary LDAP server,it can be an ipv4 or ipv6 address."
    ::= { agLdapConfig 1 }

ldapNewCfgPrimaryIpAddr OBJECT-TYPE
    SYNTAX  DisplayString (SIZE(0..128))
    MAX-ACCESS  read-write
    STATUS  current
    DESCRIPTION
        "The IP address of the Primary LDAP server,it can be an ipv4 or ipv6 address."
    ::= { agLdapConfig 2 }

ldapCurCfgSecondaryIpAddr OBJECT-TYPE
    SYNTAX  DisplayString (SIZE(0..128))
    MAX-ACCESS  read-only
    STATUS  current
    DESCRIPTION
        "The IP address of the Secondary LDAP server,it can be an ipv4 or ipv6 address."
    ::= { agLdapConfig 3 }

ldapNewCfgSecondaryIpAddr OBJECT-TYPE
    SYNTAX  DisplayString (SIZE(0..128))
    MAX-ACCESS  read-write
    STATUS  current
    DESCRIPTION
        "The IP address of the Secondary LDAP server,it can be an ipv4 or ipv6 address."
    ::= { agLdapConfig 4 }

ldapCurCfgPort OBJECT-TYPE
    SYNTAX  INTEGER  (1..65000)
    MAX-ACCESS  read-only
    STATUS  current
    DESCRIPTION
        "Specify the LDAP port number."
    ::= { agLdapConfig 5 }

ldapNewCfgPort OBJECT-TYPE
    SYNTAX  INTEGER  (1..65000)
    MAX-ACCESS  read-write
    STATUS  current
    DESCRIPTION
        "Specify the LDAP port number."
    ::= { agLdapConfig 6 }

ldapCurCfgRetries OBJECT-TYPE
    SYNTAX  INTEGER  (1..3)
    MAX-ACCESS  read-only
    STATUS  current
    DESCRIPTION
        "Number of retries to the LDAP server."
    ::= { agLdapConfig 7 }

ldapNewCfgRetries OBJECT-TYPE
    SYNTAX  INTEGER  (1..3)
    MAX-ACCESS  read-write
    STATUS  current
    DESCRIPTION
        "Number of retries to the LDAP server."
    ::= { agLdapConfig 8 }

ldapCurCfgTimeout OBJECT-TYPE
    SYNTAX  INTEGER  (4..15)
    MAX-ACCESS  read-only
    STATUS  current
    DESCRIPTION
        "The maximum number of seconds before resending authentication
         to LDAP server."
    ::= { agLdapConfig 9 }

ldapNewCfgTimeout OBJECT-TYPE
    SYNTAX  INTEGER  (4..15)
    MAX-ACCESS  read-write
    STATUS  current
    DESCRIPTION
        "The maximum number of seconds before resending authentication
         to LDAP server."
    ::= { agLdapConfig 10 }

ldapCurCfgDomain OBJECT-TYPE
    SYNTAX  DisplayString (SIZE(0..127))
    MAX-ACCESS  read-only
    STATUS  current
    DESCRIPTION
        "The LDAP domain name."
    ::= { agLdapConfig 11 }

ldapNewCfgDomain OBJECT-TYPE
    SYNTAX  DisplayString (SIZE(0..127))
    MAX-ACCESS  read-write
    STATUS  current
    DESCRIPTION
        "The LDAP domain name."
    ::= { agLdapConfig 12 }

ldapCurCfgBackdoor OBJECT-TYPE
    SYNTAX  INTEGER {
        enabled(1),
        disabled(0)
        }
    MAX-ACCESS  read-only
    STATUS  current
    DESCRIPTION
        "Enable or disable LDAP backdoor for telnet/ssh/http/https."
    ::= { agLdapConfig 13 }

ldapNewCfgBackdoor OBJECT-TYPE
    SYNTAX  INTEGER {
        enabled(1),
        disabled(0)
        }
    MAX-ACCESS  read-write
    STATUS  current
    DESCRIPTION
        "Enable or disable LDAP backdoor for telnet/ssh/http/https."
    ::= { agLdapConfig 14 }

ldapCurCfgState OBJECT-TYPE
    SYNTAX  INTEGER {
        enabled(1),
        disabled(0)
        }
    MAX-ACCESS  read-only
    STATUS  current
    DESCRIPTION
        "Enable or disable LDAP authentication."
    ::= { agLdapConfig 15 }

ldapNewCfgState OBJECT-TYPE
    SYNTAX  INTEGER {
        enabled(1),
        disabled(0)
        }
    MAX-ACCESS  read-write
    STATUS  current
    DESCRIPTION
        "Enable or disable LDAP authentication."
    ::= { agLdapConfig 16 }

ldapCurCfgPorttoUse OBJECT-TYPE
    SYNTAX  INTEGER {
        data(1),
        mgt(2)
        }
    MAX-ACCESS  read-only
    STATUS  current
    DESCRIPTION
        "Specify whether the LDAP should be performed over the
         data port or the management port."
    ::= { agLdapConfig 17 }

ldapNewCfgPorttoUse OBJECT-TYPE
    SYNTAX  INTEGER {
        data(1),
        mgt(2)
        }
    MAX-ACCESS  read-write
    STATUS  current
    DESCRIPTION
        "Specify whether the LDAP should be performed over the
         data port or the management port."
    ::= { agLdapConfig 18 }

ldapCurCfgSecPorttoUse OBJECT-TYPE
    SYNTAX  INTEGER {
        data(1),
        mgt(2)
        }
    MAX-ACCESS  read-only
    STATUS  current
    DESCRIPTION
        "Specify whether the LDAP should be performed over the
         data port or the management port."
    ::= { agLdapConfig 19 }

ldapNewCfgSecPorttoUse OBJECT-TYPE
    SYNTAX  INTEGER {
        data(1),
        mgt(2)
        }
    MAX-ACCESS  read-write
    STATUS  current
    DESCRIPTION
        "Specify whether the LDAP should be performed over the
         data port or the management port."
    ::= { agLdapConfig 20 }

ldapCurCfgUserNameAttribute OBJECT-TYPE
    SYNTAX  DisplayString (SIZE(0..127))
    MAX-ACCESS  read-only
    STATUS  current
    DESCRIPTION
        "The LDAP username attribute."
    ::= { agLdapConfig 21 }

ldapNewCfgUserNameAttribute OBJECT-TYPE
    SYNTAX  DisplayString (SIZE(0..127))
    MAX-ACCESS  read-write
    STATUS  current
    DESCRIPTION
        "The LDAP username attribute (default = uid)."
    ::= { agLdapConfig 22 }



-- sFlow Group
sflowCurCfgServerAddress OBJECT-TYPE
    SYNTAX  IpAddress
    MAX-ACCESS  read-only
    STATUS  current
    DESCRIPTION
        "The IP address of the sFlow server."
    ::= { agsFlowConfig 1 }

sflowNewCfgServerAddress OBJECT-TYPE
    SYNTAX  DisplayString (SIZE(0..46))
    MAX-ACCESS  read-write
    STATUS  current
    DESCRIPTION
        "The IP address of the sFlow server."
    ::= { agsFlowConfig 2 }

sflowCurCfgServerPort OBJECT-TYPE
    SYNTAX  INTEGER  (1..65000)
    MAX-ACCESS  read-only
    STATUS  current
    DESCRIPTION
        "Specify the sFlow server port number."
    ::= { agsFlowConfig 3 }

sflowNewCfgServerPort OBJECT-TYPE
    SYNTAX  INTEGER  (1..65000)
    MAX-ACCESS  read-write
    STATUS  current
    DESCRIPTION
        "Specify the sFlow server port number."
    ::= { agsFlowConfig 4 }

sflowCurCfgState OBJECT-TYPE
    SYNTAX  INTEGER {
        enabled(1),
        disabled(0)
        }
    MAX-ACCESS  read-only
    STATUS  current
    DESCRIPTION
        "Enable or disable sFlow."
    ::= { agsFlowConfig 5 }

sflowNewCfgState OBJECT-TYPE
    SYNTAX  INTEGER {
        enabled(1),
        disabled(0)
        }
    MAX-ACCESS  read-write
    STATUS  current
    DESCRIPTION
        "Enable or disable sFlow"
    ::= { agsFlowConfig 6 }

sflowCurPortCfgTable OBJECT-TYPE
    SYNTAX  SEQUENCE OF SflowCurPortCfgTableEntry
    MAX-ACCESS  not-accessible
    STATUS  current
    DESCRIPTION
        "The table of sFlow port configuration."
    ::= { agsFlowConfig 7 }

sflowCurPortCfgTableEntry OBJECT-TYPE
    SYNTAX  SflowCurPortCfgTableEntry
    MAX-ACCESS  not-accessible
    STATUS  current
    DESCRIPTION
        "A row in the sFlow port configuration table."
    INDEX  { sflowCurPortCfgTableId }
    ::= { sflowCurPortCfgTable 1 }

SflowCurPortCfgTableEntry ::= SEQUENCE {
    sflowCurPortCfgTableId 	    PortNumber,
    sflowCurPortSampling            INTEGER,
    sflowCurPortPolling             INTEGER
    }

sflowCurPortCfgTableId OBJECT-TYPE
    SYNTAX PortNumber
    MAX-ACCESS  read-only
    STATUS  current
    DESCRIPTION
          "sFlow port number."
    ::= { sflowCurPortCfgTableEntry 1 }
sflowCurPortSampling OBJECT-TYPE
    SYNTAX       INTEGER (256..65536)
    MAX-ACCESS   read-only
    STATUS       current
    DESCRIPTION
        "The current sFlow port sampling rate."
    ::= { sflowCurPortCfgTableEntry 2 }
sflowCurPortPolling OBJECT-TYPE
    SYNTAX       INTEGER (5..60)
    MAX-ACCESS       read-only
    STATUS       current
    DESCRIPTION
        "The current sFlow port polling interval."
    ::= { sflowCurPortCfgTableEntry 3 }

sflowNewPortCfgTable OBJECT-TYPE
    SYNTAX  SEQUENCE OF SflowNewPortCfgTableEntry
    MAX-ACCESS  not-accessible
    STATUS  current
    DESCRIPTION
        "The table of sFlow port configuration."
    ::= { agsFlowConfig 8 }

sflowNewPortCfgTableEntry OBJECT-TYPE
    SYNTAX  SflowNewPortCfgTableEntry
    MAX-ACCESS  not-accessible
    STATUS  current
    DESCRIPTION
        "A row in the sFlow port configuration table."
    INDEX  { sflowNewPortCfgTableId }
    ::= { sflowNewPortCfgTable 1 }

SflowNewPortCfgTableEntry ::= SEQUENCE {
    sflowNewPortCfgTableId 	    PortNumber,
    sflowNewPortSampling    	    INTEGER,
    sflowNewPortPolling             INTEGER
    }

sflowNewPortCfgTableId OBJECT-TYPE
    SYNTAX PortNumber
    MAX-ACCESS  read-only
    STATUS  current
    DESCRIPTION
          " sFlow port number."
    ::= { sflowNewPortCfgTableEntry 1 }
sflowNewPortSampling OBJECT-TYPE
    SYNTAX       INTEGER (256..65536)
    MAX-ACCESS    read-write
    STATUS       current
    DESCRIPTION
        "The new sFlow port sampling rate.
        Valid range: 256-65536| 0 for disable"
    ::= { sflowNewPortCfgTableEntry 2 }
sflowNewPortPolling OBJECT-TYPE
    SYNTAX       INTEGER (5..60)
    MAX-ACCESS       read-write
    STATUS       current
    DESCRIPTION
        "The new sFlow port polling interval.
	Valid range: 5-60| 0 for disable"
    ::= { sflowNewPortCfgTableEntry 3 }

sflowCurCfgMgmtPort OBJECT-TYPE
    SYNTAX  INTEGER {
        data(1)
        , mgt(2)
        }
    MAX-ACCESS  read-only
    STATUS  current
    DESCRIPTION
        "The port that the sFlow server is connected to"
    ::= { agsFlowConfig 9 }

sflowNewCfgMgmtPort OBJECT-TYPE
    SYNTAX  INTEGER {
        data(1)
        ,mgt(2)
        }
    MAX-ACCESS  read-write
    STATUS  current
    DESCRIPTION
        "Chose the port that the sFlow server will connect to"
    ::= { agsFlowConfig 10 }

-- USB Copy

agUSBoperation OBJECT-TYPE
    SYNTAX  INTEGER {
        fromUSB(1),
        toUSB(2)
        }
    MAX-ACCESS  read-write
    STATUS  current
    DESCRIPTION
        "Set operation:
           fromUSB(1): from USB to Flash
           toUSB(2):   from Flash to USB"
    ::= { agUSBCopy 1 }

agUSBfile OBJECT-TYPE
    SYNTAX  DisplayString (SIZE(0..255))
    MAX-ACCESS  read-write
    STATUS  current
    DESCRIPTION
         "USB filename (to copy from or to copy to)"
     ::= { agUSBCopy 2 }

agUSBflashFile OBJECT-TYPE
    SYNTAX  INTEGER {
        boot(1),
        image1(2),
        active(3),
        syslog(4),
        crashdump(5),
        image2(6)
        }
    MAX-ACCESS  read-write
    STATUS  current
    DESCRIPTION
        "Set flash file involved (boot image, image 1,
         active configuration, syslog, crashdump).
         Syslog and crashdump can only be copied to USB.
         (it is forbidden to copy from USB to flash)    "
    ::= { agUSBCopy 3 }

agUSBcopyFile OBJECT-TYPE
    SYNTAX  INTEGER {
        copy(1),
        idle(2),
        inprogress(3),
        complete(4),
        failed(5)
        }
    MAX-ACCESS  read-write
    STATUS  current
    DESCRIPTION
        "When this object is read the current state is returned.
         idle(1) indicates that there is no copy in progess.
         complete(4) indicates that the last copy operation is completed.
         Setting the value to copy(1), will execute the operation (copy
         to or from USB stick).
         If the copy is successful this variable will return the state
         'complete' else it will return 'failed'.
         Once the operation is completed, agUSBcopyFile should be set
         back to 'idle' state so others can issue the copy command via SNMP."
    ::= { agUSBCopy 4 }

agUSBresult OBJECT-TYPE
    SYNTAX  DisplayString (SIZE(0..255))
    MAX-ACCESS  read-only
    STATUS  current
    DESCRIPTION
         "Last USB Copy action result."
     ::= { agUSBCopy 5 }


agQsfp40GCfgTable OBJECT-TYPE
    SYNTAX SEQUENCE OF Qsfp40GPortEntry
    MAX-ACCESS not-accessible
    STATUS current
    DESCRIPTION
        "The QSFP 40G ports configuration table"
    ::= { agQsfp40GConfig 1 }

qsfp40GPortEntry OBJECT-TYPE
    SYNTAX Qsfp40GPortEntry
    MAX-ACCESS not-accessible
    STATUS current
    DESCRIPTION
        "A row in the QSFP 40G configuration table"
    INDEX { qsfpPortNumber }
    ::= { agQsfp40GCfgTable 1 }

Qsfp40GPortEntry ::= SEQUENCE {
    qsfpPortNumber      INTEGER,
    qsfpPortBootedMode  INTEGER,
    qsfpPortSavedMode   INTEGER
    }

qsfpPortNumber OBJECT-TYPE
    SYNTAX INTEGER
    MAX-ACCESS read-only
    STATUS current
    DESCRIPTION
        "The port number"
    ::= { qsfp40GPortEntry 1 }

qsfpPortBootedMode OBJECT-TYPE
    SYNTAX INTEGER {
        mode10G(1),
        mode40G(2)
        }
    MAX-ACCESS read-only
    STATUS current
    DESCRIPTION
        "The booted port configuration, either mode10G(1) for 10 G, or
         mode40G(2) for 40 G mode."
    ::= { qsfp40GPortEntry 2 }

qsfpPortSavedMode OBJECT-TYPE
    SYNTAX INTEGER {
        mode10G(1),
        mode40G(2)
        }
    MAX-ACCESS read-write
    STATUS current
    DESCRIPTION
        "The saved port configuration, either mode10G(1) for 10 G, or
         mode40G(2) for 40 G mode."
    ::= { qsfp40GPortEntry 3 }





 

-- Statistics Group

-- Packet Statistics Group
-- This group represents Packet Statistics information

pktStatsAllocs OBJECT-TYPE
    SYNTAX  Counter32
    MAX-ACCESS  read-only
    STATUS  current
    DESCRIPTION
        "Total number of packet allocations from the packet buffer pool by
         the TCP/IP protocol stack."
    ::= { pktStats 1 }

pktStatsFrees OBJECT-TYPE
    SYNTAX  Counter32
    MAX-ACCESS  read-only
    STATUS  current
    DESCRIPTION
        "Total number of times the packet buffers are freed(released) to the
         packet buffer pool by the TCP/IP protocol stack."
    ::= { pktStats 2 }

pktStatsAllocFails OBJECT-TYPE
    SYNTAX  Counter32
    MAX-ACCESS  read-only
    STATUS  current
    DESCRIPTION
        "Total number of packet allocation failures from the packet buffer
         pool by the TCP/IP protocol stack."
    ::= { pktStats 3}

pktStatsMediums OBJECT-TYPE
    SYNTAX  Gauge32
    MAX-ACCESS  read-only
    STATUS  current
    DESCRIPTION
        "Total number of packet allocations with size greater than 128 bytes
         and less than or equal to 1536 bytes from the packet buffer pool by
         the TCP/IP protocol stack."
    ::= { pktStats 4}

pktStatsJumbos OBJECT-TYPE
    SYNTAX  Gauge32
    MAX-ACCESS  read-only
    STATUS  current
    DESCRIPTION
        "Total number of packet allocations with size larger than 1536 bytes
         from the packet buffer pool by the TCP/IP protocol stack."
    ::= { pktStats 5}

pktStatsSmalls OBJECT-TYPE
    SYNTAX  Gauge32
    MAX-ACCESS  read-only
    STATUS  current
    DESCRIPTION
        "Total number of packet allocations with size less than or eqaul to
         128 bytes from the packet buffer pool by the TCP/IP protocol stack."
    ::= { pktStats 6}

pktStatsMediumsHiWatermark OBJECT-TYPE
    SYNTAX  Counter32
    MAX-ACCESS  read-only
    STATUS  current
    DESCRIPTION
        "The highest number of packet allocations with size greater than
         128 bytes and less than or equal to 1536 bytes from the packet
         buffer pool by the TCP/IP protocol stack."
    ::= { pktStats 7}

pktStatsJumbosHiWatermark OBJECT-TYPE
    SYNTAX  Counter32
    MAX-ACCESS  read-only
    STATUS  current
    DESCRIPTION
        "The highest number of packet allocations with size larger than
         1536 bytes from the packet buffer pool by the TCP/IP protocol stack."
    ::= { pktStats 8}

pktStatsSmallsHiWatermark OBJECT-TYPE
    SYNTAX  Counter32
    MAX-ACCESS  read-only
    STATUS  current
    DESCRIPTION
        "The highest number of packet allocations with size less than or
         equal to 128 bytes from the packet buffer pool by the TCP/IP
         protocol stack."
    ::= { pktStats 9}


-- MP CPU Statisitics Group


mpCpuStatsUtil1Second OBJECT-TYPE
    SYNTAX  DisplayString (SIZE(0..32))
    MAX-ACCESS  read-only
    STATUS  current
    DESCRIPTION
    "The utilization of MP CPU over 1 second. It shows the percentage."
    ::= { mpCpuStats 1 }

mpCpuStatsUtil5Seconds OBJECT-TYPE
    SYNTAX  DisplayString (SIZE(0..32))
    MAX-ACCESS  read-only
    STATUS  current
    DESCRIPTION
    "The utilization of MP CPU  over 5 seconds. It shows the percentage."
    ::= { mpCpuStats 2 }

mpCpuStatsUtil1Minute OBJECT-TYPE
    SYNTAX  DisplayString (SIZE(0..32))
    MAX-ACCESS  read-only
    STATUS  current
    DESCRIPTION
    "The utilization of MP CPU over 1 minute. It shows the percentage."
    ::= { mpCpuStats 3 }

mpCpuStatsUtil5Minutes OBJECT-TYPE
    SYNTAX  DisplayString (SIZE(0..32))
    MAX-ACCESS  read-only
    STATUS  current
    DESCRIPTION
    "The utilization of MP CPU over 5 minutes. It shows the percentage."
    ::= { mpCpuStats 6 }

-- Stats for per thread CPU utilization

cpuUtilProcessStatsTable OBJECT-TYPE
    SYNTAX  SEQUENCE OF CpuUtilProcessStatsTableEntry
    MAX-ACCESS  not-accessible
    STATUS  current
    DESCRIPTION
        "The table of CPU utilization per process statistics."
    ::= { mpCpuStats 5 }

cpuUtilProcessStatsTableEntry OBJECT-TYPE
    SYNTAX  CpuUtilProcessStatsTableEntry
    MAX-ACCESS  not-accessible
    STATUS  current
    DESCRIPTION
	"A row in the CPU utilization stats per process table."
    INDEX    { processId }
    ::= { cpuUtilProcessStatsTable 1 }

CpuUtilProcessStatsTableEntry ::=
    SEQUENCE {
    processId	
		Integer32,
    processName
        DisplayString,
    cpuProcessUtil1Sec	
        DisplayString,
    cpuProcessUtil5Sec	
        DisplayString,
    cpuProcessUtil1Min
        DisplayString,
	cpuProcessUtil5Min
        DisplayString,
    processStatus
        DisplayString
    }

processId OBJECT-TYPE
    SYNTAX  Integer32
    MAX-ACCESS  read-only
    STATUS  current
    DESCRIPTION
        "The process ID."
    ::= { cpuUtilProcessStatsTableEntry 1 }

processName OBJECT-TYPE
    SYNTAX  DisplayString (SIZE(0..32))
    MAX-ACCESS  read-only
    STATUS  current
    DESCRIPTION
         "Process Name."
    ::= { cpuUtilProcessStatsTableEntry 2 }

cpuProcessUtil1Sec OBJECT-TYPE
    SYNTAX  DisplayString (SIZE(0..32))
    MAX-ACCESS  read-only
    STATUS  current
    DESCRIPTION
        "The utilization of MP CPU over 1 second.
         It shows the percentage."
    ::= { cpuUtilProcessStatsTableEntry 3 }

cpuProcessUtil5Sec OBJECT-TYPE
    SYNTAX  DisplayString (SIZE(0..32))
    MAX-ACCESS  read-only
    STATUS  current
    DESCRIPTION
        "The utilization of MP CPU over 5 seconds.
         It shows the percentage."
    ::= { cpuUtilProcessStatsTableEntry 4 }

cpuProcessUtil1Min OBJECT-TYPE
    SYNTAX  DisplayString (SIZE(0..32))
    MAX-ACCESS  read-only
    STATUS  current
    DESCRIPTION
        "The utilization of MP CPU over 1 min.
         It shows the percentage."
    ::= { cpuUtilProcessStatsTableEntry 5 }

cpuProcessUtil5Min OBJECT-TYPE
    SYNTAX  DisplayString (SIZE(0..32))
    MAX-ACCESS  read-only
    STATUS  current
    DESCRIPTION
        "The utilization of MP CPU over 5 min.
         It shows the percentage."
    ::= { cpuUtilProcessStatsTableEntry 6 }

processStatus OBJECT-TYPE
    SYNTAX  DisplayString (SIZE(0..32))
    MAX-ACCESS  read-only
    STATUS  current
    DESCRIPTION
         "Process Status"
    ::= { cpuUtilProcessStatsTableEntry 7 }



--
-- Port statistics table
--
portStatsTable OBJECT-TYPE
    SYNTAX  SEQUENCE OF PortStatsTableEntry
    MAX-ACCESS  not-accessible
    STATUS  current
    DESCRIPTION
        "The table of port statistics."
    ::= { portStats 1 }

portStatsTableEntry OBJECT-TYPE
    SYNTAX  PortStatsTableEntry
    MAX-ACCESS  not-accessible
    STATUS  current
    DESCRIPTION
        "A row in the port stats table."
    INDEX   { portStatsIndx }
    ::= { portStatsTable 1 }

PortStatsTableEntry ::=
    SEQUENCE {
	portStatsIndx
	    PortNumber,
	portStatsPhyIfInOctets
	    Counter32,
	portStatsPhyIfInUcastPkts
	    Counter32,
	portStatsPhyIfInNUcastPkts
	    Counter32,
	portStatsPhyIfInDiscards
	    Counter32,
	portStatsPhyIfInErrors
	    Counter32,
	portStatsPhyIfInUnknownProtos
	    Counter32,
	portStatsPhyIfOutOctets
	    Counter32,
	portStatsPhyIfOutUcastPkts
	    Counter32,
	portStatsPhyIfOutNUcastPkts
	    Counter32,
	portStatsPhyIfOutDiscards
	    Counter32,
	portStatsPhyIfOutErrors
	    Counter32,
	portStatsPhyIfOutQLen
	    Gauge32,
        portStatsPhyIfInBroadcastPkts
            Counter32,
        portStatsPhyIfOutBroadcastPkts
            Counter32,
        portStatsPhyIfInMulticastPkts
            Counter32,
        portStatsPhyIfOutMulticastPkts
            Counter32,
	portStatsClear
            INTEGER
        ,portStatsLinkStateChange
            Counter32
        ,portStatsPhyIfInFctlPkts
            Counter32
        ,portStatsPhyIfOutFctlPkts
            Counter32
        ,portStatsPhyIfInFctlPktsRate
            Counter32
        ,portStatsPhyIfOutFctlPktsRate
            Counter32
        ,portStatsPhyIfIngDiscdVlan
	        Counter32
        ,portStatsPhyIfIngDiscdEgrMap       
            Counter32
        ,portStatsPhyIfIngDiscdFilter       
            Counter32
        ,portStatsPhyIfIngDiscdPolicy       
            Counter32
        ,portStatsPhyIfIngDiscdNonFwdStat       
            Counter32
        ,portStatsPhyIfIngDiscdIbpCbp
            Counter32
        ,portStatsDot1PortInFrames
            Counter32
        ,portStatsDot1PortOutFrames
            Counter32
        ,portStatsDot1PortInDiscards
            Counter32
        ,portStatsDot1TpLearnedEntryDiscards
            Counter32
        ,portStatsDot1StpPortForwardTransitions
            Counter32
        ,portStatsPhyIfEgrHOLBlockDiscd
          Counter32
        ,portStatsPhyIfEgrMMUDiscd
          Counter32
        ,portStatsPhyIfEgrCellErrDiscd
          Counter32
        ,portStatsPhyIfEgrMMUAgeDiscd
          Counter32
        ,portStatsPhyIfEgrOtherDiscd
          Counter32
    }

tcpControlBlocksTable OBJECT-TYPE
   SYNTAX SEQUENCE OF TcpControlBlocksTableEntry
   MAX-ACCESS not-accessible
   STATUS current
   DESCRIPTION
      "All TCP allocated control blocks "
   ::= { mpTcbStats 1 }

tcpControlBlocksTableEntry OBJECT-TYPE
   SYNTAX TcpControlBlocksTableEntry
   MAX-ACCESS not-accessible
   STATUS current
   DESCRIPTION
     "A row in the TCP control blocks table. "
  INDEX { tcpControlBlocksIndx }
  ::= { tcpControlBlocksTable 1 }

TcpControlBlocksTableEntry ::=
   SEQUENCE {
     tcpControlBlocksIndx
         Integer32,
     destAddr
        DisplayString,
    remotePort
         Gauge32,
    sourceAddr
         DisplayString,
   localPort
         Gauge32,
   portType
         DisplayString,
   portState
         DisplayString,
   state
         DisplayString
}

tcpControlBlocksIndx OBJECT-TYPE
   SYNTAX Integer32
   MAX-ACCESS read-only
   STATUS current
   DESCRIPTION
       "The TCP blocks index."
  ::= { tcpControlBlocksTableEntry 1 }

  destAddr OBJECT-TYPE
    SYNTAX DisplayString
    MAX-ACCESS read-only
    STATUS current
    DESCRIPTION
      "The TCP block destination address."
    ::= { tcpControlBlocksTableEntry 2 }

  remotePort OBJECT-TYPE
    SYNTAX Gauge32
    MAX-ACCESS read-only
    STATUS current
    DESCRIPTION
      "Tcp informations concerning the remote port"
    ::= { tcpControlBlocksTableEntry 3}

  sourceAddr OBJECT-TYPE
    SYNTAX DisplayString 
    MAX-ACCESS read-only
    STATUS current
    DESCRIPTION
      "IP address of the source of the Tcp block"
    ::= { tcpControlBlocksTableEntry 4}

  localPort OBJECT-TYPE
    SYNTAX Gauge32
    MAX-ACCESS read-only
    STATUS current
  DESCRIPTION
      "Tcp informations concerning the local  port"
    ::= { tcpControlBlocksTableEntry 5}


  portType OBJECT-TYPE
    SYNTAX DisplayString
    MAX-ACCESS read-only
    STATUS current
    DESCRIPTION
     "The type of the local port"
    ::= { tcpControlBlocksTableEntry 7 }

  portState OBJECT-TYPE
    SYNTAX DisplayString
    MAX-ACCESS read-only
    STATUS current
    DESCRIPTION
     " The state of the local port"
    ::= { tcpControlBlocksTableEntry 8 }


  state OBJECT-TYPE
    SYNTAX DisplayString
    MAX-ACCESS read-only
    STATUS current
    DESCRIPTION
      "The state of the Tcp"
    ::= { tcpControlBlocksTableEntry 6 }


  tcpMGMTControlBlocksTable OBJECT-TYPE
     SYNTAX SEQUENCE OF TcpMGMTTableEntry
     MAX-ACCESS not-accessible
     STATUS current
     DESCRIPTION
        "All TCP allocated control blocks on MGMT port"
     ::= { mpTcbStats 2 }

  tcpMGMTTableEntry OBJECT-TYPE
     SYNTAX TcpMGMTTableEntry
     MAX-ACCESS not-accessible
     STATUS current
     DESCRIPTION
     " A row in the TCP on MGMT port table. "
     INDEX { tcpMGMTIndx }
     ::= { tcpMGMTControlBlocksTable 1 }

  TcpMGMTTableEntry ::=
     SEQUENCE {
     tcpMGMTIndx
         Integer32,
     recvQ
         Integer32,
     sentQ
         Integer32,
     localAddress
         DisplayString,
     foreignAddress
         DisplayString,
     stateMgmt
         DisplayString
  }

  tcpMGMTIndx OBJECT-TYPE
     SYNTAX Integer32
     MAX-ACCESS read-only
     STATUS  current
     DESCRIPTION
       " Index in the tcpMGMTControlBlocksTable table."
     ::= { tcpMGMTTableEntry 1 }

  recvQ OBJECT-TYPE
    SYNTAX Integer32
    MAX-ACCESS read-only
    STATUS current
    DESCRIPTION
     "The size of the received TCP queue."
    ::= { tcpMGMTTableEntry 2 }

  sentQ OBJECT-TYPE
    SYNTAX Integer32
    MAX-ACCESS read-only
    STATUS current
    DESCRIPTION
     "The size of the sent TCP blocks queue."
    ::= { tcpMGMTTableEntry 3 }

localAddress OBJECT-TYPE
    SYNTAX DisplayString
    MAX-ACCESS read-only
    STATUS current
    DESCRIPTION
     "The local address for the TCP."
    ::= { tcpMGMTTableEntry 4 }

  foreignAddress OBJECT-TYPE
    SYNTAX DisplayString
    MAX-ACCESS read-only
    STATUS current
    DESCRIPTION
     "The remote address for the TCP."
    ::= { tcpMGMTTableEntry 5  }

  stateMgmt OBJECT-TYPE
    SYNTAX DisplayString
    MAX-ACCESS read-only
    STATUS current
    DESCRIPTION
     "The port's state."
    ::= { tcpMGMTTableEntry 6 }



  udpControlBlocksTable OBJECT-TYPE
     SYNTAX SEQUENCE OF UdpControlBlocksTableEntry
     MAX-ACCESS not-accessible
     STATUS current
     DESCRIPTION
       "All UDP control blocks in use"
     ::= { mpUdpStats 1 }

udpControlBlocksTableEntry OBJECT-TYPE
     SYNTAX UdpControlBlocksTableEntry
     MAX-ACCESS not-accessible
     STATUS current
     DESCRIPTION
        "A row in the UDP control blocks table. "
     INDEX { udpMpLocalPort }
     ::= { udpControlBlocksTable 1 }

  UdpControlBlocksTableEntry ::=
    SEQUENCE {
       udpMpLocalPort
           Integer32,
      udpMpState
           DisplayString
  }

  udpMpLocalPort OBJECT-TYPE
     SYNTAX Integer32
     MAX-ACCESS read-only
     STATUS current
     DESCRIPTION
        "The current UDP local port."
     ::= { udpControlBlocksTableEntry 1 }

  udpMpState OBJECT-TYPE
     SYNTAX DisplayString
     MAX-ACCESS read-only
     STATUS current
     DESCRIPTION
        " The port's state. "
    ::= { udpControlBlocksTableEntry 2 }


  udpMGMTControlBlocksTable OBJECT-TYPE
     SYNTAX SEQUENCE OF UdpMGMTTableEntry
     MAX-ACCESS not-accessible
     STATUS current
     DESCRIPTION
        "All UDP control blocks allocated  on MGMT port"
     ::= { mpUdpStats 2 }

udpMGMTTableEntry OBJECT-TYPE
     SYNTAX UdpMGMTTableEntry
     MAX-ACCESS not-accessible
     STATUS current
     DESCRIPTION
       " A row in the UDP on MGMT port table. "
     INDEX { udpMGMTIndx }
     ::= { udpMGMTControlBlocksTable 1 }

  UdpMGMTTableEntry ::=
     SEQUENCE {
     udpMGMTIndx
         Integer32,
     recvQUdp
         Integer32,
     sentQUdp
         Integer32,
     localAddressUdp
         DisplayString,
     foreignAddressUdp
         DisplayString,
     stateMgmtUdp
         DisplayString
  }

  udpMGMTIndx OBJECT-TYPE
     SYNTAX Integer32
     MAX-ACCESS read-only
     STATUS  current
     DESCRIPTION
       " Index in the udpMGMTControlBlocksTable table."
     ::= { udpMGMTTableEntry 1 }

  recvQUdp OBJECT-TYPE
    SYNTAX Integer32
    MAX-ACCESS read-only
    STATUS current
    DESCRIPTION
     "The size of the received UDP queue."
    ::= { udpMGMTTableEntry 2 }

  sentQUdp OBJECT-TYPE
    SYNTAX Integer32
    MAX-ACCESS read-only
    STATUS current
    DESCRIPTION
     "The size of the sent UDP blocks queue."
    ::= { udpMGMTTableEntry 3 }

localAddressUdp OBJECT-TYPE
    SYNTAX DisplayString
    MAX-ACCESS read-only
    STATUS current
    DESCRIPTION
     "The local address for the UDP."
    ::= { udpMGMTTableEntry 4 }

  foreignAddressUdp OBJECT-TYPE
    SYNTAX DisplayString
    MAX-ACCESS read-only
    STATUS current
    DESCRIPTION
     "The remote address for the UDP."
    ::= { udpMGMTTableEntry 5  }

  stateMgmtUdp OBJECT-TYPE
    SYNTAX DisplayString
    MAX-ACCESS read-only
    STATUS current
    DESCRIPTION
     "The port's state."
    ::= { udpMGMTTableEntry 6 }





portStatsIndx OBJECT-TYPE
    SYNTAX  PortNumber
    MAX-ACCESS  read-only
    STATUS  current
    DESCRIPTION
        "The port index."
    ::= { portStatsTableEntry 1 }

portStatsPhyIfInOctets OBJECT-TYPE
    SYNTAX  Counter32
    MAX-ACCESS  read-only
    STATUS  current
    DESCRIPTION
	    "The total number of octets received on the
	    interface, including framing characters."
    ::= { portStatsTableEntry 2 }

portStatsPhyIfInUcastPkts OBJECT-TYPE
    SYNTAX  Counter32
    MAX-ACCESS  read-only
    STATUS  current
    DESCRIPTION
	    "The number of subnetwork-unicast packets
	    delivered to a higher-layer protocol."
    ::= { portStatsTableEntry 3 }

portStatsPhyIfInNUcastPkts OBJECT-TYPE
    SYNTAX  Counter32
    MAX-ACCESS  read-only
    STATUS  current
    DESCRIPTION
	    "The number of non-unicast (i.e., subnetwork-
	    broadcast or subnetwork-multicast) packets
	    delivered to a higher-layer protocol."
    ::= { portStatsTableEntry 4 }

portStatsPhyIfInDiscards OBJECT-TYPE
    SYNTAX  Counter32
    MAX-ACCESS  read-only
    STATUS  current
    DESCRIPTION
	    "The number of inbound packets which were chosen
	    to be discarded even though no errors had been
	    detected to prevent their being deliverable to a
	    higher-layer protocol.  One possible reason for
	    discarding such a packet could be to free up
	    buffer space."
    ::= { portStatsTableEntry 5 }

portStatsPhyIfInErrors OBJECT-TYPE
    SYNTAX  Counter32
    MAX-ACCESS  read-only
    STATUS  current
    DESCRIPTION
	    "The number of inbound packets that contained
	    errors preventing them from being deliverable to a
	    higher-layer protocol."
    ::= { portStatsTableEntry 6 }

portStatsPhyIfInUnknownProtos OBJECT-TYPE
    SYNTAX  Counter32
    MAX-ACCESS  read-only
    STATUS  current
    DESCRIPTION
	    "The number of packets received via the interface
	    which were discarded because of an unknown or
	    unsupported protocol."
    ::= { portStatsTableEntry 7 }

portStatsPhyIfOutOctets OBJECT-TYPE
    SYNTAX  Counter32
    MAX-ACCESS  read-only
    STATUS  current
    DESCRIPTION
	    "The total number of octets transmitted out of the
	    interface, including framing characters."
    ::= { portStatsTableEntry 8 }

portStatsPhyIfOutUcastPkts OBJECT-TYPE
    SYNTAX  Counter32
    MAX-ACCESS  read-only
    STATUS  current
    DESCRIPTION
	    "The total number of packets that higher-level
	    protocols requested be transmitted to a
	    subnetwork-unicast address, including those that
	    were discarded or not sent."
    ::= { portStatsTableEntry 9 }

portStatsPhyIfOutNUcastPkts OBJECT-TYPE
    SYNTAX  Counter32
    MAX-ACCESS  read-only
    STATUS  current
    DESCRIPTION
	    "The total number of packets that higher-level
	    protocols requested be transmitted to a non-
	    unicast (i.e., a subnetwork-broadcast or
	    subnetwork-multicast) address, including those
	    that were discarded or not sent."
    ::= { portStatsTableEntry 10 }

portStatsPhyIfOutDiscards OBJECT-TYPE
    SYNTAX  Counter32
    MAX-ACCESS  read-only
    STATUS  current
    DESCRIPTION
	    "The number of outbound packets which were chosen
	    to be discarded even though no errors had been
	    detected to prevent their being transmitted.  One
	    possible reason for discarding such a packet could
	    be to free up buffer space."
    ::= { portStatsTableEntry 11 }

portStatsPhyIfOutErrors OBJECT-TYPE
    SYNTAX  Counter32
    MAX-ACCESS  read-only
    STATUS  current
    DESCRIPTION
	    "The number of outbound packets that could not be
	    transmitted because of errors."
    ::= { portStatsTableEntry 12 }

portStatsPhyIfOutQLen OBJECT-TYPE
    SYNTAX  Gauge32
    MAX-ACCESS  read-only
    STATUS  current
    DESCRIPTION
	    "The length of the output packet queue (in
	    packets)."
    ::= { portStatsTableEntry 13 }

portStatsPhyIfInBroadcastPkts OBJECT-TYPE
    SYNTAX  Counter32
    MAX-ACCESS  read-only
    STATUS  current
    DESCRIPTION
            "The number of packets, delivered by this sub-layer to
            a higher (sub-)layer, which were addressed to a
            broadcast address at this sub-layer."
    ::= { portStatsTableEntry 14 }

portStatsPhyIfOutBroadcastPkts OBJECT-TYPE
    SYNTAX  Counter32
    MAX-ACCESS  read-only
    STATUS  current
    DESCRIPTION
	    "The total number of packets that higher-level
            protocols requested be transmitted, and which were
            addressed to a broadcast address at this sub-layer,
            including those that were discarded or not sent."
    ::= { portStatsTableEntry 15 }

portStatsPhyIfInMulticastPkts OBJECT-TYPE
    SYNTAX  Counter32
    MAX-ACCESS  read-only
    STATUS  current
    DESCRIPTION
            "The number of packets, delivered by this sub-layer to
            a higher (sub-)layer, which were addressed to a
            multicast address at this sub-layer."
    ::= { portStatsTableEntry 17 }

portStatsPhyIfOutMulticastPkts OBJECT-TYPE
    SYNTAX  Counter32
    MAX-ACCESS  read-only
    STATUS  current
    DESCRIPTION
            "The total number of packets that higher-level
            protocols requested be transmitted, and which were
            addressed to a multicast address at this sub-layer,
            including those that were discarded or not sent."
    ::= { portStatsTableEntry 18 }

portStatsClear OBJECT-TYPE
    SYNTAX  INTEGER {
        ok(1),
        clear(2)
        }
    MAX-ACCESS  read-write
    STATUS  current
    DESCRIPTION
            "Setting this value to clear(2) clears the stats for this port."
    ::= { portStatsTableEntry 16 }


portStatsLinkStateChange OBJECT-TYPE
    SYNTAX           Counter32
    MAX-ACCESS       read-only
    STATUS           current
    DESCRIPTION
            "Number of link state changes."
    ::= { portStatsTableEntry 20 }

portStatsPhyIfInFctlPkts OBJECT-TYPE
    SYNTAX  Counter32
    MAX-ACCESS  read-only
    STATUS  current
    DESCRIPTION
            "The number of inbound flow control packets."
    ::= { portStatsTableEntry 21 }

portStatsPhyIfOutFctlPkts OBJECT-TYPE
    SYNTAX  Counter32
    MAX-ACCESS  read-only
    STATUS  current
    DESCRIPTION
            "The number of outbound flow control packets."
    ::= { portStatsTableEntry 22 }

portStatsPhyIfInFctlPktsRate OBJECT-TYPE
    SYNTAX  Counter32
    MAX-ACCESS  read-only
    STATUS  current
    DESCRIPTION
            "The number of inbound flow control packets per second."
    ::= { portStatsTableEntry 23 }

portStatsPhyIfOutFctlPktsRate OBJECT-TYPE
    SYNTAX  Counter32
    MAX-ACCESS  read-only
    STATUS  current
    DESCRIPTION
            "The number of outbound flow control packets per second."
    ::= { portStatsTableEntry 24 }

portStatsPhyIfIngDiscdVlan OBJECT-TYPE
    SYNTAX  Counter32
    MAX-ACCESS  read-only
    STATUS  current
    DESCRIPTION
            "The number of packets, discarded because of VLAN."
    ::= { portStatsTableEntry 25 }

portStatsPhyIfIngDiscdEgrMap OBJECT-TYPE                             
    SYNTAX  Counter32
    MAX-ACCESS  read-only
    STATUS  current
    DESCRIPTION
            "The number of packets, discarded because of empty egress portmap."
    ::= { portStatsTableEntry 26 }

portStatsPhyIfIngDiscdFilter OBJECT-TYPE                             
    SYNTAX  Counter32
    MAX-ACCESS  read-only
    STATUS  current
    DESCRIPTION
            "The number of packets, discarded because of filter."
    ::= { portStatsTableEntry 27 }

portStatsPhyIfIngDiscdPolicy OBJECT-TYPE                             
    SYNTAX  Counter32
    MAX-ACCESS  read-only
    STATUS  current
    DESCRIPTION
            "The number of packets, discarded because of policy."
    ::= { portStatsTableEntry 28 }

portStatsPhyIfIngDiscdNonFwdStat OBJECT-TYPE                             
    SYNTAX  Counter32
    MAX-ACCESS  read-only
    STATUS  current
    DESCRIPTION
            "The number of packets, discarded because of Non-Forwarding State."
    ::= { portStatsTableEntry 29 }

portStatsPhyIfIngDiscdIbpCbp OBJECT-TYPE                             
    SYNTAX  Counter32
    MAX-ACCESS  read-only
    STATUS  current
    DESCRIPTION
            "The number of packets discarded because of IBP/CBP."
    ::= { portStatsTableEntry 30 }

portStatsDot1PortInFrames OBJECT-TYPE                             
    SYNTAX  Counter32
    MAX-ACCESS  read-only
    STATUS  current
    DESCRIPTION
            "The number of IN frames per port."
    ::= { portStatsTableEntry 31 }

portStatsDot1PortOutFrames OBJECT-TYPE                             
    SYNTAX  Counter32
    MAX-ACCESS  read-only
    STATUS  current
    DESCRIPTION
            "The number of OUT frames per port."
    ::= { portStatsTableEntry 32 }

portStatsDot1PortInDiscards OBJECT-TYPE                             
    SYNTAX  Counter32
    MAX-ACCESS  read-only
    STATUS  current
    DESCRIPTION
            "The number of IN packets discarded per port."
    ::= { portStatsTableEntry 33 }

portStatsDot1TpLearnedEntryDiscards OBJECT-TYPE                             
    SYNTAX  Counter32
    MAX-ACCESS  read-only
    STATUS  current
    DESCRIPTION
            "The number of Dot1Tp learned entries discarded."
    ::= { portStatsTableEntry 34 }

portStatsDot1StpPortForwardTransitions OBJECT-TYPE                             
    SYNTAX  Counter32
    MAX-ACCESS  read-only
    STATUS  current
    DESCRIPTION
            "The number of transitions ...."
    ::= { portStatsTableEntry 35 }


portQoSCounterTable OBJECT-TYPE
    SYNTAX  SEQUENCE OF PortQoSCounterTableEntry
    MAX-ACCESS  not-accessible
    STATUS  current
    DESCRIPTION
        "The table for QoS counters."
    ::= { portStats 9 }

portQoSCounterTableEntry OBJECT-TYPE
    SYNTAX PortQoSCounterTableEntry
    MAX-ACCESS  not-accessible
    STATUS  current
    DESCRIPTION
        "A row in the port QoS table."
    INDEX   { portQoSIndex, queueQoSIndex }
    ::= { portQoSCounterTable 1 }

PortQoSCounterTableEntry ::= SEQUENCE {
        portQoSIndex             PortNumber, 
        queueQoSIndex            Integer32,
        txPackets                Counter64,
        droppedPackets           Counter64,
        txBytes                  Counter64,
        droppedBytes             Counter64,
        txPacketsRate            Counter64,
        droppedPacketsRate       Counter64,
        txBytesRate              Counter64,
        droppedBytesRate         Counter64
   }

portQoSIndex OBJECT-TYPE
      SYNTAX PortNumber
      MAX-ACCESS  read-only
      STATUS  current
      DESCRIPTION
          "The index of the port"
      ::= { portQoSCounterTableEntry 1 }

queueQoSIndex OBJECT-TYPE
      SYNTAX  Integer32
      MAX-ACCESS  read-only
      STATUS  current
      DESCRIPTION
          "The index of the queue per port."
      ::= { portQoSCounterTableEntry 2 }

txPackets  OBJECT-TYPE
      SYNTAX  Counter64
      MAX-ACCESS  read-only
      STATUS  current
      DESCRIPTION
          "The total Tx packets."
      ::= { portQoSCounterTableEntry 3 }

droppedPackets OBJECT-TYPE
      SYNTAX  Counter64
      MAX-ACCESS  read-only
      STATUS  current
      DESCRIPTION
          "The dropped packets."
      ::= { portQoSCounterTableEntry 4 }

txBytes  OBJECT-TYPE
      SYNTAX  Counter64
      MAX-ACCESS  read-only
      STATUS  current
      DESCRIPTION
          "The total Tx bytes."
      ::= { portQoSCounterTableEntry 5 }

droppedBytes OBJECT-TYPE
      SYNTAX  Counter64
      MAX-ACCESS  read-only
      STATUS  current
      DESCRIPTION
          "The dropped bytes."
      ::= { portQoSCounterTableEntry 6 }

txPacketsRate  OBJECT-TYPE
      SYNTAX  Counter64
      MAX-ACCESS  read-only
      STATUS  current
      DESCRIPTION
          "The Tx packets rate."
      ::= { portQoSCounterTableEntry 7 }

droppedPacketsRate OBJECT-TYPE
      SYNTAX  Counter64
      MAX-ACCESS  read-only
      STATUS  current
      DESCRIPTION
          "The dropped packets rate."
      ::= { portQoSCounterTableEntry 8 }

txBytesRate  OBJECT-TYPE
      SYNTAX  Counter64
      MAX-ACCESS  read-only
      STATUS  current
      DESCRIPTION
          "The Tx bytes rate."
      ::= { portQoSCounterTableEntry 9 }

droppedBytesRate OBJECT-TYPE
      SYNTAX  Counter64
      MAX-ACCESS  read-only
      STATUS  current
      DESCRIPTION
          "The dropped bytes rate."
      ::= { portQoSCounterTableEntry 10 }


portStatsPhyIfEgrHOLBlockDiscd OBJECT-TYPE
    SYNTAX  Counter32
    MAX-ACCESS  read-only
    STATUS  current
    DESCRIPTION
            "The number of packets, discarded because of HOL Blocking."
    ::= { portStatsTableEntry 36 }

portStatsPhyIfEgrMMUDiscd OBJECT-TYPE
    SYNTAX  Counter32
    MAX-ACCESS  read-only
    STATUS  current
    DESCRIPTION
            "The number of packets, discarded by MMU because of zero port bitmap."
    ::= { portStatsTableEntry 37 }

portStatsPhyIfEgrCellErrDiscd OBJECT-TYPE
    SYNTAX  Counter32
    MAX-ACCESS  read-only
    STATUS  current
    DESCRIPTION
            "The number of packets, discarded because of Cell Errors or purging."
    ::= { portStatsTableEntry 38 }

portStatsPhyIfEgrMMUAgeDiscd OBJECT-TYPE
    SYNTAX  Counter32
    MAX-ACCESS  read-only
    STATUS  current
    DESCRIPTION
            "The number of packets, discarded because of MMU Aging. Applicable in
             10/100 mode, incremented for frames aborted which were deferred for an
             excessive period of time."
    ::= { portStatsTableEntry 39 }

portStatsPhyIfEgrOtherDiscd OBJECT-TYPE
    SYNTAX  Counter32
    MAX-ACCESS  read-only
    STATUS  current
    DESCRIPTION
            "The number of packets, discarded because of Other reasons."
    ::= { portStatsTableEntry 40 }

portMgmtStatsTable OBJECT-TYPE
    SYNTAX  SEQUENCE OF PortMgmtStatsTableEntry
    MAX-ACCESS  not-accessible
    STATUS  current
    DESCRIPTION
        "The table of port statistics."
    ::= { portStats 3 }

portMgmtStatsTableEntry OBJECT-TYPE
    SYNTAX  PortMgmtStatsTableEntry
    MAX-ACCESS  not-accessible
    STATUS  current
    DESCRIPTION
        "A row in the management port stats table."
    INDEX   { portMgmtStatsIndx }
    ::= { portMgmtStatsTable 1 }

PortMgmtStatsTableEntry ::=
    SEQUENCE {
        portMgmtStatsIndx
            Integer32,
        portMgmtStatsRxBytes
            Counter32,
        portMgmtStatsTxBytes
            Counter32,
        portMgmtStatsRxpackets
            Counter32,
        portMgmtStatsTxpackets
            Counter32,
        portMgmtStatsRxErrors
            Counter32,
        portMgmtStatsTxErrors
            Counter32,
        portMgmtStatsRxDropped
            Counter32,
        portMgmtStatsTxDropped
            Counter32,
        portMgmtStatsRxOverruns
            Counter32,
        portMgmtStatsTxOverruns
            Counter32,
        portMgmtStatsRxFrame
            Counter32,
        portMgmtStatsTxCarrier
            Counter32,
        portMgmtStatsRxMulticast
            Counter32,
        portMgmtStatsTxCollisions
            Counter32
}

portMgmtStatsIndx OBJECT-TYPE
    SYNTAX  Integer32
    MAX-ACCESS  read-only
    STATUS  current
    DESCRIPTION
        "The management port index."
    ::= { portMgmtStatsTableEntry 1 }

portMgmtStatsRxBytes OBJECT-TYPE
    SYNTAX  Counter32
    MAX-ACCESS  read-only
    STATUS  current
    DESCRIPTION
            "The total number of bytes received."
    ::= { portMgmtStatsTableEntry 2 }

portMgmtStatsTxBytes OBJECT-TYPE
    SYNTAX  Counter32
    MAX-ACCESS  read-only
    STATUS  current
    DESCRIPTION
            "The total number of bytes transmitted."
    ::= { portMgmtStatsTableEntry 3 }

portMgmtStatsRxpackets OBJECT-TYPE
    SYNTAX  Counter32
    MAX-ACCESS  read-only
    STATUS  current
    DESCRIPTION
        "Total number of packet allocations from the packet buffer pool by
         the TCP/IP protocol stack."
    ::= { portMgmtStatsTableEntry 4 }

portMgmtStatsTxpackets OBJECT-TYPE
    SYNTAX  Counter32
    MAX-ACCESS  read-only
    STATUS  current
    DESCRIPTION
        "Total number of packet allocations from the packet buffer pool by
         the TCP/IP protocol stack."
    ::= { portMgmtStatsTableEntry 5 }

portMgmtStatsRxErrors OBJECT-TYPE
    SYNTAX  Counter32
    MAX-ACCESS  read-only
    STATUS  current
    DESCRIPTION
            "The number of inbound packets that contained
             errors preventing them from being deliverable to a
             higher-layer protocol."
    ::= { portMgmtStatsTableEntry 6 }

portMgmtStatsTxErrors OBJECT-TYPE
    SYNTAX  Counter32
    MAX-ACCESS  read-only
    STATUS  current
    DESCRIPTION
            "The number of outbound packets that contained
             errors preventing them from being deliverable to a
             higher-layer protocol."
    ::= { portMgmtStatsTableEntry 7 }

portMgmtStatsRxDropped OBJECT-TYPE
    SYNTAX  Counter32
    MAX-ACCESS  read-only
    STATUS  current
    DESCRIPTION
            "The number of inbound packets that were dropped."
    ::= { portMgmtStatsTableEntry 8 }

portMgmtStatsTxDropped OBJECT-TYPE
    SYNTAX  Counter32
    MAX-ACCESS  read-only
    STATUS  current
    DESCRIPTION
            "The number of outbound packets that were dropped."
    ::= { portMgmtStatsTableEntry 9 }

portMgmtStatsRxOverruns OBJECT-TYPE
    SYNTAX  Counter32
    MAX-ACCESS  read-only
    STATUS  current
    DESCRIPTION
            "The number of data overruns over this link."
    ::= { portMgmtStatsTableEntry 10 }

portMgmtStatsTxOverruns OBJECT-TYPE
    SYNTAX  Counter32
    MAX-ACCESS  read-only
    STATUS  current
    DESCRIPTION
            "The number of data overruns over this link."
    ::= { portMgmtStatsTableEntry 11 }

portMgmtStatsRxFrame OBJECT-TYPE
    SYNTAX  Counter32
    MAX-ACCESS  read-only
    STATUS  current
    DESCRIPTION
            "The number of frames received on this link."
    ::= { portMgmtStatsTableEntry 12 }

portMgmtStatsTxCarrier OBJECT-TYPE
    SYNTAX  Counter32
    MAX-ACCESS  read-only
    STATUS  current
    DESCRIPTION
        "The number of times that the carrier sense
         condition was lost or never asserted when
         attempting to transmit a frame on a this
         interface."
    ::= { portMgmtStatsTableEntry 13 }

portMgmtStatsRxMulticast OBJECT-TYPE
    SYNTAX  Counter32
    MAX-ACCESS  read-only
    STATUS  current
    DESCRIPTION
            "The total number of multicast packets received."
    ::= { portMgmtStatsTableEntry 14 }

portMgmtStatsTxCollisions OBJECT-TYPE
    SYNTAX  Counter32
    MAX-ACCESS  read-only
    STATUS  current
    DESCRIPTION
            "The number of collisions on this outbound segment."
    ::= { portMgmtStatsTableEntry 15 }


allportsStatsTable OBJECT-TYPE
    SYNTAX      SEQUENCE OF AllportsStatsTableEntry
    MAX-ACCESS  not-accessible
    STATUS      current
    DESCRIPTION
        "The table of all ports statistics."
    ::= { portStats 4 }

allportsStatsTableEntry OBJECT-TYPE
    SYNTAX      AllportsStatsTableEntry
    MAX-ACCESS  not-accessible
    STATUS      current
    DESCRIPTION
        "A row in the table of all ports statistics."
    INDEX   { allportsStatsIndx }
    ::= { allportsStatsTable 1 }

AllportsStatsTableEntry ::=
    SEQUENCE {
        allportsStatsIndx                      PortNumber,
        allportsStatsDescr                     DisplayString,
        allportsStatsSpeed		       INTEGER,
        allportsStatsPhysAddress	       PhysAddress,
        allportsStatsAdminStatus               INTEGER,
        allportsStatsOperStatus                INTEGER,
        allportsStatsInOctets                  Counter32,
        allportsStatsOutOctets                 Counter32,
        allportsStatsInPkts                    Counter32,
        allportsStatsOutPkts                   Counter32,
        allportsStatsInUcast                   DisplayString,
        allportsStatsOutUcast                  DisplayString,
        allportsStatsInBcast                   DisplayString,
        allportsStatsOutBcast                  DisplayString,
        allportsStatsInMcast                   DisplayString,
        allportsStatsOutMcast                  DisplayString,
        allportsStatsInDiscards                Counter32,
        allportsStatsOutDiscards               Counter32,
        allportsStatsInErrors                  Counter32,
        allportsStatsOutErrors                 Counter32,
        allportsStatsInUnknownProtos           DisplayString,
        allportsStatsOutQLen                   DisplayString
        ,
        allportsStatsipInReceives              Counter32,
        allportsStatsipInHeaderErrors          Counter32,
        allportsStatsipInDiscards              Counter32
        ,
        allportsStatsipInReceivesRate          Counter32,
        allportsStatsipInHeaderErrorsRate      Counter32,
        allportsStatsipInDiscardsRate          Counter32
        ,
        allportsStatsLinkStateChange           Counter32
        ,
        allportsStatsInOctetsRate              Counter32,
        allportsStatsOutOctetsRate             Counter32,
        allportsStatsInUcastRate               DisplayString,
        allportsStatsOutUcastRate              DisplayString,
        allportsStatsInBcastRate               DisplayString,
        allportsStatsOutBcastRate              DisplayString,
        allportsStatsInMcastRate               DisplayString,
        allportsStatsOutMcastRate              DisplayString,
        allportsStatsInDiscardsRate            Counter32,
        allportsStatsOutDiscardsRate           Counter32,
        allportsStatsInErrorsRate              Counter32,
        allportsStatsOutErrorsRate             Counter32
}

allportsStatsIndx OBJECT-TYPE
    SYNTAX           PortNumber
    MAX-ACCESS       read-only
    STATUS           current
    DESCRIPTION
            "The port number."
    ::= { allportsStatsTableEntry 1 }

allportsStatsDescr OBJECT-TYPE
    SYNTAX           DisplayString(SIZE(0..7))
    MAX-ACCESS       read-only
    STATUS           current
    DESCRIPTION
            "The port description."
    ::= { allportsStatsTableEntry 2 }

allportsStatsSpeed OBJECT-TYPE
    SYNTAX  INTEGER {
        mbs10(2),
        mbs100(3),
        mbs1000(4),
        any(5)
        ,
        mbs10000(6)
        ,
        mbs40000(7)
        }
    MAX-ACCESS       read-only
    STATUS           current
    DESCRIPTION
            "The current operational speed of the port."
    ::= { allportsStatsTableEntry 3 }

allportsStatsPhysAddress OBJECT-TYPE
    SYNTAX           PhysAddress
    MAX-ACCESS       read-only
    STATUS           current
    DESCRIPTION
            "The port MAC Address."
    ::= { allportsStatsTableEntry 4 }

allportsStatsAdminStatus OBJECT-TYPE
    SYNTAX  INTEGER {
        up(1),
        down(2),
        testing(3)
        }
    MAX-ACCESS       read-only
    STATUS           current
    DESCRIPTION
            "The port Admin state."
    ::= { allportsStatsTableEntry 5 }

allportsStatsOperStatus OBJECT-TYPE
    SYNTAX  INTEGER {
        up(1),
        down(2),
        testing(3)
        }
    MAX-ACCESS       read-only
    STATUS           current
    DESCRIPTION
            "The port Operational Status."
    ::= { allportsStatsTableEntry 6 }

allportsStatsInOctets OBJECT-TYPE
    SYNTAX           Counter32
    MAX-ACCESS       read-only
    STATUS           current
    DESCRIPTION
            "Octets In for port."
    ::= { allportsStatsTableEntry 7 }

allportsStatsOutOctets OBJECT-TYPE
    SYNTAX           Counter32
    MAX-ACCESS       read-only
    STATUS           current
    DESCRIPTION
            "Octets Out for port."
    ::= { allportsStatsTableEntry 8 }

allportsStatsInPkts OBJECT-TYPE
    SYNTAX           Counter32
    MAX-ACCESS       read-only
    STATUS           current
    DESCRIPTION
            "Packets In for port."
    ::= { allportsStatsTableEntry 9 }

allportsStatsOutPkts OBJECT-TYPE
    SYNTAX           Counter32
    MAX-ACCESS       read-only
    STATUS           current
    DESCRIPTION
            "Packets Out for port."
    ::= { allportsStatsTableEntry 10 }

allportsStatsInUcast OBJECT-TYPE
    SYNTAX           DisplayString(SIZE(0..20))
    MAX-ACCESS       read-only
    STATUS           current
    DESCRIPTION
            "Unicast Packets In for port."
    ::= { allportsStatsTableEntry 11 }

allportsStatsOutUcast OBJECT-TYPE
    SYNTAX           DisplayString(SIZE(0..20))
    MAX-ACCESS       read-only
    STATUS           current
    DESCRIPTION
            "Unicast Packets Out for port."
    ::= { allportsStatsTableEntry 12 }

allportsStatsInBcast OBJECT-TYPE
    SYNTAX           DisplayString(SIZE(0..20))
    MAX-ACCESS       read-only
    STATUS           current
    DESCRIPTION
            "Broadcasts Packets In for port."
    ::= { allportsStatsTableEntry 13 }

allportsStatsOutBcast OBJECT-TYPE
    SYNTAX           DisplayString(SIZE(0..20))
    MAX-ACCESS       read-only
    STATUS           current
    DESCRIPTION
            "Broadcasts Packets Out for port."
    ::= { allportsStatsTableEntry 14 }

allportsStatsInMcast OBJECT-TYPE
    SYNTAX           DisplayString(SIZE(0..20))
    MAX-ACCESS       read-only
    STATUS           current
    DESCRIPTION
            "Multicast Packets In for port."
    ::= { allportsStatsTableEntry 15 }

allportsStatsOutMcast OBJECT-TYPE
    SYNTAX           DisplayString(SIZE(0..20))
    MAX-ACCESS       read-only
    STATUS           current
    DESCRIPTION
            "Multicast Packets Out for port."
    ::= { allportsStatsTableEntry 16 }

allportsStatsInDiscards OBJECT-TYPE
    SYNTAX           Counter32
    MAX-ACCESS       read-only
    STATUS           current
    DESCRIPTION
            "Discarded Packets for port."
    ::= { allportsStatsTableEntry 17 }

allportsStatsOutDiscards OBJECT-TYPE
    SYNTAX           Counter32
    MAX-ACCESS       read-only
    STATUS           current
    DESCRIPTION
            "Outbound Packets for port."
    ::= { allportsStatsTableEntry 18 }

allportsStatsInErrors OBJECT-TYPE
    SYNTAX           Counter32
    MAX-ACCESS       read-only
    STATUS           current
    DESCRIPTION
            "Error Packets for port."
    ::= { allportsStatsTableEntry 19 }

allportsStatsOutErrors OBJECT-TYPE
    SYNTAX           Counter32
    MAX-ACCESS       read-only
    STATUS           current
    DESCRIPTION
            "Not sent packets due to error."
    ::= { allportsStatsTableEntry 20 }

allportsStatsInUnknownProtos OBJECT-TYPE
    SYNTAX           DisplayString(SIZE(0..20))
    MAX-ACCESS       read-only
    STATUS           current
    DESCRIPTION
            "Unknown protocol packets."
    ::= { allportsStatsTableEntry 21 }

allportsStatsOutQLen OBJECT-TYPE
    SYNTAX           DisplayString(SIZE(0..20))
    MAX-ACCESS       read-only
    STATUS           current
    DESCRIPTION
            "Outbound Packet Queue Length."
    ::= { allportsStatsTableEntry 22 }

allportsStatsipInReceives OBJECT-TYPE
    SYNTAX           Counter32
    MAX-ACCESS       read-only
    STATUS           current
    DESCRIPTION
            "Ip In Receives."
    ::= { allportsStatsTableEntry 23 }

allportsStatsipInHeaderErrors OBJECT-TYPE
    SYNTAX           Counter32
    MAX-ACCESS       read-only
    STATUS           current
    DESCRIPTION
            "Ip In Header Errors."
    ::= { allportsStatsTableEntry 24 }

allportsStatsipInDiscards OBJECT-TYPE
    SYNTAX           Counter32
    MAX-ACCESS       read-only
    STATUS           current
    DESCRIPTION
            "Ip In Discards."
    ::= { allportsStatsTableEntry 25 }

allportsStatsLinkStateChange OBJECT-TYPE
    SYNTAX           Counter32
    MAX-ACCESS       read-only
    STATUS           current
    DESCRIPTION
            "Number of link state changes."
    ::= { allportsStatsTableEntry 26 }

allportsStatsipInReceivesRate OBJECT-TYPE
    SYNTAX           Counter32
    MAX-ACCESS       read-only
    STATUS           current
    DESCRIPTION
            "Ip In Receives rate."
    ::= { allportsStatsTableEntry 27 }

allportsStatsipInHeaderErrorsRate OBJECT-TYPE
    SYNTAX           Counter32
    MAX-ACCESS       read-only
    STATUS           current
    DESCRIPTION
            "Ip In Header Errors rate."
    ::= { allportsStatsTableEntry 28 }

allportsStatsipInDiscardsRate OBJECT-TYPE
    SYNTAX           Counter32
    MAX-ACCESS       read-only
    STATUS           current
    DESCRIPTION
            "Ip In Discards rate."
    ::= { allportsStatsTableEntry 29 }

allportsStatsInOctetsRate OBJECT-TYPE
    SYNTAX           Counter32
    MAX-ACCESS       read-only
    STATUS           current
    DESCRIPTION
            "Octets In rate for port."
    ::= { allportsStatsTableEntry 30 }

allportsStatsOutOctetsRate OBJECT-TYPE
    SYNTAX           Counter32
    MAX-ACCESS       read-only
    STATUS           current
    DESCRIPTION
            "Octets Out rate for port."
    ::= { allportsStatsTableEntry 31 }

allportsStatsInUcastRate OBJECT-TYPE
    SYNTAX           DisplayString(SIZE(0..20))
    MAX-ACCESS       read-only
    STATUS           current
    DESCRIPTION
            "Unicast Packets In rate for port."
    ::= { allportsStatsTableEntry 32 }

allportsStatsOutUcastRate OBJECT-TYPE
    SYNTAX           DisplayString(SIZE(0..20))
    MAX-ACCESS       read-only
    STATUS           current
    DESCRIPTION
            "Unicast Packets Out rate for port."
    ::= { allportsStatsTableEntry 33 }

allportsStatsInBcastRate OBJECT-TYPE
    SYNTAX           DisplayString(SIZE(0..20))
    MAX-ACCESS       read-only
    STATUS           current
    DESCRIPTION
            "Broadcasts Packets In rate for port."
    ::= { allportsStatsTableEntry 34 }

allportsStatsOutBcastRate OBJECT-TYPE
    SYNTAX           DisplayString(SIZE(0..20))
    MAX-ACCESS       read-only
    STATUS           current
    DESCRIPTION
            "Broadcasts Packets Out rate for port."
    ::= { allportsStatsTableEntry 35 }

allportsStatsInMcastRate OBJECT-TYPE
    SYNTAX           DisplayString(SIZE(0..20))
    MAX-ACCESS       read-only
    STATUS           current
    DESCRIPTION
            "Multicast Packets In rate for port."
    ::= { allportsStatsTableEntry 36 }

allportsStatsOutMcastRate OBJECT-TYPE
    SYNTAX           DisplayString(SIZE(0..20))
    MAX-ACCESS       read-only
    STATUS           current
    DESCRIPTION
            "Multicast Packets Out rate for port."
    ::= { allportsStatsTableEntry 37 }

allportsStatsInDiscardsRate OBJECT-TYPE
    SYNTAX           Counter32
    MAX-ACCESS       read-only
    STATUS           current
    DESCRIPTION
            "Discarded In Packets rate for port."
    ::= { allportsStatsTableEntry 38 }

allportsStatsOutDiscardsRate OBJECT-TYPE
    SYNTAX           Counter32
    MAX-ACCESS       read-only
    STATUS           current
    DESCRIPTION
            "Discarded Out Packets rate for port."
    ::= { allportsStatsTableEntry 39 }

allportsStatsInErrorsRate OBJECT-TYPE
    SYNTAX           Counter32
    MAX-ACCESS       read-only
    STATUS           current
    DESCRIPTION
            "Erroneus inbound packets rate for port."
    ::= { allportsStatsTableEntry 40 }

allportsStatsOutErrorsRate OBJECT-TYPE
    SYNTAX           Counter32
    MAX-ACCESS       read-only
    STATUS           current
    DESCRIPTION
            "Not sent packets due to error rate."
    ::= { allportsStatsTableEntry 41 }


clearPortsStats OBJECT-TYPE
    SYNTAX  INTEGER {
	ok(1),
	clear(2)
	}
    MAX-ACCESS  read-write
    STATUS  current
    DESCRIPTION
        "Setting this to clear(2) results in clearing the statistics for all ports."
    ::= { portStats 6 }

dot1RateStatsTable OBJECT-TYPE
    SYNTAX SEQUENCE OF Dot1RateStatsTableEntry
    MAX-ACCESS not-accessible
    STATUS current
    DESCRIPTION
        "The table of bridging statistics per second."
    ::= { portStats 7}

dot1RateStatsTableEntry OBJECT-TYPE
    SYNTAX Dot1RateStatsTableEntry
    MAX-ACCESS not-accessible
    STATUS current
    DESCRIPTION
        "Bridging statistics per second."
    INDEX { dot1RateStatsIndx }
    ::= { dot1RateStatsTable 1 }

Dot1RateStatsTableEntry ::= SEQUENCE {
    dot1RateStatsIndx                      PortNumber,
    dot1RatePortInFrames                   Counter32,
    dot1RatePortOutFrames                  Counter32,
    dot1RatePortInDiscards                 Counter32,
    dot1RateTpLearnedEntryDiscards         Counter32
    ,dot1RateStpPortForwardTransitions     Counter32
}

dot1RateStatsIndx OBJECT-TYPE
    SYNTAX  PortNumber
    MAX-ACCESS  read-only
    STATUS  current
    DESCRIPTION
        "The port index."
    ::= { dot1RateStatsTableEntry 1 }

dot1RatePortInFrames OBJECT-TYPE
    SYNTAX  Counter32
    MAX-ACCESS  read-only
    STATUS  current
    DESCRIPTION
        "The number of frames that have been received
        per second by this port from its segment."
    ::= { dot1RateStatsTableEntry 2 }

dot1RatePortOutFrames OBJECT-TYPE
    SYNTAX  Counter32
    MAX-ACCESS  read-only
    STATUS  current
    DESCRIPTION
        "The number of frames that have been transmitted
        per second by this port to its segment."
    ::= { dot1RateStatsTableEntry 3 }

dot1RatePortInDiscards OBJECT-TYPE
    SYNTAX  Counter32
    MAX-ACCESS  read-only
    STATUS  current
    DESCRIPTION
        "Count of valid frames received which were
        discarded per second."
    ::= { dot1RateStatsTableEntry 4 }

dot1RateTpLearnedEntryDiscards OBJECT-TYPE
    SYNTAX  Counter32
    MAX-ACCESS  read-only
    STATUS  current
    DESCRIPTION
        "The number per second of Forwarding Database
        entries, which have been or would have been
        learnt, but have been discarded due to a lack
        of space to store them."
    ::= { dot1RateStatsTableEntry 5 }


dot1RateStpPortForwardTransitions OBJECT-TYPE
    SYNTAX  Counter32
    MAX-ACCESS  read-only
    STATUS  current
    DESCRIPTION
        "The number of times this port has transitioned
        per second from the Learning state to the
        Forwarding state."
    ::= { dot1RateStatsTableEntry 8 }

dot3RateStatsTable OBJECT-TYPE
    SYNTAX SEQUENCE OF Dot3RateStatsTableEntry
    MAX-ACCESS not-accessible
    STATUS current
    DESCRIPTION
        "The table of Ethernet statistics per second."
    ::= { portStats 8}

dot3RateStatsTableEntry OBJECT-TYPE
    SYNTAX Dot3RateStatsTableEntry
    MAX-ACCESS not-accessible
    STATUS current
    DESCRIPTION
        "Ethernet statistics per second."
    INDEX { dot3RateStatsIndx }
    ::= { dot3RateStatsTable 1 }

Dot3RateStatsTableEntry ::= SEQUENCE {
    dot3RateStatsIndx                       PortNumber,
    dot3RateStatsAlignmentErrors            Counter32,
    dot3RateStatsFCSErrors                  Counter32,
    dot3RateStatsSingleCollisionFrames      Counter32,
    dot3RateStatsMultipleCollisionFrames    Counter32,
    dot3RateStatsLateCollisions             Counter32,
    dot3RateStatsExcessiveCollisions        Counter32,
    dot3RateStatsInternalMacTransmitErrors  Counter32,
    dot3RateStatsFrameTooLongs              Counter32,
    dot3RateStatsInternalMacReceiveErrors   Counter32
}

dot3RateStatsIndx OBJECT-TYPE
    SYNTAX  PortNumber
    MAX-ACCESS  read-only
    STATUS  current
    DESCRIPTION
        "The port index."
    ::= { dot3RateStatsTableEntry 1 }

dot3RateStatsAlignmentErrors OBJECT-TYPE
    SYNTAX  Counter32
    MAX-ACCESS  read-only
    STATUS  current
    DESCRIPTION
        "A count of frames received per second on a particular
        interface that are not an integral number of octets
        in length and do not pass the FCS check."
    ::= { dot3RateStatsTableEntry 2 }

dot3RateStatsFCSErrors OBJECT-TYPE
    SYNTAX  Counter32
    MAX-ACCESS  read-only
    STATUS  current
    DESCRIPTION
        "A count of frames received per second on a particular
        interface that are an integral number of octets
        in length but do not pass the FCS check."
    ::= { dot3RateStatsTableEntry 3 }

dot3RateStatsSingleCollisionFrames OBJECT-TYPE
    SYNTAX  Counter32
    MAX-ACCESS  read-only
    STATUS  current
    DESCRIPTION
        "A count of successfully transmitted frames per second
        on a particular interface for which transmission is
        inhibited by exactly one collision."
    ::= { dot3RateStatsTableEntry 4 }

dot3RateStatsMultipleCollisionFrames OBJECT-TYPE
    SYNTAX  Counter32
    MAX-ACCESS  read-only
    STATUS  current
    DESCRIPTION
        "A count of successfully transmitted frames per second
        on a particular interface for which transmission is
        inhibited by more than one collision."
    ::= { dot3RateStatsTableEntry 5 }


dot3RateStatsLateCollisions OBJECT-TYPE
    SYNTAX  Counter32
    MAX-ACCESS  read-only
    STATUS  current
    DESCRIPTION
        "The number of times per second that a collision
        is detected on a particular interface later than
        512 bit-times into the transmission of a packet."
    ::= { dot3RateStatsTableEntry 8 }

dot3RateStatsExcessiveCollisions OBJECT-TYPE
    SYNTAX  Counter32
    MAX-ACCESS  read-only
    STATUS  current
    DESCRIPTION
        "A count per second of frames for which
        transmission on a particular interface fails
        due to excessive collisions."
    ::= { dot3RateStatsTableEntry 9 }

dot3RateStatsInternalMacTransmitErrors OBJECT-TYPE
    SYNTAX  Counter32
    MAX-ACCESS  read-only
    STATUS  current
    DESCRIPTION
        "A count per second of frames for which transmission
        on a particular interface fails due to an internal
        MAC sublayer transmit error."
    ::= { dot3RateStatsTableEntry 10 }


dot3RateStatsFrameTooLongs OBJECT-TYPE
    SYNTAX  Counter32
    MAX-ACCESS  read-only
    STATUS  current
    DESCRIPTION
        "A count per second of frames received on a particular
        interface that exceed the maximum permitted frame size."
    ::= { dot3RateStatsTableEntry 12 }

dot3RateStatsInternalMacReceiveErrors OBJECT-TYPE
    SYNTAX  Counter32
    MAX-ACCESS  read-only
    STATUS  current
    DESCRIPTION
        "A count per second of frames for which reception on
        a particular interface fails due to an internal MAC
        sublayer receive error."
    ::= { dot3RateStatsTableEntry 13 }


-- NTP Statisitics

ntpPrimaryServerReqSent OBJECT-TYPE
    SYNTAX Integer32
    MAX-ACCESS read-only
    STATUS current
    DESCRIPTION
        "The total number of NTP requests sent to Primary NTP Server."
    ::= { ntpStats 1 }

ntpPrimaryServerRespRcvd OBJECT-TYPE
    SYNTAX Integer32
    MAX-ACCESS read-only
    STATUS current
    DESCRIPTION
        "The total number of NTP responces received from Primary NTP Server."
    ::= { ntpStats 2 }

ntpPrimaryServerUpdates OBJECT-TYPE
    SYNTAX Integer32
    MAX-ACCESS read-only
    STATUS current
    DESCRIPTION
        "The total number of NTP Updates by Primary NTP Server."
    ::= { ntpStats 3 }

ntpSecondaryServerReqSent OBJECT-TYPE
    SYNTAX Integer32
    MAX-ACCESS read-only
    STATUS current
    DESCRIPTION
        "The total number of NTP requests sent to Secondary NTP Server."
    ::= { ntpStats 4 }

ntpSecondaryServerRespRcvd OBJECT-TYPE
    SYNTAX Integer32
    MAX-ACCESS read-only
    STATUS current
    DESCRIPTION
        "The total number of NTP responces received from Secondary NTP Server."
    ::= { ntpStats 5 }

ntpSecondaryServerUpdates OBJECT-TYPE
    SYNTAX Integer32
    MAX-ACCESS read-only
    STATUS current
    DESCRIPTION
        "The total number of NTP Updates by Secondary NTP Server."
    ::= { ntpStats 6 }

ntpLastUpdateServer OBJECT-TYPE
    SYNTAX  INTEGER {
        none(0),
        primary(1),
        secondary(2)
        }
    MAX-ACCESS read-only
    STATUS current
    DESCRIPTION
        "The type of ntp server updated last time."
    ::= { ntpStats 7 }

ntpLastUpdateTime OBJECT-TYPE
    SYNTAX  DisplayString (SIZE(0..127))
    MAX-ACCESS  read-only
    STATUS  current
    DESCRIPTION
        "The last time updated by ntp server."
    ::= { ntpStats 8 }

ntpClearStats OBJECT-TYPE
    SYNTAX  INTEGER {
        ok(1),
        clear(2)
        }
    MAX-ACCESS read-write
    STATUS current
    DESCRIPTION
        "Setting this value to clear(2) clears the stats for ntp."
    ::= { ntpStats 9 }

ntpSystemCurrentTime OBJECT-TYPE
    SYNTAX  DisplayString (SIZE(0..127))
    MAX-ACCESS  read-only
    STATUS  current
    DESCRIPTION
        "The current system time."
    ::= { ntpStats 10 }


aclStatsTable  OBJECT-TYPE
    SYNTAX      SEQUENCE OF AclStatsTableEntry
    MAX-ACCESS  not-accessible
    STATUS      current
    DESCRIPTION
        "The table of ACL statistics."
    ::= { aclStats 1 }

aclStatsTableEntry  OBJECT-TYPE
    SYNTAX      AclStatsTableEntry
    MAX-ACCESS  not-accessible
    STATUS      current
    DESCRIPTION
        "Statistics about a particular ACL configuration entry."
    INDEX { aclStatsIndex }
    ::= { aclStatsTable 1 }

AclStatsTableEntry  ::= SEQUENCE {
    aclStatsIndex          Integer32,
    aclStatsHits           Counter32,
    aclClearStats          INTEGER
    }

aclStatsIndex OBJECT-TYPE
    SYNTAX  Integer32
    MAX-ACCESS  read-only
    STATUS  current
    DESCRIPTION
        "The acl index."
    ::= { aclStatsTableEntry 1 }

aclStatsHits OBJECT-TYPE
    SYNTAX  Counter32
    MAX-ACCESS  read-only
    STATUS  current
    DESCRIPTION
        "Total number of hits for this ACL entry"
    ::= { aclStatsTableEntry 2 }

aclClearStats OBJECT-TYPE
    SYNTAX  INTEGER {
        ok(1),
        clear(2)
        }
    MAX-ACCESS read-write
    STATUS current
    DESCRIPTION
        "Setting this value to clear(2) clears the stats for the ACL."
    ::= { aclStatsTableEntry 3 }


    vmapStatsTable  OBJECT-TYPE
    SYNTAX      SEQUENCE OF VmapStatsTableEntry
    MAX-ACCESS  not-accessible
    STATUS      current
    DESCRIPTION
        "The table of VMAP statistics."
    ::= { aclStats 2 }

vmapStatsTableEntry  OBJECT-TYPE
    SYNTAX      VmapStatsTableEntry
    MAX-ACCESS  not-accessible
    STATUS      current
    DESCRIPTION
        "Statistics about a particular VMAP configuration entry."
    INDEX { vmapStatsIndex }
    ::= { vmapStatsTable 1 }

VmapStatsTableEntry  ::= SEQUENCE {
    vmapStatsIndex          Integer32,
    vmapStatsHits           Counter32,
    vmapClearStats          INTEGER
    }

vmapStatsIndex OBJECT-TYPE
    SYNTAX  Integer32
    MAX-ACCESS  read-only
    STATUS  current
    DESCRIPTION
        "The vmap index."
    ::= { vmapStatsTableEntry 1 }

vmapStatsHits OBJECT-TYPE
    SYNTAX  Counter32
    MAX-ACCESS  read-only
    STATUS  current
    DESCRIPTION
        "Total number of hits for this VMAP entry"
    ::= { vmapStatsTableEntry 2 }

vmapClearStats OBJECT-TYPE
    SYNTAX  INTEGER {
        ok(1),
        clear(2)
        }
    MAX-ACCESS read-write
    STATUS current
    DESCRIPTION
        "Setting this value to clear(2) clears the stats for the VMAP."
    ::= { vmapStatsTableEntry 3 }


acl6StatsTable  OBJECT-TYPE
	SYNTAX		SEQUENCE OF Acl6StatsTableEntry
	MAX-ACCESS	not-accessible
	STATUS		current
	DESCRIPTION
		"The table of IPv6 ACL statistics."
	::= { aclStats 3 }

acl6StatsTableEntry	OBJECT-TYPE
	SYNTAX		Acl6StatsTableEntry
	MAX-ACCESS	not-accessible
	STATUS		current
	DESCRIPTION
		"Statistics about a particular IPv6 ACL configuration entry."
	INDEX { aclStatsIndex }
	::= { acl6StatsTable 1 }

Acl6StatsTableEntry	::= SEQUENCE {
	acl6StatsIndex		   Integer32,
	acl6StatsHits		   Counter32,
	acl6ClearStats		   INTEGER
	}

acl6StatsIndex OBJECT-TYPE
	SYNTAX	Integer32
	MAX-ACCESS	read-only
	STATUS	current
	DESCRIPTION
		"The ipv6 acl index."
	::= { acl6StatsTableEntry 1 }

acl6StatsHits OBJECT-TYPE
	SYNTAX	Counter32
	MAX-ACCESS	read-only
	STATUS	current
	DESCRIPTION
		"Total number of hits for this IPv6 ACL entry"
	::= { acl6StatsTableEntry 2 }

acl6ClearStats OBJECT-TYPE
	SYNTAX	INTEGER {
		ok(1),
		clear(2)
		}
	MAX-ACCESS read-write
	STATUS current
	DESCRIPTION
		"Setting this value to clear(2) clears the stats for the IPv6 ACL."
	::= { acl6StatsTableEntry 3 }


-- Clear Statistics
snmpClearStats OBJECT-TYPE
    SYNTAX  INTEGER {
	ok(1),
	clear(2)
	}
    MAX-ACCESS  read-write
    STATUS  current
    DESCRIPTION
        "Setting this to clear(2) results in clearing the SNMP statistics."
    ::= { agClearStats 1 }

agDiffState OBJECT-TYPE
    SYNTAX  INTEGER {
        diff(1),
        flashdiff(2),
        idle(3),
        inprogress(4),
        complete(5)
        }
    MAX-ACCESS  read-write
    STATUS  current
    DESCRIPTION
         "When this object is read the current state is returned.
          idle(3) indicates that there is no diff in progess.
          complete(5) indicates that the last diff operation is completed.
          Setting the value to diff(1), will start a new diff operation
          Diff compares the new configuration with the current configuration
          and shows the pending configuration changes.
          Setting the value to flashdiff(1), will start a new diff operation.
          flashdiff compares new configuration with the flash configuration.
          To read the configuration changes use the agDiffTable once the
          state of this variable returns complete.
          Once the agDiffTable is read the state should be set back to 'idle'
          which frees the diff buffer and others can issue a diff command via
          SNMP."
    ::= { agDiff 2 }

agDiffTableSize OBJECT-TYPE
    SYNTAX  Integer32
    MAX-ACCESS  read-only
    STATUS  current
    DESCRIPTION
        "The number of strings in the diff table."
    ::= { agDiff 3 }

agDiffTable OBJECT-TYPE
    SYNTAX  SEQUENCE OF AgDiffTableEntry
    MAX-ACCESS  not-accessible
    STATUS  current
    DESCRIPTION
        "The table of diff strings."
    ::= { agDiff 4 }

agDiffTableEntry OBJECT-TYPE
    SYNTAX  AgDiffTableEntry
    MAX-ACCESS  not-accessible
    STATUS  current
    DESCRIPTION
        "An entry in the diff table."
    INDEX   { agDiffIndex }
    ::= { agDiffTable 1 }

AgDiffTableEntry ::= SEQUENCE {
    agDiffIndex      Integer32,
    agDiffString     OCTET STRING
    }

agDiffIndex OBJECT-TYPE
    SYNTAX  Integer32
    MAX-ACCESS  read-only
    STATUS  current
    DESCRIPTION
        "The table index."
    ::= { agDiffTableEntry 1 }

agDiffString OBJECT-TYPE
    SYNTAX  OCTET STRING
    MAX-ACCESS  read-only
    STATUS  current
    DESCRIPTION
        "A string in the diff table."
    ::= { agDiffTableEntry 2 }

-- Config Dump
agCfgDumpState OBJECT-TYPE
    SYNTAX  INTEGER {
        dump(1),
        idle(2),
        inprogress(3),
        complete(4)
        }
    MAX-ACCESS  read-write
    STATUS  current
    DESCRIPTION
         "When this object is read the current state is returned.
          idle(2) indicates that there is no dump in progess.
          complete(4) indicates that the last dump operation is completed.
          Setting the value to dump(1), will start a new dump operation
          Dump will show the current configuration.
          To read the configuration dump use the agCfgDumpTable once the
          state of this variable returns complete.
          Once the agCfgDumpTable is read the state should be set back to
          'idle' which frees the dump buffer and others can issue a dump
          command via SNMP."
    ::= { agCfgDump 2 }

agCfgDumpTableSize OBJECT-TYPE
    SYNTAX  Integer32
    MAX-ACCESS  read-only
    STATUS  current
    DESCRIPTION
        "The number of strings in the dump table."
    ::= { agCfgDump 3 }

agCfgDumpTable OBJECT-TYPE
    SYNTAX  SEQUENCE OF AgCfgDumpTableEntry
    MAX-ACCESS  not-accessible
    STATUS  current
    DESCRIPTION
        "The table of dump strings."
    ::= { agCfgDump 4 }

agCfgDumpTableEntry OBJECT-TYPE
    SYNTAX  AgCfgDumpTableEntry
    MAX-ACCESS  not-accessible
    STATUS  current
    DESCRIPTION
        "An entry in the dump table."
    INDEX   { agCfgDumpIndex }
    ::= { agCfgDumpTable 1 }

AgCfgDumpTableEntry ::= SEQUENCE {
    agCfgDumpIndex      Integer32,
    agCfgDumpString     OCTET STRING
    }

agCfgDumpIndex OBJECT-TYPE
    SYNTAX  Integer32
    MAX-ACCESS  read-only
    STATUS  current
    DESCRIPTION
        "The table index."
    ::= { agCfgDumpTableEntry 1 }

agCfgDumpString OBJECT-TYPE
    SYNTAX  OCTET STRING
    MAX-ACCESS  read-only
    STATUS  current
    DESCRIPTION
        "A string in the dump table."
    ::= { agCfgDumpTableEntry 2 }






-- Memory Statisitics Group


totalMemoryStats OBJECT-TYPE
    SYNTAX  Counter64
    MAX-ACCESS  read-only
    STATUS  current
    DESCRIPTION
        "The total memory in bytes."
    ::= { memoryStats 1}

memoryFreeStats OBJECT-TYPE
    SYNTAX  Counter64
    MAX-ACCESS  read-only
    STATUS  current
    DESCRIPTION
        "The free memory in bytes."
    ::= { memoryStats 2}

memorySharedStats OBJECT-TYPE
    SYNTAX  Counter64
    MAX-ACCESS  read-only
    STATUS  current
    DESCRIPTION
        "The shared memory in bytes."
    ::= { memoryStats 3}

memoryBufferStats OBJECT-TYPE
    SYNTAX  Counter64
    MAX-ACCESS  read-only
    STATUS  current
    DESCRIPTION
        "The buffer memory in bytes."
    ::= { memoryStats 4}

swapTotalStats OBJECT-TYPE
    SYNTAX  Counter64
    MAX-ACCESS  read-only
    STATUS  current
    DESCRIPTION
        "The total swap memory in bytes."
    ::= { memoryStats 5}

swapFreeStats OBJECT-TYPE
    SYNTAX  Counter64
    MAX-ACCESS  read-only
    STATUS  current
    DESCRIPTION
        "The free swap memory in bytes."
    ::= { memoryStats 6}

highTotalStats OBJECT-TYPE
    SYNTAX  Counter64
    MAX-ACCESS  read-only
    STATUS  current
    DESCRIPTION
        "The total high memory in bytes."
    ::= { memoryStats 7}

highFreeStats OBJECT-TYPE
    SYNTAX  Counter64
    MAX-ACCESS  read-only
    STATUS  current
    DESCRIPTION
        "The free high memory in bytes."
    ::= { memoryStats 8}


-- GeaPort Information

geaportInfoTable OBJECT-TYPE
    SYNTAX  SEQUENCE OF GeaportInfoTableEntry
    MAX-ACCESS  not-accessible
    STATUS  current
    DESCRIPTION
        "The table of gea port mapping."
    ::= { geaportInfo 1 }

geaportInfoTableEntry OBJECT-TYPE
    SYNTAX  GeaportInfoTableEntry
    MAX-ACCESS  not-accessible
    STATUS  current
    DESCRIPTION
        "An entry in the geaport table mapping."
    INDEX   { geaportInfoLogicalIndex }
    ::= { geaportInfoTable 1 }

GeaportInfoTableEntry ::= SEQUENCE {
    geaportInfoLogicalIndex    PortNumber,
    geaportInfoAlias	       DisplayString,
    geaportInfoPort            INTEGER,
    geaportInfoUnit            INTEGER
    }

geaportInfoLogicalIndex OBJECT-TYPE
    SYNTAX  PortNumber
    MAX-ACCESS  read-only
    STATUS  current
    DESCRIPTION
        "The logical port index."
    ::= { geaportInfoTableEntry 1 }

geaportInfoAlias OBJECT-TYPE
    SYNTAX  DisplayString
    MAX-ACCESS  read-only
    STATUS  current
    DESCRIPTION
	"The GEA Port Alias."
    ::= { geaportInfoTableEntry 2 }

geaportInfoPort OBJECT-TYPE
    SYNTAX  INTEGER
    MAX-ACCESS  read-only
    STATUS  current
    DESCRIPTION
        "The GEA Port (0-based)."
    ::= { geaportInfoTableEntry 3 }

geaportInfoUnit OBJECT-TYPE
    SYNTAX  INTEGER
    MAX-ACCESS  read-only
    STATUS  current
    DESCRIPTION
        "The GEA Unit."
    ::= { geaportInfoTableEntry 4 }

-- SFP Information

sfpInfoTable OBJECT-TYPE
    SYNTAX  SEQUENCE OF SfpInfoTableEntry
    MAX-ACCESS  not-accessible
    STATUS  current
    DESCRIPTION
        "The table of external port SFP information."
    ::= { sfpInfo 1 }

sfpInfoTableEntry OBJECT-TYPE
    SYNTAX  SfpInfoTableEntry
    MAX-ACCESS  not-accessible
    STATUS  current
    DESCRIPTION
        "A row in the external port SFP information table."
    INDEX   { sfpInfoIndx }
    ::= { sfpInfoTable 1 }

SfpInfoTableEntry ::= SEQUENCE {
    sfpInfoIndx                 PortNumber,
    sfpInfoPort			DisplayString,
    sfpInfoDevice		DisplayString,
    sfpInfoTXEnable		INTEGER,
    sfpInfoRXSignal		INTEGER,
    sfpInfoTXFault		INTEGER,
    sfpInfoApproved		INTEGER,
    sfpInfoVendor               DisplayString,
    sfpInfoSerial               DisplayString
    ,
    sfpInfoPartNumber           DisplayString,
    sfpInfoRevision             DisplayString,
    sfpInfoVoltage              DisplayString,
    sfpInfoTemperature          DisplayString,
    sfpInfoWaveLength           DisplayString
    }

sfpInfoIndx OBJECT-TYPE
    SYNTAX  PortNumber
    MAX-ACCESS  read-only
    STATUS  current
    DESCRIPTION
        "The external port SFX index."
    ::= { sfpInfoTableEntry 1 }

sfpInfoPort OBJECT-TYPE
    SYNTAX  DisplayString (SIZE(0..6))
    MAX-ACCESS  read-only
    STATUS  current
    DESCRIPTION
	  "External Port SFP/XFP alias."
    ::= { sfpInfoTableEntry 2 }

sfpInfoDevice OBJECT-TYPE
    SYNTAX  DisplayString (SIZE(0..6))
    MAX-ACCESS  read-only
    STATUS  current
    DESCRIPTION
          "External Port SFP/XFP Device."
    ::= { sfpInfoTableEntry 3 }

sfpInfoTXEnable OBJECT-TYPE
    SYNTAX  INTEGER {
	  notInstalled (1),
	  enabled (2),
	  disabled (3)
          , notAvailable (5)
    }
    MAX-ACCESS  read-only
    STATUS  current
    DESCRIPTION
	  "External Port SFP/XFP TX-Enable."
    ::= { sfpInfoTableEntry 4  }

sfpInfoRXSignal  OBJECT-TYPE
    SYNTAX  INTEGER {
	  notInstalled (1),
	  down (2),
	  link (3),
	  notAvailable (4)
    }
    MAX-ACCESS  read-only
    STATUS  current
    DESCRIPTION
          "External Port SFP/XFP RX-Signal."
    ::= { sfpInfoTableEntry 5 }

sfpInfoTXFault  OBJECT-TYPE
    SYNTAX  INTEGER {
          notInstalled (1),
          fault (2),
          none (3),
          notAvailable (4)
    }
    MAX-ACCESS  read-only
    STATUS  current
    DESCRIPTION
          "External Port SFP/XFP TX-Fault."
    ::= { sfpInfoTableEntry 6 }

sfpInfoApproved  OBJECT-TYPE
    SYNTAX  INTEGER {
      notInstalled (1),
      notApproved (2),
      sfpApproved (3)
      ,sfpAccepted (5)
    }
    MAX-ACCESS  read-only
    STATUS  current
    DESCRIPTION
          "External Port SFP/XFP Approval."
    ::= { sfpInfoTableEntry 7 }

sfpInfoVendor OBJECT-TYPE
    SYNTAX  DisplayString (SIZE(0..32))
    MAX-ACCESS  read-only
    STATUS  current
    DESCRIPTION
          "External Port SFP/XFP device vendor."
    ::= { sfpInfoTableEntry 8 }

sfpInfoSerial OBJECT-TYPE
    SYNTAX  DisplayString (SIZE(0..32))
    MAX-ACCESS  read-only
    STATUS  current
    DESCRIPTION
          "External Port SFP/XFP device serial."
    ::= { sfpInfoTableEntry 9 }
sfpInfoPartNumber OBJECT-TYPE
    SYNTAX  DisplayString (SIZE(0..32))
    MAX-ACCESS  read-only
    STATUS  current
    DESCRIPTION
          "External Port SFP/XFP device part number."
    ::= { sfpInfoTableEntry 10 }

sfpInfoRevision OBJECT-TYPE
    SYNTAX  DisplayString (SIZE(0..32))
    MAX-ACCESS  read-only
    STATUS  current
    DESCRIPTION
          "External Port SFP/XFP device revision."
    ::= { sfpInfoTableEntry 11 }

sfpInfoVoltage OBJECT-TYPE
    SYNTAX  DisplayString (SIZE(0..32))
    MAX-ACCESS  read-only
    STATUS  current
    DESCRIPTION
          "External Port SFP/XFP device voltage."
    ::= { sfpInfoTableEntry 12 }

sfpInfoTemperature OBJECT-TYPE
    SYNTAX  DisplayString (SIZE(0..32))
    MAX-ACCESS  read-only
    STATUS  current
    DESCRIPTION
          "External Port SFP/XFP device temperature."
    ::= { sfpInfoTableEntry 13 }

sfpInfoWaveLength OBJECT-TYPE
    SYNTAX  DisplayString (SIZE(0..32))
    MAX-ACCESS  read-only
    STATUS  current
    DESCRIPTION
          "External Port SFP/XFP device laser wave length."
    ::= { sfpInfoTableEntry 14 }

accessInfoClearAllUserFailAttempts OBJECT-TYPE
    SYNTAX INTEGER {
        ok(1),
        clear(2)
    }
    MAX-ACCESS  read-write
    STATUS  current
    DESCRIPTION
        "Action Object. When set to clear(2),clears all the unsuccessful 
         attempts of users.  Otherwise nothing is done.
         ok(1) is returned always when read."
    ::= { accessInfo 1 }

accessInfoClearAllUserLocks OBJECT-TYPE
    SYNTAX INTEGER {
        ok(1),
        clear(2)
    }
    MAX-ACCESS  read-write
    STATUS  current
    DESCRIPTION
        "Action Object. When set to clear(2), Unlock all locked users. 
         Otherwise nothing is done. ok(1) is returned always when read."
    ::= { accessInfo 2 }

accessUserInfoTable OBJECT-TYPE
    SYNTAX  SEQUENCE OF AccessUserInfoTableEntry
    MAX-ACCESS  not-accessible
    STATUS  current
    DESCRIPTION
        "The table of user information."
    ::= { accessInfo 3 }

accessUserInfoTableEntry OBJECT-TYPE
    SYNTAX  AccessUserInfoTableEntry
    MAX-ACCESS  not-accessible
    STATUS  current
    DESCRIPTION
        "An entry in the user information table."
    INDEX   { accessUserInfoIndex}
    ::= { accessUserInfoTable 1 }

AccessUserInfoTableEntry ::= SEQUENCE {
    accessUserInfoIndex     Integer32,
    accessUserInfoLockState INTEGER,
    accessUserInfoClearFailAttempts INTEGER,
    accessUserInfoClearLock        INTEGER
    }

accessUserInfoIndex OBJECT-TYPE
    SYNTAX  Integer32
    MAX-ACCESS  read-only
    STATUS  current
    DESCRIPTION
        "The table index. The index value corresponds to the same value
         of agAccessUserCurCfgUId for the user."
    ::= { accessUserInfoTableEntry 1 }

accessUserInfoLockState OBJECT-TYPE
    SYNTAX INTEGER {
        unlocked(1),
        locked(2)
    }
    MAX-ACCESS  read-only
    STATUS  current
    DESCRIPTION
        "Lock State of a specific user, unlocked(1) or locked(2).
         When the state is locked the user is not allowed to login 
         until the account is unlocked by the administrator."
    ::= { accessUserInfoTableEntry 2 }

accessUserInfoClearFailAttempts OBJECT-TYPE
    SYNTAX INTEGER {
        ok(1),
        clear(2)
    }
    MAX-ACCESS  read-write
    STATUS  current
    DESCRIPTION
        "Action Object. When set to clear(2), clears 
         the unsuccessful attempts of a particular user.
         Otherwise nothing is done. 
         ok(1) is returned always when read."
    ::= { accessUserInfoTableEntry 3 }

accessUserInfoClearLock OBJECT-TYPE
    SYNTAX INTEGER {
        ok(1),
        clear(2)
    }
    MAX-ACCESS  read-write
    STATUS  current
    DESCRIPTION
        "Action Object. When set to clear(2), unlock a particular user.
         Otherwise nothing is done. 
         ok(1) is returned always when read."
    ::= { accessUserInfoTableEntry 4 }




-- endif /* defined(WEB_UI) */

-- ----------------------------------------------------------------------------
-- } INSERT:  agent
-- ----------------------------------------------------------------------------

layer2                  OBJECT IDENTIFIER ::= { g8264T-mgmt 2 }
-- ----------------------------------------------------------------------------
-- { INSERT:  layer2
-- ----------------------------------------------------------------------------

layer2Configs     OBJECT IDENTIFIER ::= { layer2 1 }
layer2Stats       OBJECT IDENTIFIER ::= { layer2 2 }
layer2Info        OBJECT IDENTIFIER ::= { layer2 3 }

layer2Oper        OBJECT IDENTIFIER ::= { layer2 4 }

vlan              OBJECT IDENTIFIER ::= { layer2Configs 1 }
trunkgroup        OBJECT IDENTIFIER ::= { layer2Configs 2 }

stgCfg            OBJECT IDENTIFIER ::= { layer2Configs 3 }

mirroring         OBJECT IDENTIFIER ::= { layer2Configs 4 }

lacp              OBJECT IDENTIFIER ::= { layer2Configs 5 }
thash             OBJECT IDENTIFIER ::= { layer2Configs 6 }

mstCfg            OBJECT IDENTIFIER ::= { layer2Configs 7 }

l2GeneralCfg      OBJECT IDENTIFIER ::= { layer2Configs 8 }

failoverCfg       OBJECT IDENTIFIER ::= { layer2Configs 10 }
-- ----------------------------------------------------------------------------
-- { INSERT:  failoverCfg
-- ----------------------------------------------------------------------------

-- ----------------------------------------------------------------------------
-- { GLOBAL TEAMING CONFIG
-- ----------------------------------------------------------------------------

failoverCurCfgOnState                 OBJECT-TYPE
    SYNTAX      INTEGER  {
                    on(1),
                    off(2)
                }
    MAX-ACCESS  read-only
    STATUS      current
    DESCRIPTION
        "Failover ON/OFF setting."
    ::= { failoverCfg 1 }

failoverNewCfgOnState                 OBJECT-TYPE
    SYNTAX      INTEGER  {
                    on(1),
                    off(2)
                }
    MAX-ACCESS  read-write
    STATUS      current
    DESCRIPTION
        "Failover ON/OFF settings."
    ::= { failoverCfg 2 }


failoverMaxTriggerEntries             OBJECT-TYPE
    SYNTAX      Integer32
    MAX-ACCESS  read-only
    STATUS      current
    DESCRIPTION
        "The maximum number of entries in the Failover Trigger Table."
    ::= { failoverCfg 5 }

-- } GLOBAL TEAMING CONFIG

-- ----------------------------------------------------------------------------
-- { CUR TEAMING FOP CONFIG
-- ----------------------------------------------------------------------------

failoverCurCfgTriggerTable             OBJECT-TYPE
    SYNTAX      SEQUENCE OF FailoverCurCfgTriggerTableEntry
    MAX-ACCESS  not-accessible
    STATUS      current
    DESCRIPTION
        "The Failover Trigger Table."
    ::= { failoverCfg 6 }

failoverCurCfgTriggerTableEntry        OBJECT-TYPE
    SYNTAX      FailoverCurCfgTriggerTableEntry
    MAX-ACCESS  not-accessible
    STATUS      current
    DESCRIPTION
        "A row in the Failover Trigger Table."
    INDEX  { failoverCurCfgTriggerId }
    ::= { failoverCurCfgTriggerTable 1 }

FailoverCurCfgTriggerTableEntry ::= SEQUENCE {
    failoverCurCfgTriggerId            Integer32,
    failoverCurCfgTriggerLimit         INTEGER, 
    failoverCurCfgTriggerMmonPort      OCTET STRING,
    failoverCurCfgTriggerMmonTrunk     OCTET STRING,
    failoverCurCfgTriggerMmonKey       DisplayString,
    failoverCurCfgTriggerMconPort      OCTET STRING,
    failoverCurCfgTriggerMconTrunk     OCTET STRING,
    failoverCurCfgTriggerMconKey       DisplayString,
    failoverCurCfgTriggerState         INTEGER
    }

failoverCurCfgTriggerId                OBJECT-TYPE
    SYNTAX      Integer32
    MAX-ACCESS  read-only
    STATUS      current
    DESCRIPTION
        "The Trigger identifier."
    ::= { failoverCurCfgTriggerTableEntry 1 }

failoverCurCfgTriggerState             OBJECT-TYPE
    SYNTAX      INTEGER  {
                    enabled(1),
                    disabled(2)
                }
    MAX-ACCESS  read-only
    STATUS      current
    DESCRIPTION
        "Enable or disable Trigger state"
    ::= { failoverCurCfgTriggerTableEntry 2 }


failoverCurCfgTriggerLimit             OBJECT-TYPE
    SYNTAX      INTEGER
    MAX-ACCESS  read-only
    STATUS      current
    DESCRIPTION
        "Limit # of operational links"
    ::= { failoverCurCfgTriggerTableEntry 3 }




failoverCurCfgTriggerMmonPort          OBJECT-TYPE
    SYNTAX      OCTET STRING
    MAX-ACCESS  read-only
    STATUS      current
    DESCRIPTION
        "The Manual Monitor port list. The ports are presented in bitmap format:

             OCTET 1  OCTET 2  .....
             xxxxxxxx xxxxxxxx .....
             ||    || |_ port 8
             ||    ||
             ||    ||___ port 7
             ||    |____ port 6
             ||      .    .   .
             ||_________ port 1
             |__________ reserved

         where x : 1 - The represented port belongs to the Manual Monitor
                   0 - The represented port does not belong to the Manual Monitor"
    ::= { failoverCurCfgTriggerTableEntry 6 }
 

failoverCurCfgTriggerMmonTrunk         OBJECT-TYPE
    SYNTAX      OCTET STRING
    MAX-ACCESS  read-only
    STATUS      current
    DESCRIPTION
        "The Manual Monitor trunk list. The trunks are presented in bitmap format:
 
             OCTET 1  OCTET 2  .....
             xxxxxxxx xxxxxxxx .....
             ||    || |_ trunk 8
             ||    ||
             ||    ||___ trunk 7
             ||    |____ trunk 6
             ||      .    .   .
             ||_________ trunk 1
             |__________ reserved
 
         where x : 1 - The represented trunk belongs to the Manual Monitor
                   0 - The represented trunk does not belong to the Manual Monitor"
    ::= { failoverCurCfgTriggerTableEntry 7 }
 
failoverCurCfgTriggerMmonKey           OBJECT-TYPE
    SYNTAX DisplayString
    MAX-ACCESS  read-only
    STATUS      current
    DESCRIPTION
        "The LACP admin key. This is an array of 16-bit read-only values."
    ::= { failoverCurCfgTriggerTableEntry 8 }


failoverCurCfgTriggerMconPort          OBJECT-TYPE
    SYNTAX      OCTET STRING
    MAX-ACCESS  read-only
    STATUS      current
    DESCRIPTION
        "The Manual Control port list. The ports are presented in bitmap format:

             OCTET 1  OCTET 2  .....
             xxxxxxxx xxxxxxxx .....
             ||    || |_ port 8
             ||    ||
             ||    ||___ port 7
             ||    |____ port 6
             ||      .    .   .
             ||_________ port 1
             |__________ reserved

         where x : 1 - The represented port belongs to the Manual Control
                   0 - The represented port does not belong to the Manual Control"
    ::= { failoverCurCfgTriggerTableEntry 9 }
 
 

failoverCurCfgTriggerMconTrunk         OBJECT-TYPE
    SYNTAX      OCTET STRING
    MAX-ACCESS  read-only
    STATUS      current
    DESCRIPTION
        "The Manual Control trunk list. The trunks are presented in bitmap format:
 
             OCTET 1  OCTET 2  .....
             xxxxxxxx xxxxxxxx .....
             ||    || |_ trunk 8
             ||    ||
             ||    ||___ trunk 7
             ||    |____ trunk 6
             ||      .    .   .
             ||_________ trunk 1
             |__________ reserved
 
         where x : 1 - The represented trunk belongs to the Manual Control
                   0 - The represented trunk does not belong to the Manual Control"
    ::= { failoverCurCfgTriggerTableEntry 11 }
 
failoverCurCfgTriggerMconKey           OBJECT-TYPE
    SYNTAX      DisplayString
    MAX-ACCESS  read-only
    STATUS      current
    DESCRIPTION
        "The LACP admin key. This is an array of 16-bit read-only values."
    ::= { failoverCurCfgTriggerTableEntry 12 }
 

-- } CUR TEAMING FOP CONFIG

-- ----------------------------------------------------------------------------
-- { NEW TEAMING FOP CONFIG
-- ----------------------------------------------------------------------------

failoverNewCfgTriggerTable             OBJECT-TYPE
    SYNTAX      SEQUENCE OF FailoverNewCfgTriggerTableEntry
    MAX-ACCESS  not-accessible
    STATUS      current
    DESCRIPTION
        "The Failover Trigger Table."
    ::= { failoverCfg 7 }

failoverNewCfgTriggerTableEntry        OBJECT-TYPE
    SYNTAX      FailoverNewCfgTriggerTableEntry
    MAX-ACCESS  not-accessible
    STATUS      current
    DESCRIPTION
        "A row in the Failover Trigger Table."
    INDEX  { failoverNewCfgTriggerId }
    ::= { failoverNewCfgTriggerTable 1 }

FailoverNewCfgTriggerTableEntry ::= SEQUENCE {
    failoverNewCfgTriggerId            Integer32,
    failoverNewCfgTriggerLimit         INTEGER,
    failoverNewCfgTriggerMmonPort      OCTET STRING,
    failoverNewCfgTriggerMmonPortAdd   PortNumber,
    failoverNewCfgTriggerMmonPortRem   PortNumber,
    failoverNewCfgTriggerMmonTrunk     OCTET STRING,
    failoverNewCfgTriggerMmonTrunkAdd  INTEGER,
    failoverNewCfgTriggerMmonTrunkRem  INTEGER,
    failoverNewCfgTriggerMmonKey       DisplayString,
    failoverNewCfgTriggerMmonKeyAdd    INTEGER,
    failoverNewCfgTriggerMmonKeyRem    INTEGER,
    failoverNewCfgTriggerMconPort      OCTET STRING,
    failoverNewCfgTriggerMconPortAdd   PortNumber,
    failoverNewCfgTriggerMconPortRem   PortNumber,
    failoverNewCfgTriggerMconTrunk     OCTET STRING,
    failoverNewCfgTriggerMconTrunkAdd  INTEGER,
    failoverNewCfgTriggerMconTrunkRem  INTEGER,
    failoverNewCfgTriggerMconKey       DisplayString,
    failoverNewCfgTriggerMconKeyAdd    INTEGER,
    failoverNewCfgTriggerMconKeyRem    INTEGER,
    failoverNewCfgTriggerState         INTEGER,
    failoverNewCfgTriggerDelete        INTEGER
    }
 
failoverNewCfgTriggerId                OBJECT-TYPE
    SYNTAX      Integer32
    MAX-ACCESS  read-only
    STATUS      current
    DESCRIPTION
        "The Trigger identifier."
    ::= { failoverNewCfgTriggerTableEntry 1 }

failoverNewCfgTriggerState             OBJECT-TYPE
    SYNTAX      INTEGER  {
                    enabled(1),
                    disabled(2)
                }
    MAX-ACCESS  read-write
    STATUS      current
    DESCRIPTION
        "Enable or disable Trigger state"
    ::= { failoverNewCfgTriggerTableEntry 2 }

failoverNewCfgTriggerLimit             OBJECT-TYPE
    SYNTAX      INTEGER (0..1024)
    MAX-ACCESS  read-write
    STATUS      current
    DESCRIPTION
        "Limit # of operational links"
    ::= { failoverNewCfgTriggerTableEntry 3 }



failoverNewCfgTriggerMmonPort          OBJECT-TYPE
    SYNTAX      OCTET STRING
    MAX-ACCESS  read-only
    STATUS      current
    DESCRIPTION
        "The Manual Monitor port list. The ports are presented in bitmap format:

             OCTET 1  OCTET 2  .....
             xxxxxxxx xxxxxxxx .....
             ||    || |_ port 8
             ||    ||
             ||    ||___ port 7
             ||    |____ port 6
             ||      .    .   .
             ||_________ port 1
             |__________ reserved

         where x : 1 - The represented port belongs to the Manual Monitor
                   0 - The represented port does not belong to the Manual Monitor"
    ::= { failoverNewCfgTriggerTableEntry 10 }

failoverNewCfgTriggerMmonPortAdd       OBJECT-TYPE
    SYNTAX      PortNumber
    MAX-ACCESS  read-create
    STATUS      current
    DESCRIPTION
        "Add port to Manual Monitor.  When read, 0 is returned."
    ::= { failoverNewCfgTriggerTableEntry 11 }

failoverNewCfgTriggerMmonPortRem       OBJECT-TYPE
    SYNTAX      PortNumber
    MAX-ACCESS  read-create
    STATUS      current
    DESCRIPTION
        "Remove port from Manual Monitor.  When read, 0 is returned."
    ::= { failoverNewCfgTriggerTableEntry 12 }


failoverNewCfgTriggerMmonTrunk         OBJECT-TYPE
    SYNTAX      OCTET STRING
    MAX-ACCESS  read-only
    STATUS      current
    DESCRIPTION
        "The Manual Monitor trunk list. The trunks are presented in bitmap format:

             OCTET 1  OCTET 2  .....
             xxxxxxxx xxxxxxxx .....
             ||    || |_ trunk 8
             ||    ||
             ||    ||___ trunk 7
             ||    |____ trunk 6
             ||      .    .   .
             ||_________ trunk 1
             |__________ reserved

         where x : 1 - The represented trunk belongs to the Manual Monitor
                   0 - The represented trunk does not belong to the Manual Monitor"
    ::= { failoverNewCfgTriggerTableEntry 13 }

failoverNewCfgTriggerMmonTrunkAdd      OBJECT-TYPE
    SYNTAX      INTEGER
    MAX-ACCESS  read-create
    STATUS      current
    DESCRIPTION
        "Add trunk to Manual Monitor.  When read, 0 is returned."
    ::= { failoverNewCfgTriggerTableEntry 14 }

failoverNewCfgTriggerMmonTrunkRem      OBJECT-TYPE
    SYNTAX      INTEGER
    MAX-ACCESS  read-create
    STATUS      current
    DESCRIPTION
        "Remove trunk from Manual Monitor.  When read, 0 is returned."
    ::= { failoverNewCfgTriggerTableEntry 15 }
 
failoverNewCfgTriggerMmonKey           OBJECT-TYPE
    SYNTAX      DisplayString
    MAX-ACCESS  read-only
    STATUS      current
    DESCRIPTION
        "The LACP admin key. This is an array of 16-bit read-only values."
    ::= { failoverNewCfgTriggerTableEntry 16 }

failoverNewCfgTriggerMmonKeyAdd        OBJECT-TYPE
    SYNTAX      INTEGER (1..65535)
    MAX-ACCESS  read-create
    STATUS      current
    DESCRIPTION
        "Add LACP admin key to Manual Monitor.  When read, 0 is returned."
    ::= { failoverNewCfgTriggerTableEntry 17 }

failoverNewCfgTriggerMmonKeyRem        OBJECT-TYPE
    SYNTAX      INTEGER (1..65535) 
    MAX-ACCESS  read-create
    STATUS      current  
    DESCRIPTION 
        "Remove LACP admin key from Manual Monitor.  When read, 0 is returned."
    ::= { failoverNewCfgTriggerTableEntry 18 } 


failoverNewCfgTriggerMconPort          OBJECT-TYPE
    SYNTAX      OCTET STRING
    MAX-ACCESS  read-only
    STATUS      current
    DESCRIPTION
        "The Manual Control port list. The ports are presented in bitmap format:

             OCTET 1  OCTET 2  .....
             xxxxxxxx xxxxxxxx .....
             ||    || |_ port 8
             ||    ||
             ||    ||___ port 7
             ||    |____ port 6
             ||      .    .   .
             ||_________ port 1
             |__________ reserved

         where x : 1 - The represented port belongs to the Manual Control
                   0 - The represented port does not belong to the Manual Control"
    ::= { failoverNewCfgTriggerTableEntry 19 }

failoverNewCfgTriggerMconPortAdd       OBJECT-TYPE
    SYNTAX      PortNumber
    MAX-ACCESS  read-create
    STATUS      current
    DESCRIPTION
        "Add port to Manual Control.  When read, 0 is returned."
    ::= { failoverNewCfgTriggerTableEntry 20 }

failoverNewCfgTriggerMconPortRem       OBJECT-TYPE
    SYNTAX      PortNumber
    MAX-ACCESS  read-create
    STATUS      current
    DESCRIPTION
        "Remove port from Manual Control.  When read, 0 is returned."
    ::= { failoverNewCfgTriggerTableEntry 21 }



failoverNewCfgTriggerMconTrunk         OBJECT-TYPE
    SYNTAX      OCTET STRING
    MAX-ACCESS  read-only
    STATUS      current
    DESCRIPTION
        "The Manual Control trunk list. The trunks are presented in bitmap format:

             OCTET 1  OCTET 2  .....
             xxxxxxxx xxxxxxxx .....
             ||    || |_ trunk 8
             ||    ||
             ||    ||___ trunk 7
             ||    |____ trunk 6
             ||      .    .   .
             ||_________ trunk 1
             |__________ reserved

         where x : 1 - The represented trunk belongs to the Manual Control
                   0 - The represented trunk does not belong to the Manual Control"
    ::= { failoverNewCfgTriggerTableEntry 25 }

failoverNewCfgTriggerMconTrunkAdd      OBJECT-TYPE
    SYNTAX      INTEGER
    MAX-ACCESS  read-create
    STATUS      current
    DESCRIPTION
        "Add trunk to Manual Control.  When read, 0 is returned."
    ::= { failoverNewCfgTriggerTableEntry 26 }

failoverNewCfgTriggerMconTrunkRem      OBJECT-TYPE
    SYNTAX      INTEGER
    MAX-ACCESS  read-create
    STATUS      current
    DESCRIPTION
        "Remove trunk from Manual Control.  When read, 0 is returned."
    ::= { failoverNewCfgTriggerTableEntry 27 }
 
failoverNewCfgTriggerMconKey           OBJECT-TYPE
    SYNTAX      DisplayString
    MAX-ACCESS  read-only
    STATUS      current
    DESCRIPTION
        "The LACP admin key. This is an array of 16-bit read-only values."
    ::= { failoverNewCfgTriggerTableEntry 28 }

failoverNewCfgTriggerMconKeyAdd        OBJECT-TYPE
    SYNTAX      INTEGER (1..65535)
    MAX-ACCESS  read-create
    STATUS      current
    DESCRIPTION
        "Add LACP admin key to Manual Control.  When read, 0 is returned."
    ::= { failoverNewCfgTriggerTableEntry 29 }

failoverNewCfgTriggerMconKeyRem        OBJECT-TYPE
    SYNTAX      INTEGER (1..65535) 
    MAX-ACCESS  read-create
    STATUS      current  
    DESCRIPTION 
        "Remove LACP admin key from Manual Control.  When read, 0 is returned."
    ::= { failoverNewCfgTriggerTableEntry 30 } 


failoverNewCfgTriggerDelete            OBJECT-TYPE
    SYNTAX      INTEGER  {
                    other(1),
                    delete(2)
                }
    MAX-ACCESS  read-create
    STATUS      current
    DESCRIPTION
        "Setting the value to delete(2) will delete the entire
         row.  When read, other(1) is returned."
    ::= { failoverNewCfgTriggerTableEntry 31 } 

-- } NEW TEAMING FOP CONFIG


-- ----------------------------------------------------------------------------
-- } INSERT:  failoverCfg
-- ----------------------------------------------------------------------------

dot1x             OBJECT IDENTIFIER ::= { layer2Configs 12 }

fdb               OBJECT IDENTIFIER ::= { layer2Configs 13 }

hotlinksCfg       OBJECT IDENTIFIER ::= { layer2Configs 14 }
-- ----------------------------------------------------------------------------
-- { INSERT:  hotlinksCfg
-- ----------------------------------------------------------------------------

-- ----------------------------------------------------------------------------
-- { GLOBAL HOTLINKS CONFIG
-- ----------------------------------------------------------------------------

hotlinksCurCfgOnState                  OBJECT-TYPE
    SYNTAX      INTEGER  {
                    on(1),
                    off(2)
                }
    MAX-ACCESS  read-only
    STATUS      current
    DESCRIPTION
        "Hot Links ON/OFF setting."
    ::= { hotlinksCfg 1 }

hotlinksNewCfgOnState                  OBJECT-TYPE
    SYNTAX      INTEGER  {
                    on(1),
                    off(2)
                }
    MAX-ACCESS  read-write
    STATUS      current
    DESCRIPTION
        "Hot Links ON/OFF settings."
    ::= { hotlinksCfg 2 }

hotlinksCurCfgFdbUpdateState           OBJECT-TYPE
    SYNTAX      INTEGER {
                    enabled(1),
                    disabled(2)
                }
    MAX-ACCESS  read-only
    STATUS      current
    DESCRIPTION
        "Enable/disable Hot Links FDB Update setting."
    ::= { hotlinksCfg 3 }

hotlinksNewCfgFdbUpdateState           OBJECT-TYPE
    SYNTAX      INTEGER  {
                    enabled(1),
                    disabled(2)
                }
    MAX-ACCESS  read-write
    STATUS      current
    DESCRIPTION
        "Enable/disable Hot Links FDB Update setting."
    ::= { hotlinksCfg 4 }

hotlinksMaxTriggerEntries              OBJECT-TYPE
    SYNTAX      Integer32
    MAX-ACCESS  read-only
    STATUS      current
    DESCRIPTION
        "The maximum number of entries in the Hot Links Trigger Table."
    ::= { hotlinksCfg 5 }

-- } GLOBAL HOTLINKS CONFIG

-- ----------------------------------------------------------------------------
-- { CUR HOTLINKS FOP CONFIG
-- ----------------------------------------------------------------------------

hotlinksCurCfgTriggerTable             OBJECT-TYPE
    SYNTAX      SEQUENCE OF HotlinksCurCfgTriggerTableEntry
    MAX-ACCESS  not-accessible
    STATUS      current
    DESCRIPTION
        "The Hot Links Trigger Table."
    ::= { hotlinksCfg 6 }

hotlinksCurCfgTriggerTableEntry        OBJECT-TYPE
    SYNTAX      HotlinksCurCfgTriggerTableEntry
    MAX-ACCESS  not-accessible
    STATUS      current
    DESCRIPTION
        "A row in the Hot Links Trigger Table."
    INDEX  { hotlinksCurCfgTriggerId }
    ::= { hotlinksCurCfgTriggerTable 1 }

HotlinksCurCfgTriggerTableEntry ::= SEQUENCE {
    hotlinksCurCfgTriggerId                Integer32,
    hotlinksCurCfgTriggerName              DisplayString,
    hotlinksCurCfgTriggerState             INTEGER,
    hotlinksCurCfgTriggerPreemptState      INTEGER, 
    hotlinksCurCfgTriggerFdelay            Integer32,
    hotlinksCurCfgTriggerMasterPort        Integer32,
    hotlinksCurCfgTriggerMasterTrunk       Integer32,
    hotlinksCurCfgTriggerBackupPort        Integer32,
    hotlinksCurCfgTriggerBackupTrunk       Integer32,
    hotlinksCurCfgTriggerDelete            INTEGER
  , hotlinksCurCfgTriggerMasterAdminkey    Integer32
  , hotlinksCurCfgTriggerBackupAdminkey    Integer32
    }

hotlinksCurCfgTriggerId                OBJECT-TYPE
    SYNTAX      Integer32
    MAX-ACCESS  read-only
    STATUS      current
    DESCRIPTION
        "The Trigger identifier."
    ::= { hotlinksCurCfgTriggerTableEntry 1 }

hotlinksCurCfgTriggerName              OBJECT-TYPE
    SYNTAX      DisplayString
    MAX-ACCESS  read-only
    STATUS      current
    DESCRIPTION
        "A textual string containing the trigger name."
    ::= { hotlinksCurCfgTriggerTableEntry 2 }

hotlinksCurCfgTriggerState             OBJECT-TYPE
    SYNTAX      INTEGER  {
                    enabled(1),
                    disabled(2)
                }
    MAX-ACCESS  read-only
    STATUS      current
    DESCRIPTION
        "Enable/disable Trigger state."
    ::= { hotlinksCurCfgTriggerTableEntry 3 }

hotlinksCurCfgTriggerPreemptState      OBJECT-TYPE
    SYNTAX      INTEGER  {
                    enabled(1),
                    disabled(2)
                }
    MAX-ACCESS  read-only
    STATUS      current
    DESCRIPTION
        "Enable/disable Preemption state."
    ::= { hotlinksCurCfgTriggerTableEntry 4 }

hotlinksCurCfgTriggerFdelay            OBJECT-TYPE
    SYNTAX      Integer32
    MAX-ACCESS  read-only
    STATUS      current
    DESCRIPTION
        "Forward Delay setting (in secs)."
    ::= { hotlinksCurCfgTriggerTableEntry 5 }

hotlinksCurCfgTriggerMasterPort        OBJECT-TYPE
    SYNTAX      Integer32
    MAX-ACCESS  read-only
    STATUS      current
    DESCRIPTION
        "The master interface port number."
    ::= { hotlinksCurCfgTriggerTableEntry 6 }

hotlinksCurCfgTriggerMasterTrunk       OBJECT-TYPE
    SYNTAX      Integer32
    MAX-ACCESS  read-only
    STATUS      current
    DESCRIPTION
        "The master interface trunk number."
    ::= { hotlinksCurCfgTriggerTableEntry 7 }

hotlinksCurCfgTriggerBackupPort        OBJECT-TYPE
    SYNTAX      Integer32
    MAX-ACCESS  read-only
    STATUS      current
    DESCRIPTION
        "The backup interface port number."
    ::= { hotlinksCurCfgTriggerTableEntry 8 }

hotlinksCurCfgTriggerBackupTrunk       OBJECT-TYPE
    SYNTAX      Integer32
    MAX-ACCESS  read-only
    STATUS      current
    DESCRIPTION
        "The backup interface trunk number."
    ::= { hotlinksCurCfgTriggerTableEntry 9 }

hotlinksCurCfgTriggerDelete       OBJECT-TYPE
    SYNTAX      INTEGER  {
                    other(1),
                    delete(2)
                }
    MAX-ACCESS  read-only
    STATUS      current
    DESCRIPTION
        "Delete a Hot Links trigger configuration."
    ::= { hotlinksCurCfgTriggerTableEntry 10 }

hotlinksCurCfgTriggerMasterAdminkey       OBJECT-TYPE
    SYNTAX      Integer32
    MAX-ACCESS  read-only
    STATUS      current
    DESCRIPTION
        "The master interface admin key number."
    ::= { hotlinksCurCfgTriggerTableEntry 11 }

hotlinksCurCfgTriggerBackupAdminkey       OBJECT-TYPE
    SYNTAX      Integer32
    MAX-ACCESS  read-only
    STATUS      current
    DESCRIPTION
        "The backup interface admin key number."
    ::= { hotlinksCurCfgTriggerTableEntry 12 }


-- } CUR HOTLINKS FOP CONFIG

-- ----------------------------------------------------------------------------
-- { NEW HOTLINKS FOP CONFIG
-- ----------------------------------------------------------------------------

hotlinksNewCfgTriggerTable             OBJECT-TYPE
    SYNTAX      SEQUENCE OF HotlinksNewCfgTriggerTableEntry
    MAX-ACCESS  not-accessible
    STATUS      current
    DESCRIPTION
        "The Hot Links Trigger Table."
    ::= { hotlinksCfg 7 }

hotlinksNewCfgTriggerTableEntry        OBJECT-TYPE
    SYNTAX      HotlinksNewCfgTriggerTableEntry
    MAX-ACCESS  not-accessible
    STATUS      current
    DESCRIPTION
        "A row in the Hot Links Trigger Table."
    INDEX  { hotlinksNewCfgTriggerId }
    ::= { hotlinksNewCfgTriggerTable 1 }

HotlinksNewCfgTriggerTableEntry ::= SEQUENCE {
    hotlinksNewCfgTriggerId                       Integer32,
    hotlinksNewCfgTriggerName                     DisplayString,
    hotlinksNewCfgTriggerState                    INTEGER,
    hotlinksNewCfgTriggerPreemptState             INTEGER, 
    hotlinksNewCfgTriggerFdelay                   Integer32,
    hotlinksNewCfgTriggerMasterPort               Integer32,
    hotlinksNewCfgTriggerMasterTrunk              Integer32,
    hotlinksNewCfgTriggerBackupPort               Integer32,
    hotlinksNewCfgTriggerBackupTrunk              Integer32,
    hotlinksNewCfgTriggerDelete                   INTEGER
  , hotlinksNewCfgTriggerMasterAdminkey           Integer32
  , hotlinksNewCfgTriggerBackupAdminkey           Integer32
    }
 
hotlinksNewCfgTriggerId                OBJECT-TYPE
    SYNTAX      Integer32
    MAX-ACCESS  read-only
    STATUS      current
    DESCRIPTION
        "The Trigger identifier."
    ::= { hotlinksNewCfgTriggerTableEntry 1 }

hotlinksNewCfgTriggerName              OBJECT-TYPE
    SYNTAX      DisplayString (SIZE(0..33))
    MAX-ACCESS  read-write
    STATUS      current
    DESCRIPTION
        "A textual string containing the trigger name."
    ::= { hotlinksNewCfgTriggerTableEntry 2 }

hotlinksNewCfgTriggerState             OBJECT-TYPE
    SYNTAX      INTEGER  {
                    enabled(1),
                    disabled(2)
                }
    MAX-ACCESS  read-write
    STATUS      current
    DESCRIPTION
        "Enable/disable Trigger state."
    ::= { hotlinksNewCfgTriggerTableEntry 3 }

hotlinksNewCfgTriggerPreemptState      OBJECT-TYPE
    SYNTAX      INTEGER  {
                    enabled(1),
                    disabled(2)
                }
    MAX-ACCESS  read-write
    STATUS      current
    DESCRIPTION
        "Enable/disable Preemption state."
    ::= { hotlinksNewCfgTriggerTableEntry 4 }

hotlinksNewCfgTriggerFdelay            OBJECT-TYPE
    SYNTAX      Integer32
    MAX-ACCESS  read-write
    STATUS      current
    DESCRIPTION
        "Forward Delay setting (in secs)."
    ::= { hotlinksNewCfgTriggerTableEntry 5 }

hotlinksNewCfgTriggerMasterPort        OBJECT-TYPE
    SYNTAX      Integer32
    MAX-ACCESS  read-write
    STATUS      current
    DESCRIPTION
        "The master interface port number."
    ::= { hotlinksNewCfgTriggerTableEntry 6 }

hotlinksNewCfgTriggerMasterTrunk       OBJECT-TYPE
    SYNTAX      Integer32
    MAX-ACCESS  read-write
    STATUS      current
    DESCRIPTION
        "The master interface trunk number."
    ::= { hotlinksNewCfgTriggerTableEntry 7 }

hotlinksNewCfgTriggerBackupPort        OBJECT-TYPE
    SYNTAX      Integer32
    MAX-ACCESS  read-write
    STATUS      current
    DESCRIPTION
        "The backup interface port number."
    ::= { hotlinksNewCfgTriggerTableEntry 8 }

hotlinksNewCfgTriggerBackupTrunk       OBJECT-TYPE
    SYNTAX      Integer32
    MAX-ACCESS  read-write
    STATUS      current
    DESCRIPTION
        "The backup interface trunk number."
    ::= { hotlinksNewCfgTriggerTableEntry 9 }

hotlinksNewCfgTriggerDelete       OBJECT-TYPE
    SYNTAX      INTEGER  {
                    other(1),
                    delete(2)
                }
    MAX-ACCESS  read-write
    STATUS      current
    DESCRIPTION
        "Delete a Hot Links trigger configuration."
    ::= { hotlinksNewCfgTriggerTableEntry 10 }

hotlinksNewCfgTriggerMasterAdminkey        OBJECT-TYPE
    SYNTAX      Integer32
    MAX-ACCESS  read-write
    STATUS      current
    DESCRIPTION
        "The master interface admin key number."
    ::= { hotlinksNewCfgTriggerTableEntry 11 }

hotlinksNewCfgTriggerBackupAdminkey        OBJECT-TYPE
    SYNTAX      Integer32
    MAX-ACCESS  read-write
    STATUS      current
    DESCRIPTION
        "The backup interface admin key number."
    ::= { hotlinksNewCfgTriggerTableEntry 12 }

-- } NEW HOTLINKS FOP CONFIG

-- ----------------------------------------------------------------------------
-- { BPDU FLOOD CONFIG
-- ----------------------------------------------------------------------------
hotlinksCurCfgBpduState                OBJECT-TYPE
    SYNTAX      INTEGER {
                    enabled(1),
                    disabled(2)
                }
    MAX-ACCESS  read-only
    STATUS      current
    DESCRIPTION
        "Enable/disable Hot Links BPDU flood setting."
    ::= { hotlinksCfg 8 }

hotlinksNewCfgBpduState                OBJECT-TYPE
    SYNTAX      INTEGER  {
                    enabled(1),
                    disabled(2)
                }
    MAX-ACCESS  read-write
    STATUS      current
    DESCRIPTION
        "Enable/disable Hot Links BPDU flood setting."
    ::= { hotlinksCfg 9 }

-- } BPDU FLOOD CONFIG

-- ----------------------------------------------------------------------------
-- { FDB UPDATE RATE CONFIG
-- ----------------------------------------------------------------------------
hotlinksCurCfgFdbUpdateRate            OBJECT-TYPE
    SYNTAX      Integer32
    MAX-ACCESS  read-only
    STATUS      current
    DESCRIPTION
        "Hot Links FDB update rate (packets per second)."
    ::= { hotlinksCfg 10 }

hotlinksNewCfgFdbUpdateRate            OBJECT-TYPE
    SYNTAX      Integer32
    MAX-ACCESS  read-write
    STATUS      current
    DESCRIPTION
        "Hot Links FDB update rate (packets per second)."
    ::= { hotlinksCfg 11 }

-- } FDB UPDATE RATE CONFIG

-- ----------------------------------------------------------------------------
-- } INSERT:  hotlinksCfg
-- ----------------------------------------------------------------------------
lldpCfg           OBJECT IDENTIFIER ::= { layer2Configs 15 }

vlagCfg           OBJECT IDENTIFIER ::= { layer2Configs 18 }
vlagIslCfg        OBJECT IDENTIFIER ::= { vlagCfg 1 }

ecpCfg            OBJECT IDENTIFIER ::= { layer2Configs 19 }

thashL2L3         OBJECT IDENTIFIER ::= { thash 1 }
thashFcoe         OBJECT IDENTIFIER ::= { thash 2 }

mirrPortMirr      OBJECT IDENTIFIER ::= { mirroring 1 }

mstGeneralCfg     OBJECT IDENTIFIER ::= { mstCfg 1 }
mstCistCfg        OBJECT IDENTIFIER ::= { mstCfg 2 }

dot1xCurCfgGlobalTable  OBJECT IDENTIFIER ::= { dot1x  5 }

dot1xCurCfgGuestVlan    OBJECT IDENTIFIER ::= { dot1xCurCfgGlobalTable 1 }

dot1xNewCfgGlobalTable  OBJECT IDENTIFIER ::= { dot1x  6 }

fdbGeneralCfg	  OBJECT IDENTIFIER ::= { fdb 1 }


-- FDB
fdbCurCfgAgingTime  OBJECT-TYPE
    SYNTAX   Integer32
    MAX-ACCESS  read-only
    STATUS  current
    DESCRIPTION
        "Fdb current aging time"
    ::= { fdbGeneralCfg 1 }

fdbNewCfgAgingTime OBJECT-TYPE
    SYNTAX   Integer32
    MAX-ACCESS  read-write
    STATUS  current
    DESCRIPTION
        "Fdb new aging time."
    ::= { fdbGeneralCfg 2 }

dot1xNewCfgGuestVlan    OBJECT IDENTIFIER ::= { dot1xNewCfgGlobalTable 1 }


fdbStats          OBJECT IDENTIFIER ::= { layer2Stats 1 }

stpStats          OBJECT IDENTIFIER ::= { layer2Stats 2 }


lacpStats         OBJECT IDENTIFIER ::= { layer2Stats 4 }
hotlinksStats     OBJECT IDENTIFIER ::= { layer2Stats 6 }
-- ----------------------------------------------------------------------------
-- { INSERT:  hotlinksStats
-- ----------------------------------------------------------------------------

hotlinksStatsTriggerTable              OBJECT-TYPE
    SYNTAX      SEQUENCE OF HotlinksStatsTriggerTableEntry
    MAX-ACCESS  not-accessible
    STATUS      current
    DESCRIPTION
        "The Hot Links Trigger Table Stats."
    ::= { hotlinksStats 1 }

hotlinksStatsTriggerTableEntry         OBJECT-TYPE
    SYNTAX      HotlinksStatsTriggerTableEntry
    MAX-ACCESS  not-accessible
    STATUS      current
    DESCRIPTION
        "A row in the Hot Links Trigger Table Stats."
    INDEX  { hotlinksStatsTriggerId }
    ::= { hotlinksStatsTriggerTable 1 }

HotlinksStatsTriggerTableEntry ::= SEQUENCE {
    hotlinksStatsTriggerId             Integer32,
    hotlinksStatsTriggerName           DisplayString,
    hotlinksStatsTriggerMasterActive   Integer32,
    hotlinksStatsTriggerBackupActive   Integer32,
    hotlinksStatsTriggerFdbUpdate      Integer32,
    hotlinksStatsTriggerFdbFailed      Integer32
    }

hotlinksStatsTriggerId                 OBJECT-TYPE
    SYNTAX      Integer32
    MAX-ACCESS  read-only
    STATUS      current
    DESCRIPTION
        "The Trigger identifier."
    ::= { hotlinksStatsTriggerTableEntry 1 }

hotlinksStatsTriggerName               OBJECT-TYPE
    SYNTAX      DisplayString
    MAX-ACCESS  read-only
    STATUS      current
    DESCRIPTION
        "A textual string containing the trigger name."
    ::= { hotlinksStatsTriggerTableEntry 2 }

hotlinksStatsTriggerMasterActive       OBJECT-TYPE
    SYNTAX      Integer32
    MAX-ACCESS  read-only
    STATUS      current
    DESCRIPTION
        "The number of times the master interface was set to active."
    ::= { hotlinksStatsTriggerTableEntry 3 }

hotlinksStatsTriggerBackupActive       OBJECT-TYPE
    SYNTAX      Integer32
    MAX-ACCESS  read-only
    STATUS      current
    DESCRIPTION
        "The number of times the backup interface was set to active."
    ::= { hotlinksStatsTriggerTableEntry 4 }

hotlinksStatsTriggerFdbUpdate          OBJECT-TYPE
    SYNTAX      Integer32
    MAX-ACCESS  read-only
    STATUS      current
    DESCRIPTION
        "The number of times an FDB update was performed."
    ::= { hotlinksStatsTriggerTableEntry 5 }

hotlinksStatsTriggerFdbFailed          OBJECT-TYPE
    SYNTAX      Integer32
    MAX-ACCESS  read-only
    STATUS      current
    DESCRIPTION
        "The number of times an FDB update failed."
    ::= { hotlinksStatsTriggerTableEntry 6 }

-- ----------------------------------------------------------------------------
-- } INSERT:  hotlinksStats
-- ----------------------------------------------------------------------------
lldpStats	  OBJECT IDENTIFIER ::= { layer2Stats 7 }

oamStats          OBJECT IDENTIFIER ::= { layer2Stats 8 }


vlagStats         OBJECT IDENTIFIER ::= { layer2Stats 11 }
vlagStatsSystem   OBJECT IDENTIFIER ::= { vlagStats 1 }
vlagStatsIsl      OBJECT IDENTIFIER ::= { vlagStats 2 }
vlagStatsHealth   OBJECT IDENTIFIER ::= { vlagStats 3 }
vlagStatsLacp     OBJECT IDENTIFIER ::= { vlagStats 4 }
vlagStatsPdu      OBJECT IDENTIFIER ::= { vlagStats 5 }
vlagStatsIgmp     OBJECT IDENTIFIER ::= { vlagStats 6 }

fdbInfo           OBJECT IDENTIFIER ::= { layer2Info 1 }

stpInfo           OBJECT IDENTIFIER ::= { layer2Info 2 }

lacpInfo          OBJECT IDENTIFIER ::= { layer2Info 3 }

cistInfo          OBJECT IDENTIFIER ::= { layer2Info 4 }

genInfo           OBJECT IDENTIFIER ::= { layer2Info 7 }

vlanInfo          OBJECT IDENTIFIER ::= { layer2Info 5 }

dot1xInfo         OBJECT IDENTIFIER ::= { layer2Info 6 }

trunkGroupInfo    OBJECT IDENTIFIER ::= { layer2Info 9 }
hotlinksInfo      OBJECT IDENTIFIER ::= { layer2Info 10 }
-- ----------------------------------------------------------------------------
-- { INSERT:  hotlinksInfo
-- ----------------------------------------------------------------------------

hotlinksInfoOnState                    OBJECT-TYPE
    SYNTAX      INTEGER  {
                    on(1),
                    off(2)
                }
    MAX-ACCESS  read-only
    STATUS      current
    DESCRIPTION
        "Hot Links ON/OFF setting info."
    ::= { hotlinksInfo 1 }

hotlinksInfoFdbUpdateState             OBJECT-TYPE
    SYNTAX      INTEGER {
                    enabled(1),
                    disabled(2)
                }
    MAX-ACCESS  read-only
    STATUS      current
    DESCRIPTION
        "Enable/disable Hot Links FDB Update setting info."
    ::= { hotlinksInfo 2 }

hotlinksInfoTriggerTable               OBJECT-TYPE
    SYNTAX      SEQUENCE OF HotlinksInfoTriggerTableEntry
    MAX-ACCESS  not-accessible
    STATUS      current
    DESCRIPTION
        "The Hot Links Trigger Table Info."
    ::= { hotlinksInfo 3 }

hotlinksInfoBpduState                  OBJECT-TYPE
    SYNTAX      INTEGER {
                    enabled(1),
                    disabled(2)
                }
    MAX-ACCESS  read-only
    STATUS      current
    DESCRIPTION
        "Enable/disable Hot Links BPDU flood setting info."
    ::= { hotlinksInfo 4 }

hotlinksInfoFdbUpdateRate              OBJECT-TYPE
    SYNTAX      Integer32
    MAX-ACCESS  read-only
    STATUS      current
    DESCRIPTION
        "Hot Links FDB update rate (packets per second)."
    ::= { hotlinksInfo 5 }

hotlinksInfoTriggerTableEntry          OBJECT-TYPE
    SYNTAX      HotlinksInfoTriggerTableEntry
    MAX-ACCESS  not-accessible
    STATUS      current
    DESCRIPTION
        "A row in the Hot Links Trigger Table Info."
    INDEX  { hotlinksInfoTriggerId }
    ::= { hotlinksInfoTriggerTable 1 }

HotlinksInfoTriggerTableEntry ::= SEQUENCE {
    hotlinksInfoTriggerId                Integer32,
    hotlinksInfoTriggerName              DisplayString,
    hotlinksInfoTriggerState             INTEGER,
    hotlinksInfoTriggerPreemptState      INTEGER,
    hotlinksInfoTriggerFdelay            Integer32,
    hotlinksInfoTriggerActive            DisplayString
    }

hotlinksInfoTriggerId                  OBJECT-TYPE
    SYNTAX      Integer32
    MAX-ACCESS  read-only
    STATUS      current
    DESCRIPTION
        "The Trigger identifier."
    ::= { hotlinksInfoTriggerTableEntry 1 }

hotlinksInfoTriggerName                OBJECT-TYPE
    SYNTAX      DisplayString
    MAX-ACCESS  read-only
    STATUS      current
    DESCRIPTION
        "A textual string containing the trigger name."
    ::= { hotlinksInfoTriggerTableEntry 2 }

hotlinksInfoTriggerState               OBJECT-TYPE
    SYNTAX      INTEGER  {
                    enabled(1),
                    disabled(2)
                }
    MAX-ACCESS  read-only
    STATUS      current
    DESCRIPTION
        "Enable/disable Trigger state info."
    ::= { hotlinksInfoTriggerTableEntry 3 }

hotlinksInfoTriggerPreemptState        OBJECT-TYPE
    SYNTAX      INTEGER  {
                    enabled(1),
                    disabled(2)
                }
    MAX-ACCESS  read-only
    STATUS      current
    DESCRIPTION
        "Enable/disable Preemption state info."
    ::= { hotlinksInfoTriggerTableEntry 4 }

hotlinksInfoTriggerFdelay              OBJECT-TYPE
    SYNTAX      Integer32
    MAX-ACCESS  read-only
    STATUS      current
    DESCRIPTION
        "Forward Delay setting info (in secs)."
    ::= { hotlinksInfoTriggerTableEntry 5 }

hotlinksInfoTriggerActive              OBJECT-TYPE
    SYNTAX      DisplayString
    MAX-ACCESS  read-only
    STATUS      current
    DESCRIPTION
        "A textual string containing the active interface info."
    ::= { hotlinksInfoTriggerTableEntry 6 }



-- ----------------------------------------------------------------------------
-- } INSERT:  hotlinksInfo
-- ----------------------------------------------------------------------------
lldpInfo          OBJECT IDENTIFIER ::= { layer2Info 11 }

cistGeneralInfo   OBJECT IDENTIFIER ::= { cistInfo 1 }

dot1xSystemInfo   OBJECT IDENTIFIER ::= { dot1xInfo 2 }

oamInfo           OBJECT IDENTIFIER ::= { layer2Info 12 }

udldInfo          OBJECT IDENTIFIER ::= { layer2Info 13 }

failoverInfo      OBJECT IDENTIFIER ::= { layer2Info 14 }
-- ----------------------------------------------------------------------------
-- { INSERT:  failoverInfo
-- ----------------------------------------------------------------------------

failoverInfoState   OBJECT-TYPE
    SYNTAX      INTEGER {
                    on(1),
                    off(2)
                }
    MAX-ACCESS  read-only  
    STATUS      current
    DESCRIPTION 
        "Current state of failover"
    ::= { failoverInfo 1 }

failoverInfoTriggerTable    OBJECT-TYPE
    SYNTAX      SEQUENCE OF FailoverInfoTriggerEntry
    MAX-ACCESS  not-accessible
    STATUS      current
    DESCRIPTION 
        "This table holds the information for individual triggers"
    ::= { failoverInfo 3 }

failoverInfoTriggerEntry   OBJECT-TYPE
    SYNTAX      FailoverInfoTriggerEntry
    MAX-ACCESS  not-accessible
    STATUS      current
    DESCRIPTION
        "A row in the failover trigger table."
    INDEX       { failoverInfoTriggerId }
    ::= { failoverInfoTriggerTable 1 }

FailoverInfoTriggerEntry ::= SEQUENCE {
    failoverInfoTriggerId               Integer32,
    failoverInfoTriggerState            INTEGER,
    failoverInfoTriggerLimit            INTEGER, 
    failoverInfoTriggerMonitorState     INTEGER,
    failoverInfoTriggerMonitorPorts     OCTET STRING,
    failoverInfoTriggerControlState     INTEGER,
    failoverInfoTriggerControlPorts     OCTET STRING,
    failoverInfoTriggerControlPorts     OCTET STRING
    }

failoverInfoTriggerId   OBJECT-TYPE
    SYNTAX  Integer32
    MAX-ACCESS  read-only
    STATUS      current
    DESCRIPTION
        "The trigger identifier."
    ::= { failoverInfoTriggerEntry 1 }

failoverInfoTriggerState    OBJECT-TYPE
    SYNTAX      INTEGER  {
                    enabled(1),
                    disabled(2)
                }
    MAX-ACCESS  read-only
    STATUS      current
    DESCRIPTION
        "The trigger state."
    ::= { failoverInfoTriggerEntry 2 }

failoverInfoTriggerLimit    OBJECT-TYPE
    SYNTAX      INTEGER
    MAX-ACCESS  read-only
    STATUS      current
    DESCRIPTION
        "Limit number of operational links"
    ::= { failoverInfoTriggerEntry 3 }

failoverInfoTriggerMonitorState OBJECT-TYPE
    SYNTAX  INTEGER{
        up(1),
        down(2)
        }
    MAX-ACCESS  read-only
    STATUS  current
    DESCRIPTION
        "The runtime monitor state"
    ::= { failoverInfoTriggerEntry 4 }

failoverInfoTriggerMonitorPorts OBJECT-TYPE
    SYNTAX      OCTET STRING
    MAX-ACCESS  read-only
    STATUS      current
    DESCRIPTION
        "The list of ports that are monitored. The ports are
         represented in bitmap format in receiving order:

              OCTET 1  OCTET 2  .....
             xxxxxxxx xxxxxxxx .....
             ||    || |_ port 8
             ||    ||
             ||    ||___ port 7
             ||    |____ port 6
             ||      .    .   .
             ||_________ port 1
             |__________ reserved

         where x : 1 - The represented port belongs to Monitor list
            0 - The represented port does not belong to Monitor list"
    ::= { failoverInfoTriggerEntry 5 }

failoverInfoTriggerControlState OBJECT-TYPE
    SYNTAX      INTEGER{
        auto-controlled(1),
        auto-disabled(2)
        }
    MAX-ACCESS  read-only
    STATUS  current
    DESCRIPTION
        "The runtime control state"
    ::= { failoverInfoTriggerEntry 6 }

failoverInfoTriggerControlPorts OBJECT-TYPE
    SYNTAX      OCTET STRING
    MAX-ACCESS  read-only
    STATUS      current
    DESCRIPTION
        "The list of ports that are controlled. The ports are
         represented in bitmap format in receiving order:

              OCTET 1  OCTET 2  .....
             xxxxxxxx xxxxxxxx .....
             ||    || |_ port 8
             ||    ||
             ||    ||___ port 7
             ||    |____ port 6
             ||      .    .   .
             ||_________ port 1
             |__________ reserved

         where x : 1 - The represented port belongs to Control list
            0 - The represented port does not belong to Control list"
    ::= { failoverInfoTriggerEntry 7 }



failoverInfoMonPortStateTable    OBJECT-TYPE
    SYNTAX      SEQUENCE OF FailoverInfoTriggerMonPortEntry
    MAX-ACCESS  not-accessible
    STATUS      current
    DESCRIPTION 
        "This table holds the information for individual triggers"
    ::= { failoverInfo 4 }

failoverInfoTriggerMonPortEntry   OBJECT-TYPE
    SYNTAX      FailoverInfoTriggerMonPortEntry
    MAX-ACCESS  not-accessible
    STATUS      current
    DESCRIPTION
        "A row in the failover trigger table."
    INDEX       { failoverInfoTriggerMonId, failoverInfoTriggerMonPortId }
    ::= { failoverInfoMonPortStateTable 1 }

FailoverInfoTriggerMonPortEntry ::= SEQUENCE {
    failoverInfoTriggerMonId                   Integer32,
    failoverInfoTriggerMonPortId            PortNumber,
    failoverInfoTriggerMonPortStatus        INTEGER
    }

failoverInfoTriggerMonId   OBJECT-TYPE
    SYNTAX  Integer32
    MAX-ACCESS  read-only
    STATUS      current
    DESCRIPTION
        "The trigger identifier."
    ::= { failoverInfoTriggerMonPortEntry 1 }

failoverInfoTriggerMonPortId    OBJECT-TYPE
    SYNTAX  PortNumber
    MAX-ACCESS  read-only
    STATUS  current
    DESCRIPTION
        "The Port identifier."
    ::= { failoverInfoTriggerMonPortEntry 2 }

failoverInfoTriggerMonPortStatus    OBJECT-TYPE
    SYNTAX  INTEGER{
        failed(0),
        operational(1)
        }
    MAX-ACCESS  read-only
    STATUS  current
    DESCRIPTION
        "The Port Status."
    ::= { failoverInfoTriggerMonPortEntry 3 }


failoverInfoCtlPortStateTable    OBJECT-TYPE
    SYNTAX      SEQUENCE OF FailoverInfoTriggerCtlPortEntry
    MAX-ACCESS  not-accessible
    STATUS      current
    DESCRIPTION 
        "This table holds the information for individual triggers"
    ::= { failoverInfo 5 }

failoverInfoTriggerCtlPortEntry   OBJECT-TYPE
    SYNTAX      FailoverInfoTriggerCtlPortEntry
    MAX-ACCESS  not-accessible
    STATUS      current
    DESCRIPTION
        "A row in the failover trigger table."
    INDEX       { failoverInfoTriggerCtlId, failoverInfoTriggerCtlPortId }
    ::= { failoverInfoCtlPortStateTable 1 }

FailoverInfoTriggerCtlPortEntry ::= SEQUENCE {
    failoverInfoTriggerCtlId                   Integer32,
    failoverInfoTriggerCtlPortId            PortNumber,
    failoverInfoTriggerCtlPortStatus        INTEGER
    }

failoverInfoTriggerCtlId   OBJECT-TYPE
    SYNTAX  Integer32
    MAX-ACCESS  read-only
    STATUS      current
    DESCRIPTION
        "The trigger identifier."
    ::= { failoverInfoTriggerCtlPortEntry 1 }

failoverInfoTriggerCtlPortId    OBJECT-TYPE
    SYNTAX  PortNumber
    MAX-ACCESS  read-only
    STATUS  current
    DESCRIPTION
        "The Port identifier."
    ::= { failoverInfoTriggerCtlPortEntry 2 }

failoverInfoTriggerCtlPortStatus    OBJECT-TYPE
    SYNTAX  INTEGER{
        failed(0),
        operational(1)
        }
    MAX-ACCESS  read-only
    STATUS  current
    DESCRIPTION
        "The Port Status."
    ::= { failoverInfoTriggerCtlPortEntry 3 }


-- ----------------------------------------------------------------------------
-- } INSERT:  failoverInfo
-- ----------------------------------------------------------------------------

vlagInfo           OBJECT IDENTIFIER ::= { layer2Info 16 }
vlagInfoSystem     OBJECT IDENTIFIER ::= { vlagInfo 1 }
vlagInfoGroup      OBJECT IDENTIFIER ::= { vlagInfo 2 }
vlagInfoIslGroup   OBJECT IDENTIFIER ::= { vlagInfoGroup 2 }

ecpInfo            OBJECT IDENTIFIER ::= { layer2Info 17 }

-- VLAN group
vlanMaxEnt OBJECT-TYPE
    SYNTAX  Integer32 
    MAX-ACCESS  read-only
    STATUS  current
    DESCRIPTION
        "The maximum number of rows in the VLAN configuration table."
    ::= { vlan 1 }

vlanMaxVlanID OBJECT-TYPE
    SYNTAX  Integer32 
    MAX-ACCESS  read-only
    STATUS  current
    DESCRIPTION
        "The maximum allowed VLAN ID."
    ::= { vlan 4 }

vlanCurCfgTable OBJECT-TYPE
    SYNTAX  SEQUENCE OF VlanCurCfgTableEntry
    MAX-ACCESS  not-accessible
    STATUS  current
    DESCRIPTION
        "The table of VLAN configuration."
    ::= { vlan 2 }

vlanCurCfgTableEntry OBJECT-TYPE
    SYNTAX  VlanCurCfgTableEntry
    MAX-ACCESS  not-accessible
    STATUS  current
    DESCRIPTION
        "A row in the VLAN configuration table."
    INDEX  { vlanCurCfgVlanId }
    ::= { vlanCurCfgTable 1 }

VlanCurCfgTableEntry ::= SEQUENCE {
    vlanCurCfgVlanId 		Integer32,
    vlanCurCfgPorts 		OCTET STRING,
    vlanCurCfgState 		INTEGER,
    vlanCurCfgStg  	        Integer32,
    vlanCurCfgPrVlanType	INTEGER,
    vlanCurCfgPrVlanMapPriId 	Integer32,
    vlanCurCfgVlanName 		DisplayString
    }

vlanCurCfgVlanId OBJECT-TYPE
    SYNTAX  Integer32
    MAX-ACCESS  read-only
    STATUS  current
    DESCRIPTION
        "The VLAN identifier."
    ::= { vlanCurCfgTableEntry 1 }

vlanCurCfgPorts	OBJECT-TYPE
    SYNTAX  OCTET STRING
    MAX-ACCESS  read-only
    STATUS  current
    DESCRIPTION
        "The port list in the VLAN. The ports are presented in bitmap format.
	 in receiving order:

	     OCTET 1  OCTET 2  .....
             xxxxxxxx xxxxxxxx ..... 
             ||    || |_ port 8
             ||    ||  
             ||    ||___ port 7
             ||    |____ port 6
             ||      .    .   .
             ||_________ port 1
             |__________ reserved

         where x : 1 - The represented port belongs to the VLAN
		   0 - The represented port does not belong to the VLAN"
    ::= { vlanCurCfgTableEntry 2 }

vlanCurCfgState	OBJECT-TYPE
    SYNTAX  INTEGER  {
	enabled(2),
	disabled(3)
	}
    MAX-ACCESS  read-only
    STATUS  current
    DESCRIPTION
        "Enable or disable a VLAN"
    ::= { vlanCurCfgTableEntry 3 }


vlanCurCfgStg OBJECT-TYPE
    SYNTAX  Integer32  
    MAX-ACCESS  read-only
    STATUS  current
    DESCRIPTION
        "The Spanning Tree Group for the VLAN."
    ::= { vlanCurCfgTableEntry 5 }




vlanCurCfgVlanName OBJECT-TYPE
    SYNTAX  DisplayString (SIZE(0..32))
    MAX-ACCESS  read-only
    STATUS  current
    DESCRIPTION
        "The VLAN name."
    ::= { vlanCurCfgTableEntry 9 }

vlanCurCfgPrVlanType OBJECT-TYPE
    SYNTAX  INTEGER{
        none(0),
        primary(1),
        isolated(2),
        community(3)
        }
    MAX-ACCESS  read-only
    STATUS  current
    DESCRIPTION
        "The type of the Private VLAN."
    ::= { vlanCurCfgTableEntry 10 }

vlanCurCfgPrVlanMapPriId OBJECT-TYPE
    SYNTAX  Integer32
    MAX-ACCESS  read-only
    STATUS  current
    DESCRIPTION
        "The primary vlan id"
    ::= { vlanCurCfgTableEntry 11 }





vlanNewCfgTable OBJECT-TYPE
    SYNTAX  SEQUENCE OF VlanNewCfgTableEntry
    MAX-ACCESS  not-accessible
    STATUS  current
    DESCRIPTION
        "The table of VLAN configuration."
    ::= { vlan 3 }

vlanNewCfgTableEntry OBJECT-TYPE
    SYNTAX  VlanNewCfgTableEntry
    MAX-ACCESS  not-accessible
    STATUS  current
    DESCRIPTION
        "A row in the VLAN configuration table."
    INDEX  { vlanNewCfgVlanId }
    ::= { vlanNewCfgTable 1 }

VlanNewCfgTableEntry ::= SEQUENCE {
    vlanNewCfgVlanId 		Integer32,
    vlanNewCfgVlanName 		DisplayString,
    vlanNewCfgPorts 		OCTET STRING,
    vlanNewCfgState 		INTEGER,
    vlanNewCfgAddPort 		PortNumber,
    vlanNewCfgRemovePort	PortNumber,
    vlanNewCfgStg  	        Integer32,
    vlanNewCfgPrVlanType	INTEGER,
    vlanNewCfgPrVlanMapPriId 	Integer32,
    vlanNewCfgDelete 		INTEGER
    }
vlanNewCfgVlanId OBJECT-TYPE
    SYNTAX  Integer32
    MAX-ACCESS  read-only
    STATUS  current
    DESCRIPTION
        "The VLAN identifier."
    ::= { vlanNewCfgTableEntry 1 }

vlanNewCfgVlanName OBJECT-TYPE
    SYNTAX  DisplayString (SIZE(0..32))
    MAX-ACCESS  read-create
    STATUS  current
    DESCRIPTION
        "The VLAN name."
    ::= { vlanNewCfgTableEntry 2 }

vlanNewCfgPorts	OBJECT-TYPE
    SYNTAX  OCTET STRING
    MAX-ACCESS  read-only
    STATUS  current
    DESCRIPTION
        "The port list in the VLAN.  The ports are presented in bitmap format.
         in receiving order:

	     OCTET 1  OCTET 2  .....
             xxxxxxxx xxxxxxxx ..... 
             ||    || |_ port 8
             ||    ||  
             ||    ||___ port 7
             ||    |____ port 6
             ||      .    .   .
             ||_________ port 1
             |__________ reserved

         where x : 1 - The represented port belongs to the VLAN
	           0 - The represented port does not belong to the VLAN"
    ::= { vlanNewCfgTableEntry 3 }

vlanNewCfgState	OBJECT-TYPE
    SYNTAX  INTEGER  {
	enabled(2),
	disabled(3)
	}
    MAX-ACCESS  read-create
    STATUS  current
    DESCRIPTION
        "Enable or disable a VLAN"
    ::= { vlanNewCfgTableEntry 4 }

vlanNewCfgAddPort OBJECT-TYPE
    SYNTAX  PortNumber
    MAX-ACCESS  read-create
    STATUS  current
    DESCRIPTION
        "The port to be added to the specified VLAN.  A '0' value is 
         returned when read."
    ::= { vlanNewCfgTableEntry 5 }

vlanNewCfgRemovePort OBJECT-TYPE
    SYNTAX  PortNumber
    MAX-ACCESS  read-create
    STATUS  current
    DESCRIPTION
        "The port to be removed from the specified VLAN.  A '0'
         value is returned when read."
    ::= { vlanNewCfgTableEntry 6 }

vlanNewCfgDelete OBJECT-TYPE
    SYNTAX  INTEGER  {
        other(1),
        delete(2)
        }
    MAX-ACCESS  read-create
    STATUS  current
    DESCRIPTION
        "This is an action object to create or delete a VLAN.
         other(1) is returned always when read.
         The following values are writable: delete(2)...to delete a VLAN"
    ::= { vlanNewCfgTableEntry 7 }


vlanNewCfgStg OBJECT-TYPE
    SYNTAX  Integer32  
    MAX-ACCESS  read-create
    STATUS  current
    DESCRIPTION
        "The Spanning Tree Group for the VLAN."
    ::= { vlanNewCfgTableEntry 9 }




vlanNewCfgPrVlanType OBJECT-TYPE
    SYNTAX  INTEGER{
        none(0),
        primary(1),
        isolated(2),
        community(3)
        }
    MAX-ACCESS  read-write
    STATUS  current
    DESCRIPTION
        "The type of the Private VLAN."
    ::= { vlanNewCfgTableEntry 13 }

vlanNewCfgPrVlanMapPriId OBJECT-TYPE
    SYNTAX  Integer32
    MAX-ACCESS  read-write
    STATUS  current
    DESCRIPTION
        "The primary vlan id. To delete set 0."
    ::= { vlanNewCfgTableEntry 14 }





pvlanCurCfgTable OBJECT-TYPE
    SYNTAX  SEQUENCE OF PvlanCurCfgTableEntry
    MAX-ACCESS  not-accessible
    STATUS  current
    DESCRIPTION
        "The table of PROTOCOL VLAN configuration."
    ::= { vlan 5 } 

pvlanCurCfgTableEntry OBJECT-TYPE
    SYNTAX  PvlanCurCfgTableEntry
    MAX-ACCESS  not-accessible
    STATUS  current
    DESCRIPTION
        "A row in the Protocol VLAN configuration table."
    INDEX  { pvlanCurCfgVlanId, pvlanCurCfgPvlanId }
    ::= { pvlanCurCfgTable 1 } 

PvlanCurCfgTableEntry ::= SEQUENCE {
    pvlanCurCfgVlanId 		Integer32,
    pvlanCurCfgPvlanId 		Integer32,
    pvlanCurCfgPvlanFrameType	INTEGER,
    pvlanCurCfgPvlanEtherType	DisplayString,
    pvlanCurCfgPvlanPorts	OCTET STRING,
    pvlanCurCfgPvlanPrio        INTEGER,
    pvlanCurCfgPvlanState	INTEGER,
    pvlanCurCfgPvlanTagPorts	OCTET STRING,
    pvlanCurCfgPvlanPredefProto INTEGER
    } 

pvlanCurCfgVlanId OBJECT-TYPE
    SYNTAX  Integer32
    MAX-ACCESS  read-only
    STATUS  current
    DESCRIPTION
        "The VLAN identifier."
    ::= { pvlanCurCfgTableEntry 1 }

pvlanCurCfgPvlanId OBJECT-TYPE
    SYNTAX  Integer32
    MAX-ACCESS  read-only
    STATUS  current
    DESCRIPTION
        "The PVLAN identifier."
    ::= { pvlanCurCfgTableEntry 2 }

pvlanCurCfgPvlanFrameType OBJECT-TYPE
    SYNTAX  INTEGER{
        none(0),
        ethernet2(1),
        snap(2),
        llc(3)
        }
    MAX-ACCESS  read-only
    STATUS  current
    DESCRIPTION
        "The frame type of the PVLAN."
    ::= { pvlanCurCfgTableEntry 3 }

pvlanCurCfgPvlanEtherType OBJECT-TYPE
    SYNTAX  DisplayString
    MAX-ACCESS  read-only
    STATUS  current
    DESCRIPTION
        "The Ether type of the PVLAN."
    ::= { pvlanCurCfgTableEntry 4 }

pvlanCurCfgPvlanPorts OBJECT-TYPE
    SYNTAX  OCTET STRING
    MAX-ACCESS  read-only
    STATUS  current
    DESCRIPTION
        "The port list in the PVLAN. The ports are presented in bitmap format."
    ::= { pvlanCurCfgTableEntry 5 }

pvlanCurCfgPvlanPrio OBJECT-TYPE
    SYNTAX  INTEGER
    MAX-ACCESS  read-only
    STATUS  current
    DESCRIPTION
        "The priority of the PVLAN."
    ::= { pvlanCurCfgTableEntry 6 }

pvlanCurCfgPvlanState OBJECT-TYPE
    SYNTAX  INTEGER {
        enabled(1),
        disabled(0)
    }
    MAX-ACCESS  read-only
    STATUS  current
    DESCRIPTION
        "Enable or disable a PVLAN."
    ::= { pvlanCurCfgTableEntry 7 }

pvlanCurCfgPvlanTagPorts OBJECT-TYPE
    SYNTAX  OCTET STRING
    MAX-ACCESS  read-only
    STATUS  current
    DESCRIPTION
        "The list of tagged-PVLAN ports. The ports are presented in bitmap format."
    ::= { pvlanCurCfgTableEntry 8 }

pvlanCurCfgPvlanPredefProto OBJECT-TYPE
    SYNTAX  INTEGER {
        userDefined(0),
        decEther2(1),
        ipv4Ether2(2),
        ipv6Ether2(3),
        ipx802dot2(4),
        ipx802dot3(5),
        ipxEther2(6),
        ipxSnap(7),
        netbios(8),
        rarpEther2(9),
        sna802dot2(10),
        snaEther2(11),
        vinesEther2(12),
        xnsEther2(13)
    }
    MAX-ACCESS  read-only
    STATUS  current
    DESCRIPTION
        "A predefined Protocol (setting EtherType and FrameType to
         predefined values)."
    ::= { pvlanCurCfgTableEntry 9 }

pvlanNewCfgTable OBJECT-TYPE
    SYNTAX  SEQUENCE OF PvlanNewCfgTableEntry
    MAX-ACCESS  not-accessible
    STATUS  current
    DESCRIPTION
        "The table of PROTOCOL VLAN configuration."
    ::= { vlan 6 }

pvlanNewCfgTableEntry OBJECT-TYPE
    SYNTAX  PvlanNewCfgTableEntry
    MAX-ACCESS  not-accessible
    STATUS  current
    DESCRIPTION
        "A row in the Protocol VLAN configuration table."
    INDEX  { pvlanNewCfgVlanId, pvlanNewCfgPvlanId }
    ::= { pvlanNewCfgTable 1 }

PvlanNewCfgTableEntry ::= SEQUENCE {
    pvlanNewCfgVlanId 		Integer32,
    pvlanNewCfgPvlanId 		Integer32,
    pvlanNewCfgPvlanFrameType	INTEGER,
    pvlanNewCfgPvlanEtherType	DisplayString, 
    pvlanNewCfgPvlanAddPort	PortNumber,
    pvlanNewCfgPvlanRemovePort	PortNumber,
    pvlanNewCfgPvlanPrio        INTEGER,
    pvlanNewCfgPvlanState	INTEGER,
    pvlanNewCfgPvlanTagPort	PortNumber,
    pvlanNewCfgPvlanUntagPort	PortNumber,
    pvlanNewCfgPvlanPorts       OCTET STRING,
    pvlanNewCfgPvlanTagPorts    OCTET STRING,
    pvlanNewCfgPvlanDelete	INTEGER,
    pvlanNewCfgPvlanPredefProto INTEGER
    } 

pvlanNewCfgVlanId OBJECT-TYPE
    SYNTAX  Integer32
    MAX-ACCESS  read-only
    STATUS  current
    DESCRIPTION
        "The VLAN identifier."
    ::= { pvlanNewCfgTableEntry 1 }

pvlanNewCfgPvlanId OBJECT-TYPE
    SYNTAX  Integer32
    MAX-ACCESS  read-write
    STATUS  current
    DESCRIPTION
        "The PVLAN identifier."
    ::= { pvlanNewCfgTableEntry 2 }

pvlanNewCfgPvlanFrameType OBJECT-TYPE
    SYNTAX  INTEGER{
        none(0),
        ethernet2(1),
        snap(2),
        llc(3)
        }
    MAX-ACCESS  read-write
    STATUS  current
    DESCRIPTION
        "The frame type of the PVLAN."
    ::= { pvlanNewCfgTableEntry 3 }

pvlanNewCfgPvlanEtherType OBJECT-TYPE
    SYNTAX  DisplayString
    MAX-ACCESS  read-write
    STATUS  current
    DESCRIPTION
        "The Ehter type of the PVLAN."
    ::= { pvlanNewCfgTableEntry 4 }

pvlanNewCfgPvlanAddPort OBJECT-TYPE
    SYNTAX  PortNumber
    MAX-ACCESS  read-write
    STATUS  current
    DESCRIPTION
        "The port to be added to the specified PVLAN.  A '0' value is 
         returned when read."
    ::= { pvlanNewCfgTableEntry 5 }

pvlanNewCfgPvlanRemovePort OBJECT-TYPE
    SYNTAX  PortNumber
    MAX-ACCESS  read-write
    STATUS  current
    DESCRIPTION
        "The port to be removed to the specified PVLAN.  A '0' value is 
         returned when read."
    ::= { pvlanNewCfgTableEntry 6 }

pvlanNewCfgPvlanPrio OBJECT-TYPE
    SYNTAX  INTEGER
    MAX-ACCESS  read-write
    STATUS  current
    DESCRIPTION
        "The priority of the PVLAN."
    ::= { pvlanNewCfgTableEntry 7 }

pvlanNewCfgPvlanState OBJECT-TYPE
    SYNTAX  INTEGER {
        enabled(1),
        disabled(0)
    }
    MAX-ACCESS  read-write
    STATUS  current
    DESCRIPTION
        "Enable or disable a PVLAN"
    ::= { pvlanNewCfgTableEntry 8 }

pvlanNewCfgPvlanTagPort OBJECT-TYPE
    SYNTAX  PortNumber
    MAX-ACCESS  read-write
    STATUS  current
    DESCRIPTION
        "The port to be tagged for the specified PVLAN.  A '0' value is 
         returned when read."
    ::= { pvlanNewCfgTableEntry 9 }

pvlanNewCfgPvlanUntagPort OBJECT-TYPE
    SYNTAX  PortNumber
    MAX-ACCESS  read-write
    STATUS  current
    DESCRIPTION
        "The port to be untagged for the specified PVLAN.  A '0' value is 
         returned when read."
    ::= { pvlanNewCfgTableEntry 10 }

pvlanNewCfgPvlanPorts OBJECT-TYPE
    SYNTAX  OCTET STRING
    MAX-ACCESS  read-only
    STATUS  current
    DESCRIPTION
        "The port list in the PVLAN. The ports are presented in bitmap format."
    ::= { pvlanNewCfgTableEntry 11 }

pvlanNewCfgPvlanTagPorts OBJECT-TYPE
    SYNTAX  OCTET STRING
    MAX-ACCESS  read-only
    STATUS  current
    DESCRIPTION
        "The list of tagged-PVLAN ports. The ports are presented in bitmap format."
    ::= { pvlanNewCfgTableEntry 12 }

pvlanNewCfgPvlanDelete OBJECT-TYPE
    SYNTAX  INTEGER {
        delete(2),
        no(0)
    }
    MAX-ACCESS  read-write
    STATUS  current
    DESCRIPTION
        "Delete a PVLAN"
    ::= { pvlanNewCfgTableEntry 13 }

pvlanNewCfgPvlanPredefProto OBJECT-TYPE
    SYNTAX  INTEGER {
        userDefined(0),
        decEther2(1),     
        ipv4Ether2(2),
        ipv6Ether2(3),
        ipx802dot2(4),
        ipx802dot3(5),
        ipxEther2(6),
        ipxSnap(7),
        netbios(8),
        rarpEther2(9),
        sna802dot2(10),
        snaEther2(11),
        vinesEther2(12),
        xnsEther2(13)
    }
    MAX-ACCESS  read-write
    STATUS  current
    DESCRIPTION
        "A predefined Protocol (setting EtherType and FrameType to
         predefined values)."
    ::= { pvlanNewCfgTableEntry 14 }

 

-- Link Aggregation Control Protocol Group
lacpCurSystemPriority OBJECT-TYPE
    SYNTAX  INTEGER (1..65535)
    MAX-ACCESS  read-only
    STATUS  current
    DESCRIPTION
       "A 2-octet read-write value indicating the priority
        value associated with the Actor's System ID."
    ::= { lacp 1 }

lacpNewSystemPriority OBJECT-TYPE
    SYNTAX  INTEGER (1..65535)
    MAX-ACCESS  read-write
    STATUS  current
    DESCRIPTION
       "A 2-octet read-write value indicating the priority
        value associated with the Actor's System ID."
    ::= { lacp 2 }

lacpCurSystemTimeoutTime OBJECT-TYPE
    SYNTAX  INTEGER  {
        short(3),
        long(90)
        }
    MAX-ACCESS  read-only
    STATUS  current
    DESCRIPTION
        "If a port does not receive LACPDUs for Timeout time LACP 
         information pertaining to the port is invalidated.
         Its every 3 sec (short) and every 90 sec (long 3)."
    ::= { lacp 5 }

lacpNewSystemTimeoutTime OBJECT-TYPE
    SYNTAX  INTEGER  {
        short(3),
        long(90)
        }
    MAX-ACCESS  read-write
    STATUS  current
    DESCRIPTION
        "If a port does not receive LACPDUs for Timeout time LACP 
         information pertaining to the port is invalidated.
         Its every 3 sec (short) and every 90 sec (long 3)."
    ::= { lacp 6 }

lacpCurPortCfgTable OBJECT-TYPE
    SYNTAX  SEQUENCE OF LacpCurPortCfgTableEntry
    MAX-ACCESS  not-accessible
    STATUS  current
    DESCRIPTION
        "The table of LACP port configuration."
    ::= { lacp 7 }

lacpCurPortCfgTableEntry OBJECT-TYPE
    SYNTAX  LacpCurPortCfgTableEntry
    MAX-ACCESS  not-accessible
    STATUS  current
    DESCRIPTION
        "A row in the LACP port configuration table."
    INDEX  { lacpCurPortCfgTableId }
    ::= { lacpCurPortCfgTable 1 }

LacpCurPortCfgTableEntry ::= SEQUENCE {
    lacpCurPortCfgTableId 	    PortNumber,
    lacpCurPortState                INTEGER, 
    lacpCurPortActorPortPriority    INTEGER, 
    lacpCurPortActorAdminKey        INTEGER
    , lacpCurPortActorMinLinks      INTEGER
    , lacpCurPortSuspendIndividual  INTEGER
    }

lacpCurPortCfgTableId OBJECT-TYPE
    SYNTAX PortNumber
    MAX-ACCESS  read-only
    STATUS  current
    DESCRIPTION
          " LACP port number."
    ::= { lacpCurPortCfgTableEntry 1 }

lacpCurPortState OBJECT-TYPE
    SYNTAX  INTEGER  {
        off(1),
        active(2),
        passive(3)
        }
    MAX-ACCESS  read-only
    STATUS  current
    DESCRIPTION
        "LACP port state can be one of three states 
         off (Not participating in LACP) 
         Active (Initiates LACPDU updates)
         Passive (Does not initiate LACPDU updates but responds to peer."
    ::= { lacpCurPortCfgTableEntry 2 }

lacpCurPortActorPortPriority OBJECT-TYPE
    SYNTAX       INTEGER (1..65535)
    MAX-ACCESS       read-only
    STATUS       current
    DESCRIPTION
        "The priority value assigned to this Aggregation Port.
        This 16-bit value is read-only."
    ::= { lacpCurPortCfgTableEntry 3 }

lacpCurPortActorAdminKey OBJECT-TYPE
    SYNTAX       INTEGER (1..65535)
    MAX-ACCESS       read-only
    STATUS       current
    DESCRIPTION
        "The current administrative value of the Key for the
        Aggregation Port. This is a 16-bit read-only value.
        The meaning of particular Key values is of local
        significance."
    ::= { lacpCurPortCfgTableEntry 4 }

lacpCurPortActorMinLinks OBJECT-TYPE
    SYNTAX       INTEGER (1..16)
    MAX-ACCESS       read-only
    STATUS       current
    DESCRIPTION
    "The current minimum links for the Aggregation Port. 
    This is a 16-bit read-only value. The meaning of 
    particular Key values is of local significance."
    ::= { lacpCurPortCfgTableEntry 5 }

lacpCurPortSuspendIndividual OBJECT-TYPE
SYNTAX  INTEGER  {
        suspend(1),
        individual(2)
        }
    MAX-ACCESS   read-only
    STATUS       current
    DESCRIPTION
    "It indicates if the port can be treated as an individual
     link when it does not get LACPDU from the peer port.
     suspend (can't be treated as a normal link)
     individual (can be treated as a normal link)"
    ::= { lacpCurPortCfgTableEntry 6 }

lacpNewPortCfgTable OBJECT-TYPE
    SYNTAX  SEQUENCE OF LacpNewPortCfgTableEntry
    MAX-ACCESS  not-accessible
    STATUS  current
    DESCRIPTION
        "The table of LACP port configuration."
    ::= { lacp 8 }

lacpNewPortCfgTableEntry OBJECT-TYPE
    SYNTAX  LacpNewPortCfgTableEntry
    MAX-ACCESS  not-accessible
    STATUS  current
    DESCRIPTION
        "A row in the LACP port configuration table."
    INDEX  { lacpNewPortCfgTableId }
    ::= { lacpNewPortCfgTable 1 }

LacpNewPortCfgTableEntry ::= SEQUENCE {
    lacpNewPortCfgTableId 	    PortNumber,
    lacpNewPortState                INTEGER, 
    lacpNewPortActorPortPriority    INTEGER, 
    lacpNewPortActorAdminKey        INTEGER,
    lacpNewPortActorMinLinks        INTEGER,
    lacpNewPortSetToDefault         INTEGER
    , lacpNewPortSuspendIndividual  INTEGER
    }

lacpNewPortCfgTableId OBJECT-TYPE
    SYNTAX PortNumber
    MAX-ACCESS  read-only
    STATUS  current
    DESCRIPTION
          " LACP port number."
    ::= { lacpNewPortCfgTableEntry 1 }

lacpNewPortState OBJECT-TYPE
    SYNTAX  INTEGER  {
        off(1),
        active(2),
        passive(3)
        }
    MAX-ACCESS  read-write
    STATUS  current
    DESCRIPTION
        "LACP port state can be one of three states 
         off (Not participating in LACP) 
         Active (Initiates LACPDU updates)
         Passive (Does not initiate LACPDU updates but responds to peer."
    ::= { lacpNewPortCfgTableEntry 2 }

lacpNewPortActorPortPriority OBJECT-TYPE
    SYNTAX       INTEGER (1..65535)
    MAX-ACCESS       read-write
    STATUS       current
    DESCRIPTION
        "The priority value assigned to this Aggregation Port.
        This 16-bit value is read-write."
    ::= { lacpNewPortCfgTableEntry 3 }

lacpNewPortActorAdminKey OBJECT-TYPE
    SYNTAX       INTEGER (1..65535)
    MAX-ACCESS       read-write
    STATUS       current
    DESCRIPTION
        "The current administrative value of the Key for the
        Aggregation Port. This is a 16-bit read-write value.
        The meaning of particular Key values is of local
        significance."
    ::= { lacpNewPortCfgTableEntry 4 }

lacpNewPortActorMinLinks OBJECT-TYPE
    SYNTAX       INTEGER (1..16)
    MAX-ACCESS       read-write
    STATUS       current
    DESCRIPTION
        "The current minimum links for the Aggregation Port. 
        This is a 16-bit read-write value. The meaning of 
        particular Key values is of local significance."
    ::= { lacpNewPortCfgTableEntry 5 }

lacpNewPortSetToDefault OBJECT-TYPE
    SYNTAX  INTEGER  {
        none(1),
        setDefault(2)
        }
    MAX-ACCESS  read-write
    STATUS  current
    DESCRIPTION
        "When read, always returns none(1). 
         When setting setDefault(2) value, the LACP port settings 
         are set to the default values."
    ::= { lacpNewPortCfgTableEntry 6 }

lacpNewPortSuspendIndividual OBJECT-TYPE
SYNTAX  INTEGER  {
        suspend(1),
        individual(2)
        }
MAX-ACCESS   read-write
    STATUS       current
    DESCRIPTION
        "It indicates if the port can be treated as an individual
	link when it does not get LACPDU from the peer port.
	suspend (can't be treated as a normal link)
	individual (can be treated as a normal link)"
    ::= { lacpNewPortCfgTableEntry 7 }

lacpDeleteTrunk OBJECT-TYPE
    SYNTAX       INTEGER (1..65535)
    MAX-ACCESS   read-write
    STATUS       current
    DESCRIPTION
        "Delete a trunk with specified admin key"
    ::= { lacp 9 }    

lacpNewSystemSetToDefault OBJECT-TYPE
    SYNTAX  INTEGER  {
        none(1),
        setDefault(2)
        }
    MAX-ACCESS  read-write
    STATUS  current
    DESCRIPTION
        "When read, always returns none(1).
         When setting setDefault(2) value, the LACP system settings
         are set to the default values."
    ::= { lacp 10 }
    

-- Trunk Group Group
trunkGroupTableMaxSize OBJECT-TYPE
    SYNTAX  Integer32
    MAX-ACCESS  read-only
    STATUS  current
    DESCRIPTION
        "The maximum number of entries in trunk group table."
    ::= { trunkgroup 1 }

trunkGroupCurCfgTable OBJECT-TYPE
    SYNTAX  SEQUENCE OF TrunkGroupCurCfgTableEntry
    MAX-ACCESS  not-accessible
    STATUS  current
    DESCRIPTION
        "The table of trunk group configuration."
    ::= { trunkgroup 2 }

trunkGroupCurCfgTableEntry OBJECT-TYPE
    SYNTAX  TrunkGroupCurCfgTableEntry
    MAX-ACCESS  not-accessible
    STATUS  current
    DESCRIPTION
        "A row in the trunk group configuration table."
    INDEX   { trunkGroupCurCfgIndex }
    ::= { trunkGroupCurCfgTable 1 }

TrunkGroupCurCfgTableEntry ::= SEQUENCE {
    trunkGroupCurCfgIndex         Integer32,
    trunkGroupCurCfgPorts         OCTET STRING,
    trunkGroupCurCfgState         INTEGER
    }
 
trunkGroupCurCfgIndex OBJECT-TYPE
    SYNTAX  Integer32  
    MAX-ACCESS  read-only
    STATUS  current
    DESCRIPTION
        "The identifier of the trunk group."
    ::= { trunkGroupCurCfgTableEntry 1 }
 
trunkGroupCurCfgPorts OBJECT-TYPE
    SYNTAX  OCTET STRING
    MAX-ACCESS  read-only
    STATUS  current
    DESCRIPTION
        "The port list in the trunk group. The ports are presented in 
         bitmap format.
 
         in receiving order:
 
             OCTET 1  OCTET 2  .....
             xxxxxxxx xxxxxxxx ..... 
             ||    || |_ port 8
             ||    ||  
             ||    ||___ port 7
             ||    |____ port 6
             ||      .    .   .
             ||_________ port 1
             |__________ reserved

         where x : 1 - The represented port belongs to the trunk group
                   0 - The represented port does not belong to the trunk group"
    ::= { trunkGroupCurCfgTableEntry 2 }
 
trunkGroupCurCfgState OBJECT-TYPE
    SYNTAX  INTEGER  {
        enable(1),
        disable(2)
        }
    MAX-ACCESS  read-only
    STATUS  current
    DESCRIPTION
        "Enable or disable a trunk group."
    ::= { trunkGroupCurCfgTableEntry 3 }
 
 




trunkGroupNewCfgTable OBJECT-TYPE
    SYNTAX  SEQUENCE OF TrunkGroupNewCfgTableEntry
    MAX-ACCESS  not-accessible
    STATUS  current
    DESCRIPTION
        "The table of trunk group configuration."
    ::= { trunkgroup 3 }

trunkGroupNewCfgTableEntry OBJECT-TYPE
    SYNTAX  TrunkGroupNewCfgTableEntry
    MAX-ACCESS  not-accessible
    STATUS  current
    DESCRIPTION
        "A row in the trunk group configuration table."
    INDEX   { trunkGroupNewCfgIndex }
    ::= { trunkGroupNewCfgTable 1 }

TrunkGroupNewCfgTableEntry ::= SEQUENCE {
    trunkGroupNewCfgIndex          Integer32,
    trunkGroupNewCfgPorts          OCTET STRING,
    trunkGroupNewCfgAddPort        PortNumber,
    trunkGroupNewCfgRemovePort     PortNumber,
    trunkGroupNewCfgState          INTEGER,
    trunkGroupNewCfgDelete         INTEGER
    }
 
trunkGroupNewCfgIndex OBJECT-TYPE
    SYNTAX  Integer32  
    MAX-ACCESS  read-only
    STATUS  current
    DESCRIPTION
        "The identifier of the trunk group."
    ::= { trunkGroupNewCfgTableEntry 1 }
 
trunkGroupNewCfgPorts OBJECT-TYPE
    SYNTAX  OCTET STRING
    MAX-ACCESS  read-only
    STATUS  current
    DESCRIPTION
        "The port list in the trunk group.  The ports are presented
         in bitmap format.

         in receiving order:

             OCTET 1  OCTET 2  .....
             xxxxxxxx xxxxxxxx ..... 
             ||    || |_ port 8
             ||    ||  
             ||    ||___ port 7
             ||    |____ port 6
             ||      .    .   .
             ||_________ port 1
             |__________ reserved
 
         where x : 1 - The represented port belongs to the trunk group
                   0 - The represented port does not belong to the trunk group"
    ::= { trunkGroupNewCfgTableEntry 2 }
 
trunkGroupNewCfgAddPort OBJECT-TYPE
    SYNTAX  PortNumber
    MAX-ACCESS  read-create
    STATUS  current
    DESCRIPTION
        "The port to be added in the trunk group. When read, 0 is returned."
    ::= { trunkGroupNewCfgTableEntry 3 }

trunkGroupNewCfgRemovePort OBJECT-TYPE
    SYNTAX  PortNumber
    MAX-ACCESS  read-create
    STATUS  current
    DESCRIPTION
        "The port to be deleted from the trunk group. when read, 0
	 is returned."
    ::= { trunkGroupNewCfgTableEntry 4 }

trunkGroupNewCfgState OBJECT-TYPE
    SYNTAX  INTEGER  {
        enable(1),
        disable(2)
        }
    MAX-ACCESS  read-create
    STATUS  current
    DESCRIPTION
        "Enable or disable a trunk group."
    ::= { trunkGroupNewCfgTableEntry 5 }
 
trunkGroupNewCfgDelete OBJECT-TYPE
    SYNTAX  INTEGER  {
        other(1),
        delete(2)
        }
    MAX-ACCESS  read-create
    STATUS  current
    DESCRIPTION
        "Setting the value to delete(2) will delete the entire
         row. When read, other(1) is returned."
    ::= { trunkGroupNewCfgTableEntry 6 }





l2ThashCurCfgSmacState OBJECT-TYPE
    SYNTAX  INTEGER  {
        enable(1),
        disable(2)
        }
    MAX-ACCESS  read-only
    STATUS  current
    DESCRIPTION
        "Enable or disable smac hash for traffic."
    ::= { thashL2L3 1 }

l2ThashNewCfgSmacState OBJECT-TYPE
    SYNTAX  INTEGER  {
        enable(1),
        disable(2)
        }
    MAX-ACCESS  read-write
    STATUS  current
    DESCRIPTION
        "Enable or disable smac hash for traffic."
    ::= { thashL2L3 2 }

l2ThashCurCfgDmacState OBJECT-TYPE
    SYNTAX  INTEGER  {
        enable(1),
        disable(2)
        }
    MAX-ACCESS  read-only
    STATUS  current
    DESCRIPTION
        "Enable or disable dmac hash for traffic."
    ::= { thashL2L3 3 }

l2ThashNewCfgDmacState OBJECT-TYPE
    SYNTAX  INTEGER  {
        enable(1),
        disable(2)
        }
    MAX-ACCESS  read-write
    STATUS  current
    DESCRIPTION
        "Enable or disable dmac hash for traffic."
    ::= { thashL2L3 4 }

l3ThashCurCfgIpUseL2State OBJECT-TYPE
    SYNTAX  INTEGER  {
        enable(1),
        disable(2)
        }
    MAX-ACCESS  read-only
    STATUS  current
    DESCRIPTION
        "Enable or disable L2 hash for IP traffic."
    ::= { thashL2L3 5 }

l3ThashNewCfgIpUseL2State OBJECT-TYPE
    SYNTAX  INTEGER  {
        enable(1),
        disable(2)
        }
    MAX-ACCESS  read-write
    STATUS  current
    DESCRIPTION
        "Enable or disable L2 hash for IP traffic."
    ::= { thashL2L3 6 }

l3ThashCurCfgSipState OBJECT-TYPE
    SYNTAX  INTEGER  {
        enable(1),
        disable(2)
        }
    MAX-ACCESS  read-only
    STATUS  current
    DESCRIPTION
        "Enable or disable sip hash for IP traffic."
    ::= { thashL2L3 7 }

l3ThashNewCfgSipState OBJECT-TYPE
    SYNTAX  INTEGER  {
        enable(1),
        disable(2)
        }
    MAX-ACCESS  read-write
    STATUS  current
    DESCRIPTION
        "Enable or disable sip hash for IP traffic."
    ::= { thashL2L3 8 }

l3ThashCurCfgDipState OBJECT-TYPE
    SYNTAX  INTEGER  {
        enable(1),
        disable(2)
        }
    MAX-ACCESS  read-only
    STATUS  current
    DESCRIPTION
        "Enable or disable dip hash for IP traffic."
    ::= { thashL2L3 9 }

l3ThashNewCfgDipState OBJECT-TYPE
    SYNTAX  INTEGER  {
        enable(1),
        disable(2)
        }
    MAX-ACCESS  read-write
    STATUS  current
    DESCRIPTION
        "Enable or disable dip hash for IP traffic."
    ::= { thashL2L3 10 }

l2ThashCurCfgIngressState OBJECT-TYPE
    SYNTAX  INTEGER  {
        enable(1),
        disable(2)
        }
    MAX-ACCESS  read-only
    STATUS  current
    DESCRIPTION
        "Enable or disable ingres port hash."
    ::= { thashL2L3 11 }

l2ThashNewCfgIngressState OBJECT-TYPE
    SYNTAX  INTEGER  {
        enable(1),
        disable(2)
        }
    MAX-ACCESS  read-write
    STATUS  current
    DESCRIPTION
        "Enable or disable ingres port hash."
    ::= { thashL2L3 12 }

l3ThashCurCfgL4PortState OBJECT-TYPE
    SYNTAX  INTEGER  {
        enable(1),
        disable(2)
        }
    MAX-ACCESS  read-only
    STATUS  current
    DESCRIPTION
        "Enable or disable L4 port hash."
    ::= { thashL2L3 13 }

l3ThashNewCfgL4PortState OBJECT-TYPE
    SYNTAX  INTEGER  {
        enable(1),
        disable(2)
        }
    MAX-ACCESS  read-write
    STATUS  current
    DESCRIPTION
        "Enable or disable L4 port hash."
    ::= { thashL2L3 14 }
fcoeThashCurCfgSourceState OBJECT-TYPE
    SYNTAX  INTEGER  {
        enable(1),
        disable(2)
        }
    MAX-ACCESS  read-only
    STATUS  current
    DESCRIPTION
        "Enable or disable fcoe source-id hash."
    ::= { thashFcoe 1 }

fcoeThashNewCfgSourceState OBJECT-TYPE
    SYNTAX  INTEGER  {
        enable(1),
        disable(2)
        }
    MAX-ACCESS  read-write
    STATUS  current
    DESCRIPTION
        "Enable or disable fcoe source-id hash."
    ::= { thashFcoe 2 }

fcoeThashCurCfgDestinationState OBJECT-TYPE
    SYNTAX  INTEGER  {
        enable(1),
        disable(2)
        }
    MAX-ACCESS  read-only
    STATUS  current
    DESCRIPTION
        "Enable or disable fcoe destination-id hash."
    ::= { thashFcoe 3 }

fcoeThashNewCfgDestinationState OBJECT-TYPE
    SYNTAX  INTEGER  {
        enable(1),
        disable(2)
        }
    MAX-ACCESS  read-write
    STATUS  current
    DESCRIPTION
        "Enable or disable fcoe destination-id hash."
    ::= { thashFcoe 4 }


fcoeThashCurCfgCntagState OBJECT-TYPE
    SYNTAX  INTEGER  {
        enable(1),
        disable(2)
        }
    MAX-ACCESS  read-only
    STATUS  current
    DESCRIPTION
        "Enable or disable fcoe cntag-id hash."
    ::= { thashFcoe 5 }

fcoeThashNewCfgCntagState OBJECT-TYPE
    SYNTAX  INTEGER  {
        enable(1),
        disable(2)
        }
    MAX-ACCESS  read-write
    STATUS  current
    DESCRIPTION
        "Enable or disable fcoe cntag-id hash."
    ::= { thashFcoe 6 }

fcoeThashCurCfgOriginatorState OBJECT-TYPE
    SYNTAX  INTEGER  {
        enable(1),
        disable(2)
        }
    MAX-ACCESS  read-only
    STATUS  current
    DESCRIPTION
        "Enable or disable fcoe originator-id hash."
    ::= { thashFcoe 7 }

fcoeThashNewCfgOriginatorState OBJECT-TYPE
    SYNTAX  INTEGER  {
        enable(1),
        disable(2)
        }
    MAX-ACCESS  read-write
    STATUS  current
    DESCRIPTION
        "Enable or disable fcoe originator-id hash."
    ::= { thashFcoe 8 }


fcoeThashCurCfgResponderState OBJECT-TYPE
    SYNTAX  INTEGER  {
        enable(1),
        disable(2)
        }
    MAX-ACCESS  read-only
    STATUS  current
    DESCRIPTION
        "Enable or disable fcoe responder-id hash."
    ::= { thashFcoe 9 }

fcoeThashNewCfgResponderState OBJECT-TYPE
    SYNTAX  INTEGER  {
        enable(1),
        disable(2)
        }
    MAX-ACCESS  read-write
    STATUS  current
    DESCRIPTION
        "Enable or disable fcoe responder-id hash."
    ::= { thashFcoe 10 }

fcoeThashCurCfgFabricState OBJECT-TYPE
    SYNTAX  INTEGER  {
        enable(1),
        disable(2)
        }
    MAX-ACCESS  read-only
    STATUS  current
    DESCRIPTION
        "Enable or disable fcoe fabric-id hash."
    ::= { thashFcoe 11 }

fcoeThashNewCfgFabricState OBJECT-TYPE
    SYNTAX  INTEGER  {
        enable(1),
        disable(2)
        }
    MAX-ACCESS  read-write
    STATUS  current
    DESCRIPTION
        "Enable or disable fcoe fabric-id hash."
    ::= { thashFcoe 12}

-- Spanning Tree Group Configuration
-- This group specifies the additional configurations that are not
-- covered by the Bridge MIB (RFC 1493).
-- The relative Spanning Tree information can be retrieved or configured
-- using Bridge MIB with an unique community string for each group specified
-- in entLogicalTable of Entity MIB (RFC 2037).
--
stgCurCfgTable OBJECT-TYPE
    SYNTAX SEQUENCE OF StgCurCfgTableEntry
    MAX-ACCESS not-accessible
    STATUS current
    DESCRIPTION
        "The table of Spanning Tree Group configuration."
    ::= { stgCfg 1 }

stgCurCfgTableEntry OBJECT-TYPE
    SYNTAX StgCurCfgTableEntry
    MAX-ACCESS not-accessible
    STATUS current
    DESCRIPTION
        "Information about a particular Spanning Tree Group configuration."
    INDEX { stgCurCfgIndex }
    ::= { stgCurCfgTable 1 }

StgCurCfgTableEntry ::= SEQUENCE {
    stgCurCfgIndex           Integer32,
    stgCurCfgState           INTEGER,
    stgCurCfgPriority        INTEGER,
    stgCurCfgBrgHelloTime    INTEGER,
    stgCurCfgBrgForwardDelay INTEGER,
    stgCurCfgBrgMaxAge       INTEGER,
    stgCurCfgVlanBmap        OCTET STRING
    }

stgCurCfgIndex OBJECT-TYPE
    SYNTAX Integer32
    MAX-ACCESS read-only
    STATUS current
    DESCRIPTION
        "The identifier of a particular Spanning Tree Group.  This is also
         index to the entLogicalTable of Entity MIB."
    ::= { stgCurCfgTableEntry 1 }

stgCurCfgState OBJECT-TYPE
    SYNTAX INTEGER {
        on(1),
        off(2)
        }
    MAX-ACCESS read-only
    STATUS current
    DESCRIPTION
        "Turn on of off Spanning Tree operation of a particular Spanning
         Tree Group."
    ::= { stgCurCfgTableEntry 2 }


stgCurCfgPriority OBJECT-TYPE
    SYNTAX  INTEGER (0..65535)
    MAX-ACCESS  read-only
    STATUS  current
    DESCRIPTION
        "The value of the write-able portion of the Bridge ID, i.e., the first
         two octets of the (8 octet long) Bridge ID."
    ::= { stgCurCfgTableEntry 5 }

stgCurCfgBrgHelloTime OBJECT-TYPE
    SYNTAX  INTEGER (1..10)
    MAX-ACCESS  read-only
    STATUS  current
    DESCRIPTION
        "The value in seconds that all bridges use for HelloTime when this 
         bridge is acting as the root."
    ::= { stgCurCfgTableEntry 6 }

stgCurCfgBrgForwardDelay OBJECT-TYPE
    SYNTAX  INTEGER (4..30)
    MAX-ACCESS  read-only
    STATUS  current
    DESCRIPTION
        "The value in seconds that all bridges use for ForwardDelay when this 
         bridge is acting as the root."
    ::= { stgCurCfgTableEntry 7 }

stgCurCfgBrgMaxAge OBJECT-TYPE
    SYNTAX  INTEGER (6..40)
    MAX-ACCESS  read-only
    STATUS  current
    DESCRIPTION
        "The value in seconds that all bridges use for MaxAge when this bridge
         is acting as the root."
    ::= { stgCurCfgTableEntry 8 }

stgCurCfgVlanBmap OBJECT-TYPE
    SYNTAX  OCTET STRING (SIZE(0..512)) 
    MAX-ACCESS  read-only
    STATUS  current
    DESCRIPTION
	"The vlans applied to the spanning tree group.  The vlans are 
         presented in bitmap format. This string displays vlan number
	 from 1 to 4096.

	 in receiving order:

	     OCTET 1  OCTET 2  .....
             xxxxxxxx xxxxxxxx ..... 
             ||    || |_ vlan 9
             ||    ||  
             ||    ||___ vlan 8
             ||    |____ vlan 7
             ||      .    .   .
             ||_________ vlan 2
             |__________ vlan 1 (as index to stgCurCfgTable)

         where x : 1 - The represented vlan applied to the spanning tree. 
		   0 - The represented vlan not applied to the spanning tree"
    ::= { stgCurCfgTableEntry 10 }


stgNewCfgTable OBJECT-TYPE
    SYNTAX SEQUENCE OF StgNewCfgTableEntry
    MAX-ACCESS not-accessible
    STATUS current
    DESCRIPTION
        "The table of Spanning Tree Groups configuration in the new_config."
    ::= { stgCfg 2 }

stgNewCfgTableEntry OBJECT-TYPE
    SYNTAX StgNewCfgTableEntry
    MAX-ACCESS not-accessible
    STATUS current
    DESCRIPTION
        "Information about a particular Spanning Tree Group configuration."
    INDEX { stgNewCfgIndex }
    ::= { stgNewCfgTable 1 }

StgNewCfgTableEntry ::= SEQUENCE {
    stgNewCfgIndex           Integer32,
    stgNewCfgState           INTEGER,
    stgNewCfgDefaultCfg      INTEGER,
    stgNewCfgAddVlan         Integer32,
    stgNewCfgRemoveVlan      Integer32,
    stgNewCfgPriority        INTEGER,
    stgNewCfgBrgHelloTime    INTEGER,
    stgNewCfgBrgForwardDelay INTEGER,
    stgNewCfgBrgMaxAge       INTEGER,
    stgNewCfgVlanBmap        OCTET STRING,
    stgNewCfgRemoveAllVlan   INTEGER
    }

stgNewCfgIndex  OBJECT-TYPE
    SYNTAX Integer32
    MAX-ACCESS read-only
    STATUS current
    DESCRIPTION
        "The identifier of a particular Spanning Tree Group.  This is also
         index to the entLogicalTable of Entity MIB."
    ::= { stgNewCfgTableEntry 1 }

stgNewCfgState OBJECT-TYPE
    SYNTAX INTEGER {
        on(1),
        off(2)
        }
    MAX-ACCESS read-write
    STATUS current
    DESCRIPTION
        "Turn on of off Spanning Tree operation of a particular Spanning
         Tree Group."
    ::= { stgNewCfgTableEntry 2 }

stgNewCfgDefaultCfg OBJECT-TYPE
    SYNTAX INTEGER {
        default-config(1)
        }
    MAX-ACCESS read-write
    STATUS current
    DESCRIPTION
        "Setting the value to default-config(1) will set the default
         configuration as recommended by IEEE 802.1D for a particular
         Spanning Tree Group.  default-config (1) is always returned 
	 When read, but it does not mean anything."
    ::= { stgNewCfgTableEntry 3 }

stgNewCfgAddVlan OBJECT-TYPE
    SYNTAX  Integer32
    MAX-ACCESS  read-write
    STATUS  current
    DESCRIPTION
        "The vlan to be added to the specified Spanning Tree Group.  A 
         '0' value is returned when read." 
    ::= {stgNewCfgTableEntry 4 }

stgNewCfgRemoveVlan OBJECT-TYPE
    SYNTAX  Integer32
    MAX-ACCESS  read-write
    STATUS  current
    DESCRIPTION
        "The vlan to be removed from the specified Spanning Tree Group.
         A '0' value is returned when read."
    ::= { stgNewCfgTableEntry 5 }


stgNewCfgPriority OBJECT-TYPE
    SYNTAX  INTEGER (0..65535)
    MAX-ACCESS  read-write
    STATUS  current
    DESCRIPTION
        "The value of the write-able portion of the Bridge ID, i.e., the first
         two octets of the (8 octet long) Bridge ID."
    ::= { stgNewCfgTableEntry 8 }

stgNewCfgBrgHelloTime OBJECT-TYPE
    SYNTAX  INTEGER (1..10)
    MAX-ACCESS  read-write
    STATUS  current
    DESCRIPTION
        "The value in seconds that all bridges use for HelloTime when this 
         bridge is acting as the root."
    ::= { stgNewCfgTableEntry 9 }

stgNewCfgBrgForwardDelay OBJECT-TYPE
    SYNTAX  INTEGER (4..30)
    MAX-ACCESS  read-write
    STATUS  current
    DESCRIPTION
        "The value in seconds that all bridges use for ForwardDelay when this 
         bridge is acting as the root."
    ::= { stgNewCfgTableEntry 10 }

stgNewCfgBrgMaxAge OBJECT-TYPE
    SYNTAX  INTEGER (6..40)
    MAX-ACCESS  read-write
    STATUS  current
    DESCRIPTION
        "The value in seconds that all bridges use for MaxAge when this bridge
         is acting as the root."
    ::= { stgNewCfgTableEntry 11 }

stgNewCfgVlanBmap OBJECT-TYPE
    SYNTAX  OCTET STRING (SIZE(0..512)) 
    MAX-ACCESS  read-only
    STATUS  current
    DESCRIPTION
	"The vlans applied to the spanning tree group.  The vlans are 
         presented in bitmap format. This string displays vlan number
	 from 1 to 4096.

	 in receiving order:

	     OCTET 1  OCTET 2  .....
             xxxxxxxx xxxxxxxx ..... 
             ||    || |_ vlan 9
             ||    ||  
             ||    ||___ vlan 8
             ||    |____ vlan 7
             ||      .    .   .
             ||_________ vlan 2
             |__________ vlan 1 (as index to stgCurCfgTable)

         where x : 1 - The represented vlan applied to the spanning tree. 
		   0 - The represented vlan not applied to the spanning tree"
    ::= { stgNewCfgTableEntry 13 }

stgNewCfgRemoveAllVlan OBJECT-TYPE
    SYNTAX INTEGER {
        default-config(1)
        }
    MAX-ACCESS read-write
    STATUS current
    DESCRIPTION
        "The all vlans to be removed from the specified Spanning Tree Group.
         A '0' value is returned when read."
    ::= { stgNewCfgTableEntry 14 }


stgCurCfgPortTable OBJECT-TYPE
    SYNTAX SEQUENCE OF StgCurCfgPortTableEntry
    MAX-ACCESS not-accessible
    STATUS current
    DESCRIPTION
        "The table of Spanning Tree Group port configuration in the
         current_config."
    ::= { stgCfg 3 }

stgCurCfgPortTableEntry OBJECT-TYPE
    SYNTAX StgCurCfgPortTableEntry
    MAX-ACCESS not-accessible
    STATUS current
    DESCRIPTION
        "Information about port configuration of a particular Spanning Tree
         Group."
    INDEX { stgCurCfgStgIndex, stgCurCfgPortIndex }
    ::= { stgCurCfgPortTable 1 }

StgCurCfgPortTableEntry ::= SEQUENCE {
    stgCurCfgStgIndex      Integer32,
    stgCurCfgPortIndex     PortNumber,
    stgCurCfgPortPriority  INTEGER,
    stgCurCfgPortPathCost  Integer32,
    stgCurCfgPortState     INTEGER
    }

stgCurCfgStgIndex OBJECT-TYPE
    SYNTAX Integer32
    MAX-ACCESS read-only
    STATUS current
    DESCRIPTION
        "The identifier of a particular Spanning Tree Group.  This is also
         index to the entLogicalTable of Entity MIB."
    ::= { stgCurCfgPortTableEntry 1 }

stgCurCfgPortIndex OBJECT-TYPE
    SYNTAX PortNumber
    MAX-ACCESS read-only
    STATUS current
    DESCRIPTION
        "The port identifier of a particular Spanning Tree Group."
    ::= { stgCurCfgPortTableEntry 2 }

stgCurCfgPortState OBJECT-TYPE
    SYNTAX INTEGER {
        on(1),
        off(2)
        }
    MAX-ACCESS read-only
    STATUS current
    DESCRIPTION
        "Turn on of off Spanning Tree operation of a particular port of a
         Spanning Tree Group."
    ::= { stgCurCfgPortTableEntry 3 }

stgCurCfgPortPriority OBJECT-TYPE
    SYNTAX INTEGER (0..240)
    MAX-ACCESS read-only
    STATUS current
    DESCRIPTION
        "The value of the priority field which is contained in the first 
         (in network byte order) octet of the (2 octet long) Port ID."
    ::= { stgCurCfgPortTableEntry 4 }

stgCurCfgPortPathCost OBJECT-TYPE
    SYNTAX Integer32 
    MAX-ACCESS read-only
    STATUS current
    DESCRIPTION
       "The contribution of this port to the path cost of paths towards the 
        spanning tree root which include this port (
        range is (0..200000000) )."
    ::= { stgCurCfgPortTableEntry 5 }



stgNewCfgPortTable OBJECT-TYPE
    SYNTAX SEQUENCE OF StgNewCfgPortTableEntry
    MAX-ACCESS not-accessible
    STATUS current
    DESCRIPTION
        "The table of Spanning Tree Group port configuration in the
         new_config."
    ::= { stgCfg 4 }

stgNewCfgPortTableEntry OBJECT-TYPE
    SYNTAX StgNewCfgPortTableEntry
    MAX-ACCESS not-accessible
    STATUS current
    DESCRIPTION
        "Information about port configuration of a particular Spanning Tree
         Group."
    INDEX { stgNewCfgStgIndex, stgNewCfgPortIndex }
    ::= { stgNewCfgPortTable 1 }

StgNewCfgPortTableEntry ::= SEQUENCE {
    stgNewCfgStgIndex      Integer32,
    stgNewCfgPortIndex     PortNumber,
    stgNewCfgPortPriority  INTEGER,
    stgNewCfgPortPathCost  Integer32,
    stgNewCfgPortState     INTEGER
    }

stgNewCfgStgIndex OBJECT-TYPE
    SYNTAX Integer32
    MAX-ACCESS read-only
    STATUS current
    DESCRIPTION
        "The identifier of a particular Spanning Tree Group.  This is also
         index to the entLogicalTable of Entity MIB."
    ::= { stgNewCfgPortTableEntry 1 }

stgNewCfgPortIndex OBJECT-TYPE
    SYNTAX PortNumber
    MAX-ACCESS read-only
    STATUS current
    DESCRIPTION
        "The port identifier of a particular Spanning Tree Group."
    ::= { stgNewCfgPortTableEntry 2 }

stgNewCfgPortState OBJECT-TYPE
    SYNTAX INTEGER {
        on(1),
        off(2)
        }
    MAX-ACCESS read-create
    STATUS current
    DESCRIPTION
        "Turn on of off Spanning Tree operation of a particular port of a
         Spanning Tree Group."
    ::= { stgNewCfgPortTableEntry 3 }

stgNewCfgPortPriority OBJECT-TYPE
    SYNTAX INTEGER (0..240)
    MAX-ACCESS read-create
    STATUS current
    DESCRIPTION
        "The value of the priority field which is contained in the first 
         (in network byte order) octet of the (2 octet long) Port ID."
    ::= { stgNewCfgPortTableEntry 4 }

stgNewCfgPortPathCost OBJECT-TYPE
    SYNTAX  Integer32 
    MAX-ACCESS read-create
    STATUS current
    DESCRIPTION
       "The contribution of this port to the path cost of paths towards the 
        spanning tree root which include this port (
        range is (0..200000000) )."
    ::= { stgNewCfgPortTableEntry 5 }



    

-- Complete Port Mirroring 
pmCurCfgPortMirrState OBJECT-TYPE
    SYNTAX  INTEGER {
	enabled(1),
	disabled(2)
	}
    MAX-ACCESS  read-only
    STATUS  current
    DESCRIPTION
        "The state of port-based port mirroring."
    ::= { mirrPortMirr 1 }
 
pmNewCfgPortMirrState OBJECT-TYPE
    SYNTAX  INTEGER {
	enabled(1),
	disabled(2)
        }
    MAX-ACCESS  read-write
    STATUS  current
    DESCRIPTION
        "The state of port-based port mirroring."
    ::= { mirrPortMirr 2 }

pmCurCfgPortMonitorTable OBJECT-TYPE
    SYNTAX  SEQUENCE OF PmCurCfgPortMonitorEntry
    MAX-ACCESS  not-accessible
    STATUS  current
    DESCRIPTION
        "The table of monitoring ports."
    ::= { mirrPortMirr 3 }

pmCurCfgPortMonitorEntry OBJECT-TYPE
    SYNTAX  PmCurCfgPortMonitorEntry
    MAX-ACCESS  not-accessible
    STATUS  current
    DESCRIPTION
        "A row in the monitoring port table."
    INDEX   { pmCurCfgPmirrMoniPortIndex, pmCurCfgPmirrMirrPortIndex }
    ::= { pmCurCfgPortMonitorTable 1 }

PmCurCfgPortMonitorEntry ::= SEQUENCE {
    pmCurCfgPmirrMoniPortIndex       PortNumber,
    pmCurCfgPmirrMirrPortIndex       PortNumber,
    pmCurCfgPmirrDirection           INTEGER
    }

pmCurCfgPmirrMoniPortIndex OBJECT-TYPE
    SYNTAX  PortNumber
    MAX-ACCESS  read-only
    STATUS  current
    DESCRIPTION
        "The monitoring port number." 
    ::= { pmCurCfgPortMonitorEntry 1 }

pmCurCfgPmirrMirrPortIndex OBJECT-TYPE 
    SYNTAX  PortNumber
    MAX-ACCESS  read-only 
    STATUS  current 
    DESCRIPTION 
        "The mirrored port number" 
    ::= { pmCurCfgPortMonitorEntry 2 }

pmCurCfgPmirrDirection OBJECT-TYPE
    SYNTAX  INTEGER {
	in(1),
	out(2),
	both(3)
        }
    MAX-ACCESS  read-only
    STATUS  current
    DESCRIPTION
        "The type of traffic to be monitored with respect to the
         mirrored port."
    ::= { pmCurCfgPortMonitorEntry 3 }

pmNewCfgPortMonitorTable OBJECT-TYPE
    SYNTAX  SEQUENCE OF PmNewCfgPortMonitorEntry
    MAX-ACCESS  not-accessible
    STATUS  current
    DESCRIPTION
        "The table of monitoring ports."
    ::= { mirrPortMirr 4 }

pmNewCfgPortMonitorEntry OBJECT-TYPE
    SYNTAX  PmNewCfgPortMonitorEntry
    MAX-ACCESS  not-accessible
    STATUS  current
    DESCRIPTION
        "A row in the monitoring port table."
    INDEX   { pmNewCfgPmirrMoniPortIndex, pmNewCfgPmirrMirrPortIndex }
    ::= { pmNewCfgPortMonitorTable 1 }

PmNewCfgPortMonitorEntry ::= SEQUENCE {
    pmNewCfgPmirrMoniPortIndex          PortNumber,
    pmNewCfgPmirrMirrPortIndex          PortNumber,
    pmNewCfgPmirrDirection              INTEGER,
    pmNewCfgPmirrDelete                 INTEGER,
    pmNewCfgPmonDelete                 INTEGER
    }

pmNewCfgPmirrMoniPortIndex OBJECT-TYPE
    SYNTAX  PortNumber
    MAX-ACCESS  read-only
    STATUS  current
    DESCRIPTION
        "The monitoring port number." 
    ::= { pmNewCfgPortMonitorEntry 1 }

pmNewCfgPmirrMirrPortIndex OBJECT-TYPE 
    SYNTAX  PortNumber 
    MAX-ACCESS  read-only 
    STATUS  current 
    DESCRIPTION 
        "The mirrored port number" 
    ::= { pmNewCfgPortMonitorEntry 2 }

pmNewCfgPmirrDirection OBJECT-TYPE
    SYNTAX  INTEGER {
	in(1),
	out(2),
	both(3)
        }
    MAX-ACCESS  read-create
    STATUS  current
    DESCRIPTION
        "The type of traffic to be monitored with respect to the
         mirrored port."
    ::= { pmNewCfgPortMonitorEntry 3 }

pmNewCfgPmirrDelete OBJECT-TYPE
    SYNTAX  INTEGER  {
        other(1),
        delete(2)
        }
    MAX-ACCESS  read-create
    STATUS  current
    DESCRIPTION
        "Setting the value to delete(2) will delete the entire
         row. When read, other(1) is returned."
    ::= { pmNewCfgPortMonitorEntry 4 }


pmNewCfgPmonDelete OBJECT-TYPE
    SYNTAX  INTEGER  {
        other(1),
        delete(2)
        }
    MAX-ACCESS  read-create
    STATUS  current
    DESCRIPTION
        "Setting the value to delete(2) will delete the monitor
         port. When read, other(1) is returned."
    ::= { pmNewCfgPortMonitorEntry 10 }

-- MST Configuration 


mstCurCfgRegionName OBJECT-TYPE
   SYNTAX  DisplayString (SIZE (0..32))
   MAX-ACCESS  read-only
   STATUS  current
   DESCRIPTION
      "The Name for the Region's configuration."
   ::= { mstGeneralCfg 3 } 

mstNewCfgRegionName OBJECT-TYPE
   SYNTAX  DisplayString (SIZE (0..32))
   MAX-ACCESS  read-write
   STATUS  current
   DESCRIPTION
      "The Name for the Region's configuration."
   ::= { mstGeneralCfg 4 } 

mstCurCfgRegionRevision OBJECT-TYPE
    SYNTAX  INTEGER  (0..65535)
    MAX-ACCESS  read-only
    STATUS  current
    DESCRIPTION
        "Revision of the MST Region."
    ::= { mstGeneralCfg 5 }

mstNewCfgRegionRevision OBJECT-TYPE
    SYNTAX  INTEGER  (0..65535)
    MAX-ACCESS  read-write
    STATUS  current
    DESCRIPTION
        "Revision of the MST Region."
    ::= { mstGeneralCfg 6 }

mstCurCfgMaxHopCount OBJECT-TYPE
    SYNTAX  INTEGER  (4..60)
    MAX-ACCESS  read-only
    STATUS  current
    DESCRIPTION
        "Indicates the maximum hop count value."
    ::= { mstGeneralCfg 7 }

mstNewCfgMaxHopCount OBJECT-TYPE
    SYNTAX  INTEGER  (4..60)
    MAX-ACCESS  read-write
    STATUS  current
    DESCRIPTION
        "Indicates the maximum hop count value."
    ::= { mstGeneralCfg 8 }

mstCurCfgStpMode OBJECT-TYPE
    SYNTAX  INTEGER  {
        mstp(1),
        rstp(2),
        pvrst(3)
    }
    MAX-ACCESS  read-only
    STATUS  current
    DESCRIPTION
        "The version of Spanning Tree Protocal the bridge is currently 
         running."
    ::= { mstGeneralCfg 9 }

mstNewCfgStpMode OBJECT-TYPE
    SYNTAX  INTEGER  {
        mstp(1),
        rstp(2),
        pvrst(3)
    }
    MAX-ACCESS  read-write
    STATUS  current
    DESCRIPTION
        "The version of Spanning Tree Protocal the bridge is currently 
         running."
    ::= { mstGeneralCfg 10 }

mstCistDefaultCfg OBJECT-TYPE
    SYNTAX INTEGER {
        default(1)
        }
    MAX-ACCESS read-write
    STATUS current
    DESCRIPTION
        "Setting the value to default(1) will set the Multiple
         Spanning Tree and member parameters to default.  default(1) is 
         always returned when read, but it does not mean anything."
    ::= { mstCistCfg 1 }

-- CIST Brige Configuration
mstCistBridgeCfg  OBJECT IDENTIFIER ::= { mstCistCfg 2 }

mstCistCurCfgBridgePriority OBJECT-TYPE
    SYNTAX  INTEGER  (0..65535)
    MAX-ACCESS  read-only
    STATUS  current
    DESCRIPTION
        "The value of the writable portion of the Brigde Identifier comprising
         of the first two octets."
    ::= { mstCistBridgeCfg 1 }

mstCistNewCfgBridgePriority OBJECT-TYPE
    SYNTAX  INTEGER  (0..65535)
    MAX-ACCESS  read-write
    STATUS  current
    DESCRIPTION
        "The value of the writable portion of the Brigde Identifier comprising
         of the first two octets."
    ::= { mstCistBridgeCfg 2 }


mstCistCurCfgBridgeMaxAge OBJECT-TYPE
    SYNTAX  INTEGER  (6..40)
    MAX-ACCESS  read-only
    STATUS  current
    DESCRIPTION
        "The value in seconds that all bridges use for MaxAge when this bridge
         is acting as the root."
    ::= { mstCistBridgeCfg 5 }

mstCistNewCfgBridgeMaxAge OBJECT-TYPE
    SYNTAX  INTEGER  (6..40)
    MAX-ACCESS  read-write
    STATUS  current
    DESCRIPTION
        "The value in seconds that all bridges use for MaxAge when this bridge
         is acting as the root."
    ::= { mstCistBridgeCfg 6 }

mstCistCurCfgBridgeForwardDelay OBJECT-TYPE
    SYNTAX  INTEGER  (4..30)
    MAX-ACCESS  read-only
    STATUS  current
    DESCRIPTION
        "The value in seconds that all bridges use for ForwardDelay when this 
         bridge is acting as the root."
    ::= { mstCistBridgeCfg 7 }

mstCistNewCfgBridgeForwardDelay OBJECT-TYPE
    SYNTAX  INTEGER  (4..30)
    MAX-ACCESS  read-write
    STATUS  current
    DESCRIPTION
        "The value in seconds that all bridges use for ForwardDelay when this 
         bridge is acting as the root."
    ::= { mstCistBridgeCfg 8 }

mstCistCurCfgVlanBmap OBJECT-TYPE
    SYNTAX  OCTET STRING (SIZE(0..512)) 
    MAX-ACCESS  read-only
    STATUS  current
    DESCRIPTION
    "The vlans applied to the CIST group.  The vlans are 
     presented in bitmap format. This string displays vlan number
     from 1 to 4094.

     in receiving order:

         OCTET 1  OCTET 2  .....
             xxxxxxxx xxxxxxxx ..... 
             ||    || |_ vlan 9
             ||    ||  
             ||    ||___ vlan 8
             ||    |____ vlan 7
             ||      .    .   .
             ||_________ vlan 2
             |__________ vlan 1

         where x : 1 - The represented vlan applied to the CIST group. 
                   0 - The represented vlan not applied to the group"
    ::= { mstCistBridgeCfg 9 }

mstCistNewCfgVlanBmap OBJECT-TYPE
    SYNTAX  OCTET STRING (SIZE(0..512)) 
    MAX-ACCESS  read-only
    STATUS  current
    DESCRIPTION
    "The vlans applied to the CIST group.  The vlans are 
     presented in bitmap format. This string displays vlan number
     from 1 to 4094.

     in receiving order:

         OCTET 1  OCTET 2  .....
             xxxxxxxx xxxxxxxx ..... 
             ||    || |_ vlan 9
             ||    ||  
             ||    ||___ vlan 8
             ||    |____ vlan 7
             ||      .    .   .
             ||_________ vlan 2
             |__________ vlan 1

         where x : 1 - The represented vlan applied to the CIST group. 
                   0 - The represented vlan not applied to the group"
    ::= { mstCistBridgeCfg 10 }

mstCistNewCfgAddVlan OBJECT-TYPE
    SYNTAX  Integer32
    MAX-ACCESS  read-create
    STATUS  current
    DESCRIPTION
        "The vlan to be added to the CIST Group.  A 
         '0' value is returned when read." 
    ::= { mstCistBridgeCfg 11 }

-- CIST Port Configuration

mstCistCurCfgPortTable OBJECT-TYPE
    SYNTAX SEQUENCE OF MstCistCurCfgPortTableEntry
    MAX-ACCESS not-accessible
    STATUS current
    DESCRIPTION
        "The table of CIST Port configuration."
    ::= { mstCistCfg 3 }

mstCistCurCfgPortTableEntry OBJECT-TYPE
    SYNTAX MstCistCurCfgPortTableEntry
    MAX-ACCESS not-accessible
    STATUS current
    DESCRIPTION
        "Information about a particular CIST Port configuration."
    INDEX { mstCistCurCfgPortIndex }
    ::= { mstCistCurCfgPortTable 1 }

MstCistCurCfgPortTableEntry ::= SEQUENCE {
    mstCistCurCfgPortIndex      PortNumber,
    mstCistCurCfgPortPriority   INTEGER,
    mstCistCurCfgPortPathCost   INTEGER,
    mstCistCurCfgPortLinkType   INTEGER,
    mstCistCurCfgPortEdge       INTEGER,
    mstCistCurCfgPortStpState   INTEGER,
    mstCistCurCfgPortHelloTime  INTEGER
    , mstCistCurCfgPortPvstProtection  INTEGER 
    }

mstCistCurCfgPortIndex OBJECT-TYPE
    SYNTAX PortNumber
    MAX-ACCESS read-only
    STATUS current
    DESCRIPTION
        "The port number of the port for which this entry contains spanning
         tree configuration."
    ::= { mstCistCurCfgPortTableEntry 1 }

mstCistCurCfgPortPriority OBJECT-TYPE
    SYNTAX INTEGER (0..240)
    MAX-ACCESS read-only
    STATUS current
    DESCRIPTION
        "The four most significant bits of the Port Identifier of the 
         Spanning Tree instance can be modified by setting this value."
    ::= { mstCistCurCfgPortTableEntry 2 }

mstCistCurCfgPortPathCost OBJECT-TYPE
    SYNTAX INTEGER (0..200000000)
    MAX-ACCESS read-only
    STATUS current
    DESCRIPTION
        "The contribution of this port to the path cost of paths towards 
         the CIST Root which include this port."
    ::= { mstCistCurCfgPortTableEntry 3 }

mstCistCurCfgPortLinkType OBJECT-TYPE
    SYNTAX INTEGER {
        auto(1),
        p2p(2),
        shared(3)
        }
    MAX-ACCESS read-only
    STATUS current
    DESCRIPTION
        "The administrative point-to-point status of the LAN segment attached 
         to this port.  A value of p2p (2) indicates that this port should 
         always be treated as if it is connected to a point-to-point link. 
         A value of shared(3) indicates that this port should be treated as 
         having a shared media connection.  A value of auto(1) indicates that 
         this port is considered to have a point-to-point link if it is an 
         Aggregator and all of its members are aggregatable, or if the MAC 
         entity is configured for full duplex operation, either through
         auto-negotiation or by management means. (for MSTP only)"
    ::= { mstCistCurCfgPortTableEntry 4 }

mstCistCurCfgPortEdge OBJECT-TYPE
    SYNTAX INTEGER {
        enabled(1),
        disabled(2)
        }
    MAX-ACCESS read-only
    STATUS current
    DESCRIPTION
        "The value of the Edge Port parameter. (for MSTP only)"
    ::= { mstCistCurCfgPortTableEntry 5 }

mstCistCurCfgPortStpState OBJECT-TYPE
    SYNTAX INTEGER {
        on(1),
        off(2)
        }
    MAX-ACCESS read-only
    STATUS current
    DESCRIPTION
        "Turn port's Spanning Tree on/off."
    ::= { mstCistCurCfgPortTableEntry 6 }

mstCistCurCfgPortHelloTime OBJECT-TYPE
    SYNTAX  INTEGER (1..10)
    MAX-ACCESS  read-only
    STATUS  current
    DESCRIPTION
        "The amount of time between the transmission of Configuration Port 
         PDUs in seconds."
    ::= { mstCistCurCfgPortTableEntry 7 } 

    mstCistCurCfgPortPvstProtection OBJECT-TYPE
    SYNTAX INTEGER {
        enabled(1),
        disabled(2)
        }
    MAX-ACCESS read-only
    STATUS current
    DESCRIPTION
        "The value of the PVST Protection parameter."
    ::= { mstCistCurCfgPortTableEntry 8 }

mstCistNewCfgPortTable OBJECT-TYPE
    SYNTAX SEQUENCE OF MstCistNewCfgPortTableEntry
    MAX-ACCESS not-accessible
    STATUS current
    DESCRIPTION
        "The table of CIST Port configuration."
    ::= { mstCistCfg 4 }

mstCistNewCfgPortTableEntry OBJECT-TYPE
    SYNTAX MstCistNewCfgPortTableEntry
    MAX-ACCESS not-accessible
    STATUS current
    DESCRIPTION
        "Information about a particular CIST Port configuration."
    INDEX { mstCistNewCfgPortIndex }
    ::= { mstCistNewCfgPortTable 1 }

MstCistNewCfgPortTableEntry ::= SEQUENCE {
    mstCistNewCfgPortIndex      PortNumber,
    mstCistNewCfgPortPriority   INTEGER,
    mstCistNewCfgPortPathCost   INTEGER,
    mstCistNewCfgPortStpState   INTEGER,
    mstCistNewCfgPortHelloTime  INTEGER
    , mstCistNewCfgPortPvstProtection  INTEGER 
    }

mstCistNewCfgPortIndex OBJECT-TYPE
    SYNTAX PortNumber
    MAX-ACCESS read-only
    STATUS current
    DESCRIPTION
        "The port number of the port for which this entry contains spanning
         tree configuration."
    ::= { mstCistNewCfgPortTableEntry 1 }

mstCistNewCfgPortPriority OBJECT-TYPE
    SYNTAX INTEGER (0..240)
    MAX-ACCESS read-write
    STATUS current
    DESCRIPTION
        "The four most significant bits of the Port Identifier of the 
         Spanning Tree instance can be modified by setting this value."
    ::= { mstCistNewCfgPortTableEntry 2 }

mstCistNewCfgPortPathCost OBJECT-TYPE
    SYNTAX INTEGER (0..200000000)
    MAX-ACCESS read-write
    STATUS current
    DESCRIPTION
        "The contribution of this port to the path cost of paths towards 
         the CIST Root which include this port."
    ::= { mstCistNewCfgPortTableEntry 3 }



mstCistNewCfgPortStpState OBJECT-TYPE
    SYNTAX INTEGER {
        on(1),
        off(2)
        }
    MAX-ACCESS read-write
    STATUS current
    DESCRIPTION
        "Turn port's Spanning Tree on/off."
    ::= { mstCistNewCfgPortTableEntry 6 }

mstCistNewCfgPortHelloTime OBJECT-TYPE
    SYNTAX  INTEGER (1..10)
    MAX-ACCESS  read-write
    STATUS  current
    DESCRIPTION
        "The amount of time between the transmission of Configuration Port 
         PDUs in seconds."
    ::= { mstCistNewCfgPortTableEntry 7 }

    mstCistNewCfgPortPvstProtection OBJECT-TYPE
    SYNTAX INTEGER {
        enabled(1),
        disabled(2)
        }
    MAX-ACCESS read-write
    STATUS current
    DESCRIPTION
        "The value of the PVST Protection parameter."
    ::= { mstCistNewCfgPortTableEntry 8 }
 

-- L2 general




pvstCompatibilityCurCfgState OBJECT-TYPE
    SYNTAX INTEGER  {
        enable(1),
        disable(2)
        }
    MAX-ACCESS  read-only
    STATUS  current
    DESCRIPTION
        "Enable or disable PVST+ compatibility"
    ::= { l2GeneralCfg 9 }

pvstCompatibilityNewCfgState OBJECT-TYPE
    SYNTAX INTEGER  {
        enable(1),
        disable(2)
        }
    MAX-ACCESS  read-write
    STATUS  current
    DESCRIPTION
        "Enable or disable PVST+ compatibility"
    ::= { l2GeneralCfg 10 }

nostpCurCfgState OBJECT-TYPE
    SYNTAX INTEGER {
        enable(1),
        disable(2)
        }
    MAX-ACCESS read-only
    STATUS current
    DESCRIPTION
        "STP Mode Disable global state."
    ::= { l2GeneralCfg 11 }

nostpNewCfgState OBJECT-TYPE
    SYNTAX INTEGER {
        enable(1),
        disable(2)
        }
    MAX-ACCESS read-write
    STATUS current
    DESCRIPTION
        "Enable or disable STP Mode Disable."
    ::= { l2GeneralCfg 12 }

stpLoopGuardCurCfgState OBJECT-TYPE
    SYNTAX INTEGER {
        enable(1),
        disable(2)
        }
    MAX-ACCESS read-only
    STATUS current
    DESCRIPTION
        "STP loop guard global state."
    ::= { l2GeneralCfg 13 }

stpLoopGuardNewCfgState OBJECT-TYPE
    SYNTAX INTEGER {
        enable(1),
        disable(2)
        }
    MAX-ACCESS read-write
    STATUS current
    DESCRIPTION
        "Enable or disable STP loop guard."
    ::= { l2GeneralCfg 14 }

vlanAutoStgCurCfgState OBJECT-TYPE
    SYNTAX INTEGER {
        enable(1),
        disable(2)
        }
    MAX-ACCESS read-only
    STATUS current
    DESCRIPTION
        "VLAN automatic STG assignment global state."
    ::= { l2GeneralCfg 15 }

vlanAutoStgNewCfgState OBJECT-TYPE
    SYNTAX INTEGER {
        enable(1),
        disable(2)
        }
    MAX-ACCESS read-write
    STATUS current
    DESCRIPTION
        "Enable or disable VLAN automatic STG assignment."
    ::= { l2GeneralCfg 16 }



--
-- { LLDP Port Table
--
lldpPortTableMaxEnt OBJECT-TYPE
    SYNTAX  INTEGER
    MAX-ACCESS  read-only
    STATUS  current
    DESCRIPTION
        "The maximum number of rows in the port configuration
         host table."
    ::= { lldpCfg 1 }

lldpCurCfgPortTable OBJECT-TYPE
    SYNTAX  SEQUENCE OF LldpCurCfgPortEntry
    MAX-ACCESS  not-accessible
    STATUS  current
    DESCRIPTION
        "The table of LLDP port configuration in the current_configuration
         block."
    ::= { lldpCfg 2 }

lldpCurCfgPortEntry OBJECT-TYPE
    SYNTAX  LldpCurCfgPortEntry 
    MAX-ACCESS  not-accessible
    STATUS  current
    DESCRIPTION
        "A row in the LLDP port configuration table in the
         current_configuration block."
    INDEX   { lldpCurCfgPortIndx }
    ::= { lldpCurCfgPortTable 1 }
 
LldpCurCfgPortEntry ::= SEQUENCE {
    lldpCurCfgPortIndx           PortNumber,
    lldpCurCfgPortAdmStat        INTEGER,
    lldpCurCfgPortSnmpTrap    	 INTEGER
    ,lldpCurCfgPortportdesctlv   INTEGER
    ,lldpCurCfgPortsysnametlv    INTEGER
    ,lldpCurCfgPortsysdescrtlv   INTEGER
    ,lldpCurCfgPortsyscaptlv     INTEGER
    ,lldpCurCfgPortmgmtaddrtlv   INTEGER
    ,lldpCurCfgPortportvidtlv    INTEGER
    ,lldpCurCfgPortportprottlv   INTEGER
    ,lldpCurCfgPortvlannametlv   INTEGER
    ,lldpCurCfgPortprotidtlv     INTEGER
    ,lldpCurCfgPortmacphytlv     INTEGER
    ,lldpCurCfgPortpowermditlv   INTEGER
    ,lldpCurCfgPortlinkaggrtlv   INTEGER
    ,lldpCurCfgPortframesztlv    INTEGER
    ,lldpCurCfgPortdcbxtlv       INTEGER
    }
 
lldpCurCfgPortIndx OBJECT-TYPE
    SYNTAX  PortNumber
    MAX-ACCESS  read-only
    STATUS  current
    DESCRIPTION
        "The index of the row in LLDP port configurations table."
    ::= { lldpCurCfgPortEntry 1 }
 
lldpCurCfgPortAdmStat OBJECT-TYPE
    SYNTAX  INTEGER {
	enabledTxOnly(1),
	enabledRxOnly(2),
	enabledRxTx(3),
        disabled(4)
        } 
    MAX-ACCESS  read-only
    STATUS  current
    DESCRIPTION
        "This is the admin status of the LLDP port."
    ::= { lldpCurCfgPortEntry 2 }

lldpCurCfgPortSnmpTrap OBJECT-TYPE
    SYNTAX  INTEGER {
        enabled(1),
        disabled(2)
        } 
    MAX-ACCESS  read-only
    STATUS  current
    DESCRIPTION
        "This is the SNMP trap notification state of the LLDP port."
    ::= { lldpCurCfgPortEntry 3 }
 
lldpCurCfgPortportdesctlv OBJECT-TYPE
    SYNTAX  INTEGER {
        enabled(1),
        disabled(2)
        }
    MAX-ACCESS  read-only
    STATUS  current
    DESCRIPTION
        "This is the Port Description TLV state of the LLDP port."
    ::= { lldpCurCfgPortEntry 4 }

lldpCurCfgPortsysnametlv OBJECT-TYPE
    SYNTAX  INTEGER {
        enabled(1),
        disabled(2)
        }
    MAX-ACCESS  read-only
    STATUS  current
    DESCRIPTION
        "This is the System Name TLV state of the LLDP port."
    ::= { lldpCurCfgPortEntry 5 }

lldpCurCfgPortsysdescrtlv OBJECT-TYPE
    SYNTAX  INTEGER {
        enabled(1),
        disabled(2)
        }
    MAX-ACCESS  read-only
    STATUS  current
    DESCRIPTION
        "This is the System Description TLV state of the LLDP port."
    ::= { lldpCurCfgPortEntry 6 }

lldpCurCfgPortsyscaptlv OBJECT-TYPE
    SYNTAX  INTEGER {
        enabled(1),
        disabled(2)
        }
    MAX-ACCESS  read-only
    STATUS  current
    DESCRIPTION
        "This is the System Capabilities TLV state of the LLDP port."
    ::= { lldpCurCfgPortEntry 7 }

lldpCurCfgPortmgmtaddrtlv OBJECT-TYPE
    SYNTAX  INTEGER {
        enabled(1),
        disabled(2)
        }
    MAX-ACCESS  read-only
    STATUS  current
    DESCRIPTION
        "This is the Management Address TLV state of the LLDP port."
    ::= { lldpCurCfgPortEntry 8 }

lldpCurCfgPortportvidtlv OBJECT-TYPE
    SYNTAX  INTEGER {
        enabled(1),
        disabled(2)
        }
    MAX-ACCESS  read-only
    STATUS  current
    DESCRIPTION
        "This is the Port VLAN ID TLV state of the LLDP port."
    ::= { lldpCurCfgPortEntry 9 }

lldpCurCfgPortportprottlv OBJECT-TYPE
    SYNTAX  INTEGER {
        enabled(1),
        disabled(2)
        }
    MAX-ACCESS  read-only
    STATUS  current
    DESCRIPTION
        "This is the Port and Protocol VLAN ID TLV state of the LLDP port."
    ::= { lldpCurCfgPortEntry 10 }

lldpCurCfgPortvlannametlv OBJECT-TYPE
    SYNTAX  INTEGER {
        enabled(1),
        disabled(2)
        }
    MAX-ACCESS  read-only
    STATUS  current
    DESCRIPTION
        "This is the VLAN Name TLV state of the LLDP port."
    ::= { lldpCurCfgPortEntry 11 }

lldpCurCfgPortprotidtlv OBJECT-TYPE
    SYNTAX  INTEGER {
        enabled(1),
        disabled(2)
        }
    MAX-ACCESS  read-only
    STATUS  current
    DESCRIPTION
        "This is the Protocol Identity TLV state of the LLDP port."
    ::= { lldpCurCfgPortEntry 12 }

lldpCurCfgPortmacphytlv OBJECT-TYPE
    SYNTAX  INTEGER {
        enabled(1),
        disabled(2)
        }
    MAX-ACCESS  read-only
    STATUS  current
    DESCRIPTION
        "This is the MAC/PHY Configuration/Status TLV state of the LLDP port."
    ::= { lldpCurCfgPortEntry 13 }

lldpCurCfgPortpowermditlv OBJECT-TYPE
    SYNTAX  INTEGER {
        enabled(1),
        disabled(2)
        }
    MAX-ACCESS  read-only
    STATUS  current
    DESCRIPTION
        "This is the Power Via MDI TLV state of the LLDP port."
    ::= { lldpCurCfgPortEntry 14 }

lldpCurCfgPortlinkaggrtlv OBJECT-TYPE
    SYNTAX  INTEGER {
        enabled(1),
        disabled(2)
        }
    MAX-ACCESS  read-only
    STATUS  current
    DESCRIPTION
        "This is the Link Aggregation TLV state of the LLDP port."
    ::= { lldpCurCfgPortEntry 15 }

lldpCurCfgPortframesztlv OBJECT-TYPE
    SYNTAX  INTEGER {
        enabled(1),
        disabled(2)
        }
    MAX-ACCESS  read-only
    STATUS  current
    DESCRIPTION
        "This is the Maximum Frame Size TLV state of the LLDP port."
    ::= { lldpCurCfgPortEntry 16 }

lldpCurCfgPortdcbxtlv OBJECT-TYPE
    SYNTAX  INTEGER {
        enabled(1),
        disabled(2)
        }
    MAX-ACCESS  read-only
    STATUS  current
    DESCRIPTION
        "This is the DCBX TLV state of the LLDP port."
    ::= { lldpCurCfgPortEntry 17 }



lldpNewCfgPortTable OBJECT-TYPE
    SYNTAX  SEQUENCE OF LldpNewCfgPortEntry
    MAX-ACCESS  not-accessible
    STATUS  current
    DESCRIPTION
        "The table of LLDP port configuration in the new_configuration
         block."
    ::= { lldpCfg 3 }

lldpNewCfgPortEntry OBJECT-TYPE
    SYNTAX  LldpNewCfgPortEntry
    MAX-ACCESS  not-accessible
    STATUS  current
    DESCRIPTION
        "A row in the LLDP port configuration table in the
         new_configuration block."
    INDEX   { lldpNewCfgPortIndx }
    ::= { lldpNewCfgPortTable 1 }
 
LldpNewCfgPortEntry ::= SEQUENCE {
    lldpNewCfgPortIndx           PortNumber,
    lldpNewCfgPortAdmStat        INTEGER,
    lldpNewCfgPortSnmpTrap       INTEGER
    ,lldpNewCfgPortportdesctlv   INTEGER
    ,lldpNewCfgPortsysnametlv    INTEGER
    ,lldpNewCfgPortsysdescrtlv   INTEGER
    ,lldpNewCfgPortsyscaptlv     INTEGER
    ,lldpNewCfgPortmgmtaddrtlv   INTEGER
    ,lldpNewCfgPortportvidtlv    INTEGER
    ,lldpNewCfgPortportprottlv   INTEGER
    ,lldpNewCfgPortvlannametlv   INTEGER
    ,lldpNewCfgPortprotidtlv     INTEGER
    ,lldpNewCfgPortmacphytlv     INTEGER
    ,lldpNewCfgPortpowermditlv   INTEGER
    ,lldpNewCfgPortlinkaggrtlv   INTEGER
    ,lldpNewCfgPortframesztlv    INTEGER
    ,lldpNewCfgPortalltlv        INTEGER
    ,lldpNewCfgPortdcbxtlv       INTEGER
    }
 
lldpNewCfgPortIndx OBJECT-TYPE
    SYNTAX  PortNumber
    MAX-ACCESS  read-only
    STATUS  current
    DESCRIPTION
        "The index of the row in LLDP port configurations table."
    ::= { lldpNewCfgPortEntry 1 }
 
lldpNewCfgPortAdmStat OBJECT-TYPE
    SYNTAX  INTEGER {
	enabledTxOnly(1),
	enabledRxOnly(2),
	enabledRxTx(3),
	disabled(4)
        } 
    MAX-ACCESS  read-write
    STATUS  current
    DESCRIPTION
        "This is the admin status of the LLDP port."
    ::= { lldpNewCfgPortEntry 2 }

lldpNewCfgPortSnmpTrap OBJECT-TYPE
    SYNTAX  INTEGER {
        enabled(1),
	disabled(2)
        } 
    MAX-ACCESS  read-write
    STATUS  current
    DESCRIPTION
        "This is the SNMP trap notification state of the LLDP port"
    ::= { lldpNewCfgPortEntry 3 }

lldpNewCfgPortportdesctlv OBJECT-TYPE
    SYNTAX  INTEGER {
        enabled(1),
        disabled(2)
        }
    MAX-ACCESS  read-write
    STATUS  current
    DESCRIPTION
        "This is the Port Description TLV state of the LLDP port."
    ::= { lldpNewCfgPortEntry 4 }

lldpNewCfgPortsysnametlv OBJECT-TYPE
    SYNTAX  INTEGER {
        enabled(1),
        disabled(2)
        }
    MAX-ACCESS  read-write
    STATUS  current
    DESCRIPTION
        "This is the System Name TLV state of the LLDP port."
    ::= { lldpNewCfgPortEntry 5 }

lldpNewCfgPortsysdescrtlv OBJECT-TYPE
    SYNTAX  INTEGER {
        enabled(1),
        disabled(2)
        }
    MAX-ACCESS  read-write
    STATUS  current
    DESCRIPTION
        "This is the System Description TLV state of the LLDP port."
    ::= { lldpNewCfgPortEntry 6 }

lldpNewCfgPortsyscaptlv OBJECT-TYPE
    SYNTAX  INTEGER {
        enabled(1),
        disabled(2)
        }
    MAX-ACCESS  read-write
    STATUS  current
    DESCRIPTION
        "This is the System Capabilities TLV state of the LLDP port."
    ::= { lldpNewCfgPortEntry 7 }

lldpNewCfgPortmgmtaddrtlv OBJECT-TYPE
    SYNTAX  INTEGER {
        enabled(1),
        disabled(2)
        }
    MAX-ACCESS  read-write
    STATUS  current
    DESCRIPTION
        "This is the Management Address TLV state of the LLDP port."
    ::= { lldpNewCfgPortEntry 8 }

lldpNewCfgPortportvidtlv OBJECT-TYPE
    SYNTAX  INTEGER {
        enabled(1),
        disabled(2)
        }
    MAX-ACCESS  read-write
    STATUS  current
    DESCRIPTION
        "This is the Port VLAN ID TLV state of the LLDP port."
    ::= { lldpNewCfgPortEntry 9 }

lldpNewCfgPortportprottlv OBJECT-TYPE
    SYNTAX  INTEGER {
        enabled(1),
        disabled(2)
        }
    MAX-ACCESS  read-write
    STATUS  current
    DESCRIPTION
        "This is the Port and Protocol VLAN ID TLV state of the LLDP port."
    ::= { lldpNewCfgPortEntry 10 }

lldpNewCfgPortvlannametlv OBJECT-TYPE
    SYNTAX  INTEGER {
        enabled(1),
        disabled(2)
        }
    MAX-ACCESS  read-write
    STATUS  current
    DESCRIPTION
        "This is the VLAN Name TLV state of the LLDP port."
    ::= { lldpNewCfgPortEntry 11 }

lldpNewCfgPortprotidtlv OBJECT-TYPE
    SYNTAX  INTEGER {
        enabled(1),
        disabled(2)
        }
    MAX-ACCESS  read-write
    STATUS  current
    DESCRIPTION
        "This is the Protocol Identity TLV state of the LLDP port."
    ::= { lldpNewCfgPortEntry 12 }

lldpNewCfgPortmacphytlv OBJECT-TYPE
    SYNTAX  INTEGER {
        enabled(1),
        disabled(2)
        }
    MAX-ACCESS  read-write
    STATUS  current
    DESCRIPTION
        "This is the MAC/PHY Configuration/Status TLV state of the LLDP port."
    ::= { lldpNewCfgPortEntry 13 }

lldpNewCfgPortpowermditlv OBJECT-TYPE
    SYNTAX  INTEGER {
        enabled(1),
        disabled(2)
        }
    MAX-ACCESS  read-write
    STATUS  current
    DESCRIPTION
        "This is the Power Via MDI TLV state of the LLDP port."
    ::= { lldpNewCfgPortEntry 14 }

lldpNewCfgPortlinkaggrtlv OBJECT-TYPE
    SYNTAX  INTEGER {
        enabled(1),
        disabled(2)
        }
    MAX-ACCESS  read-write
    STATUS  current
    DESCRIPTION
        "This is the Link Aggregation TLV state of the LLDP port."
    ::= { lldpNewCfgPortEntry 15 }

lldpNewCfgPortframesztlv OBJECT-TYPE
    SYNTAX  INTEGER {
        enabled(1),
        disabled(2)
        }
    MAX-ACCESS  read-write
    STATUS  current
    DESCRIPTION
        "This is the Maximum Frame Size TLV state of the LLDP port."
    ::= { lldpNewCfgPortEntry 16 }

lldpNewCfgPortalltlv OBJECT-TYPE
    SYNTAX  INTEGER {
        enabled(1),
        disabled(2),
        other(3)
        }
    MAX-ACCESS  read-write
    STATUS  current
    DESCRIPTION
        "Set the corresponding state for all the LLDP port's TLVs.
         other(3) is returned when the object is read."
    ::= { lldpNewCfgPortEntry 17 }

lldpNewCfgPortdcbxtlv OBJECT-TYPE
    SYNTAX  INTEGER {
        enabled(1),
        disabled(2)
        }
    MAX-ACCESS  read-write
    STATUS  current
    DESCRIPTION
        "This is the DCBX TLV state of the LLDP port."
    ::= { lldpNewCfgPortEntry 18 }


--
-- } End of LLDP Port Table
--

--
-- { LLDP General Table
--
lldpGeneral      OBJECT IDENTIFIER ::= { lldpCfg 4 }

lldpCurCfgState OBJECT-TYPE
    SYNTAX INTEGER {
        on(1),
        off(2)
        }
    MAX-ACCESS read-only
    STATUS current
    DESCRIPTION
        "LLDP global state."
    ::= { lldpGeneral 1 }

lldpNewCfgState OBJECT-TYPE
    SYNTAX INTEGER {
        on(1),
        off(2)
        }
    MAX-ACCESS read-write
    STATUS current
    DESCRIPTION
        "Globally turn LLDP on or off."
    ::= { lldpGeneral 2 }
       
lldpCurCfgMsgTxInt OBJECT-TYPE
      SYNTAX  INTEGER  (5..32768)
      MAX-ACCESS  read-only
      STATUS  current
      DESCRIPTION
              "LLDP message transmission interval for LLDPDU."
      ::= { lldpGeneral 3 }
       
lldpNewCfgMsgTxInt OBJECT-TYPE
      SYNTAX  INTEGER  (5..32768)
      MAX-ACCESS  read-write
      STATUS  current
      DESCRIPTION
              "LLDP message transmission interval for LLDPDU."
      ::= { lldpGeneral 4 }
       
lldpCurCfgMsgTxHld OBJECT-TYPE
      SYNTAX  INTEGER  (2..10)
      MAX-ACCESS  read-only
      STATUS  current
      DESCRIPTION
              "LLDP message transmission holdtime-multiplier."
      ::= { lldpGeneral 5 }
       
lldpNewCfgMsgTxHld OBJECT-TYPE
      SYNTAX  INTEGER  (2..10)
      MAX-ACCESS  read-write
      STATUS  current
      DESCRIPTION
              "LLDP message transmission holdtime-multiplier."
      ::= { lldpGeneral 6 }
 
lldpCurCfgNotifInt OBJECT-TYPE
      SYNTAX  INTEGER (1..3600)
      MAX-ACCESS  read-only
      STATUS  current
      DESCRIPTION
              "LLDP minimum SNMP trap notification interval."
      ::= { lldpGeneral 7 }
       
lldpNewCfgNotifInt OBJECT-TYPE
      SYNTAX  INTEGER (1..3600)
      MAX-ACCESS  read-write
      STATUS  current
      DESCRIPTION
              "LLDP minimum SNMP trap notification interval."
      ::= { lldpGeneral 8 }
       
lldpCurCfgTxDelay OBJECT-TYPE
      SYNTAX  INTEGER  (1..8192)
      MAX-ACCESS  read-only
      STATUS  current
      DESCRIPTION
              "LLDP delay interval between advertisements."
      ::= { lldpGeneral 9 }
       
lldpNewCfgTxDelay OBJECT-TYPE
      SYNTAX  INTEGER  (1..8192)
      MAX-ACCESS  read-write
      STATUS  current
      DESCRIPTION
              "LLDP delay interval between advertisements."
      ::= { lldpGeneral 10 }

lldpCurCfgReinitDelay OBJECT-TYPE
      SYNTAX  INTEGER  (1..10)
      MAX-ACCESS  read-only
      STATUS  current
      DESCRIPTION
              "LLDP reinit delay interval."
      ::= { lldpGeneral 11 }
       
lldpNewCfgReinitDelay OBJECT-TYPE
      SYNTAX  INTEGER  (1..10)
      MAX-ACCESS  read-write
      STATUS  current
      DESCRIPTION
              "LLDP reinit delay interval."
      ::= { lldpGeneral 12 }
--
-- } End of LLDP General Table
--

--
-- { LLDP Statistics
--
lldpStatsTableMaxEnt OBJECT-TYPE
      SYNTAX  INTEGER
      MAX-ACCESS  read-only
      STATUS  current
      DESCRIPTION
              "The maximum number of rows in the statistics 
	       host table."
      ::= { lldpStats 1 }

lldpStatsTable OBJECT-TYPE
      SYNTAX SEQUENCE OF LldpStatsTableEntry
      MAX-ACCESS not-accessible
      STATUS current
      DESCRIPTION
              "The table of LLDP statistics."
      ::= { lldpStats 2 }

lldpStatsClearAll  OBJECT-TYPE
    SYNTAX  INTEGER {
        ok(1),
        clear(2)
        }
    MAX-ACCESS  read-write
    STATUS  current
    DESCRIPTION
        "Setting this to clear(2) results in clearing the LLDP statistics
        for all the ports."
    ::= { lldpStats 3 }

lldpStatsTableEntry OBJECT-TYPE
      SYNTAX LldpStatsTableEntry
      MAX-ACCESS not-accessible
      STATUS current
      DESCRIPTION
              "LLDP statistics info."
      INDEX   { lldpStatsIndex }
      ::= { lldpStatsTable 1 }

LldpStatsTableEntry ::= SEQUENCE {
    lldpStatsIndex                 PortNumber,
    lldpStatsFramesOutTotal        Counter32,
    lldpStatsFramesInTotal         Counter32,
    lldpStatsFramesInErrorsTotal   Counter32,
    lldpStatsFramesDiscardedTotal  Counter32,
    lldpStatsTLVsUnrecognizedTotal Counter32,
    lldpStatsAgeoutsTotal          Counter32,
    lldpStatsClear                 INTEGER
}

lldpStatsIndex OBJECT-TYPE
    SYNTAX  PortNumber
    MAX-ACCESS  read-only
    STATUS  current
    DESCRIPTION
        "The index of the row in LLDP port statistics."
    ::= { lldpStatsTableEntry 1 }
 
lldpStatsFramesOutTotal OBJECT-TYPE
    SYNTAX Counter32
    MAX-ACCESS read-only
    STATUS current
    DESCRIPTION
	"The total number of LLDP frames transmitted in this port." 
    ::= { lldpStatsTableEntry 2 }

lldpStatsFramesInTotal OBJECT-TYPE
    SYNTAX Counter32
    MAX-ACCESS read-only
    STATUS current
    DESCRIPTION
	"The total number of LLDP frames received in this port." 
    ::= { lldpStatsTableEntry 3 }

lldpStatsFramesInErrorsTotal OBJECT-TYPE
    SYNTAX Counter32
    MAX-ACCESS read-only
    STATUS current
    DESCRIPTION
	"The total number of erroneous LLDP frames received in this port." 
    ::= { lldpStatsTableEntry 4 }

lldpStatsFramesDiscardedTotal OBJECT-TYPE
    SYNTAX Counter32
    MAX-ACCESS read-only
    STATUS current
    DESCRIPTION
	"The total number of received LLDP frames discarded in this port." 
    ::= { lldpStatsTableEntry 5 }

lldpStatsTLVsUnrecognizedTotal OBJECT-TYPE
    SYNTAX Counter32
    MAX-ACCESS read-only
    STATUS current
    DESCRIPTION
	"The total number of unrecognized TLVs in this port." 
    ::= { lldpStatsTableEntry 6 }

lldpStatsAgeoutsTotal OBJECT-TYPE
    SYNTAX Counter32
    MAX-ACCESS read-only
    STATUS current
    DESCRIPTION
	"The total number of neighbor's information deleted in this port." 
    ::= { lldpStatsTableEntry 7 }

lldpStatsClear  OBJECT-TYPE
    SYNTAX  INTEGER {
        ok(1),
        clear(2)
        }
    MAX-ACCESS  read-write
    STATUS  current
    DESCRIPTION
        "Setting this to clear(2) results in clearing the LLDP statistics."
    ::= { lldpStatsTableEntry 8 }

--
-- } End of LLDP Statistics
--

--
--  { LLDP Info
--
lldpInfoPortTable OBJECT-TYPE
      SYNTAX SEQUENCE OF LldpInfoPortEntry
      MAX-ACCESS not-accessible
      STATUS  current
      DESCRIPTION
              "The table of LLDP Port Info."
      ::= { lldpInfo 1 }

lldpInfoPortEntry OBJECT-TYPE
      SYNTAX LldpInfoPortEntry
      MAX-ACCESS not-accessible
      STATUS current
      DESCRIPTION
              "LLDP Port Info."
      INDEX   { lldpInfoPortIndex }
      ::= { lldpInfoPortTable 1 }

LldpInfoPortEntry ::= SEQUENCE {
      lldpInfoPortIndex                PortNumber,
      lldpInfoPortAlias                DisplayString,
      lldpInfoPortMacAddress           PhysAddress,
      lldpInfoPortMtu                  Integer32,
      lldpInfoPortEnabled              INTEGER,
      lldpInfoPortAdminStatus          INTEGER,
      lldpInfoPortRxChanges            INTEGER
     ,lldpInfoPortportdesctlv   INTEGER
     ,lldpInfoPortsysnametlv    INTEGER
     ,lldpInfoPortsysdescrtlv   INTEGER
     ,lldpInfoPortsyscaptlv     INTEGER
     ,lldpInfoPortmgmtaddrtlv   INTEGER
     ,lldpInfoPortportvidtlv    INTEGER
     ,lldpInfoPortportprottlv   INTEGER
     ,lldpInfoPortvlannametlv   INTEGER
     ,lldpInfoPortprotidtlv     INTEGER
     ,lldpInfoPortmacphytlv     INTEGER
     ,lldpInfoPortpowermditlv   INTEGER
     ,lldpInfoPortlinkaggrtlv   INTEGER
     ,lldpInfoPortframesztlv    INTEGER
     ,lldpInfoPortdcbxtlv       INTEGER
}

lldpInfoPortIndex OBJECT-TYPE
      SYNTAX  PortNumber
      MAX-ACCESS  read-only
      STATUS  current
      DESCRIPTION
          "The index of the row in LLDP info port table."
      ::= { lldpInfoPortEntry 1 }

lldpInfoPortAlias OBJECT-TYPE
      SYNTAX  DisplayString  (SIZE(0..32))
      MAX-ACCESS  read-only
      STATUS  current
      DESCRIPTION
          "The port alias of the port in LLDP info port table."
      ::= { lldpInfoPortEntry 2 }

lldpInfoPortMacAddress OBJECT-TYPE
      SYNTAX  PhysAddress
      MAX-ACCESS  read-only
      STATUS  current
      DESCRIPTION
          "The mac address of the port in LLDP info port table."
      ::= { lldpInfoPortEntry 3 }

lldpInfoPortMtu OBJECT-TYPE
      SYNTAX  Integer32
      MAX-ACCESS  read-only
      STATUS  current
      DESCRIPTION
          "The MTU size of the port in LLDP info port table."
      ::= { lldpInfoPortEntry 4 }

lldpInfoPortEnabled OBJECT-TYPE
      SYNTAX  INTEGER {
          true(1),
          false(2)
      }
      MAX-ACCESS  read-only
      STATUS  current
      DESCRIPTION
          "The PortEnabled field of the port in LLDP info port table."
      ::= { lldpInfoPortEntry 5 }

lldpInfoPortAdminStatus OBJECT-TYPE
      SYNTAX  INTEGER {
          enabledTxOnly(1),
          enabledRxOnly(2),
          enabledRxTx(3),
          disabled(4)
      }
      MAX-ACCESS  read-only
      STATUS  current
      DESCRIPTION
          "The Admin Status of the port in LLDP info port table."
      ::= { lldpInfoPortEntry 6 }

lldpInfoPortRxChanges OBJECT-TYPE
      SYNTAX  INTEGER {
          true(1),
          false(2)
      }
      MAX-ACCESS  read-only
      STATUS  current
      DESCRIPTION
          "The rxChanges field of the port in LLDP info port table."
      ::= { lldpInfoPortEntry 7 }

lldpInfoPortportdesctlv OBJECT-TYPE
    SYNTAX  INTEGER {
        enabled(1),
        disabled(2)
        }
    MAX-ACCESS  read-only
    STATUS  current
    DESCRIPTION
        "This is the Port Description TLV state of the LLDP port."
    ::= { lldpInfoPortEntry 8 }

lldpInfoPortsysnametlv OBJECT-TYPE
    SYNTAX  INTEGER {
        enabled(1),
        disabled(2)
        }
    MAX-ACCESS  read-only
    STATUS  current
    DESCRIPTION
        "This is the System Name TLV state of the LLDP port."
    ::= { lldpInfoPortEntry 9 }

lldpInfoPortsysdescrtlv OBJECT-TYPE
    SYNTAX  INTEGER {
        enabled(1),
        disabled(2)
        }
    MAX-ACCESS  read-only
    STATUS  current
    DESCRIPTION
        "This is the System Description TLV state of the LLDP port."
    ::= { lldpInfoPortEntry 10 }

lldpInfoPortsyscaptlv OBJECT-TYPE
    SYNTAX  INTEGER {
        enabled(1),
        disabled(2)
        }
    MAX-ACCESS  read-only
    STATUS  current
    DESCRIPTION
        "This is the System Capabilities TLV state of the LLDP port."
    ::= { lldpInfoPortEntry 11 }

lldpInfoPortmgmtaddrtlv OBJECT-TYPE
    SYNTAX  INTEGER {
        enabled(1),
        disabled(2)
        }
    MAX-ACCESS  read-only
    STATUS  current
    DESCRIPTION
        "This is the Management Address TLV state of the LLDP port."
    ::= { lldpInfoPortEntry 12 }

lldpInfoPortportvidtlv OBJECT-TYPE
    SYNTAX  INTEGER {
        enabled(1),
        disabled(2)
        }
    MAX-ACCESS  read-only
    STATUS  current
    DESCRIPTION
        "This is the Port VLAN ID TLV state of the LLDP port."
    ::= { lldpInfoPortEntry 13 }

lldpInfoPortportprottlv OBJECT-TYPE
    SYNTAX  INTEGER {
        enabled(1),
        disabled(2)
        }
    MAX-ACCESS  read-only
    STATUS  current
    DESCRIPTION
        "This is the Port and Protocol VLAN ID TLV state of the LLDP port."
    ::= { lldpInfoPortEntry 14 }

lldpInfoPortvlannametlv OBJECT-TYPE
    SYNTAX  INTEGER {
        enabled(1),
        disabled(2)
        }
    MAX-ACCESS  read-only
    STATUS  current
    DESCRIPTION
        "This is the VLAN Name TLV state of the LLDP port."
    ::= { lldpInfoPortEntry 15 }

lldpInfoPortprotidtlv OBJECT-TYPE
    SYNTAX  INTEGER {
        enabled(1),
        disabled(2)
        }
    MAX-ACCESS  read-only
    STATUS  current
    DESCRIPTION
        "This is the Protocol Identity TLV state of the LLDP port."
    ::= { lldpInfoPortEntry 16 }

lldpInfoPortmacphytlv OBJECT-TYPE
    SYNTAX  INTEGER {
        enabled(1),
        disabled(2)
        }
    MAX-ACCESS  read-only
    STATUS  current
    DESCRIPTION
        "This is the MAC/PHY Configuration/Status TLV state of the LLDP port."
    ::= { lldpInfoPortEntry 17 }

lldpInfoPortpowermditlv OBJECT-TYPE
    SYNTAX  INTEGER {
        enabled(1),
        disabled(2)
        }
    MAX-ACCESS  read-only
    STATUS  current
    DESCRIPTION
        "This is the Power Via MDI TLV state of the LLDP port."
    ::= { lldpInfoPortEntry 18 }

lldpInfoPortlinkaggrtlv OBJECT-TYPE
    SYNTAX  INTEGER {
        enabled(1),
        disabled(2)
        }
    MAX-ACCESS  read-only
    STATUS  current
    DESCRIPTION
        "This is the Link Aggregation TLV state of the LLDP port."
    ::= { lldpInfoPortEntry 19 }

lldpInfoPortframesztlv OBJECT-TYPE
    SYNTAX  INTEGER {
        enabled(1),
        disabled(2)
        }
    MAX-ACCESS  read-only
    STATUS  current
    DESCRIPTION
        "This is the Maximum Frame Size TLV state of the LLDP port."
    ::= { lldpInfoPortEntry 20 }

lldpInfoPortdcbxtlv OBJECT-TYPE
    SYNTAX  INTEGER {
        enabled(1),
        disabled(2)
        }
    MAX-ACCESS  read-only
    STATUS  current
    DESCRIPTION
        "This is the DCBX TLV state of the LLDP port."
    ::= { lldpInfoPortEntry 21 }


lldpInfoTxTable OBJECT-TYPE
      SYNTAX SEQUENCE OF LldpInfoTxEntry
      MAX-ACCESS not-accessible
      STATUS  current
      DESCRIPTION
              "The table of LLDP Transmit State Machine Info."
      ::= { lldpInfo 2 }

lldpInfoTxEntry OBJECT-TYPE
      SYNTAX LldpInfoTxEntry
      MAX-ACCESS not-accessible
      STATUS current
      DESCRIPTION
              "LLDP Transmit State Machine Info."
      INDEX   { lldpInfoTxIndex }
      ::= { lldpInfoTxTable 1 }

LldpInfoTxEntry ::= SEQUENCE {
      lldpInfoTxIndex                PortNumber,
      lldpInfoTxState                INTEGER,
      lldpInfoTxLocalChanged         INTEGER,
      lldpInfoTxTTL                  Integer32,
      lldpInfoTxTxTTR                Integer32,
      lldpInfoTxDelayWhile           Integer32,
      lldpInfoTxShutdownWhile        Integer32,
      lldpInfoTxReinitDelay          Integer32,
      lldpInfoTxHoldMultiplier       Integer32,
      lldpInfoTxTransmitInterval     Integer32,
      lldpInfoTxTransmitDelay        Integer32,
      lldpInfoTxDMAC                 DisplayString
}

lldpInfoTxIndex OBJECT-TYPE
      SYNTAX  PortNumber
      MAX-ACCESS  read-only
      STATUS  current
      DESCRIPTION
          "The index of the row in LLDP Transmit State Machine info table."
      ::= { lldpInfoTxEntry 1 }

lldpInfoTxState OBJECT-TYPE
      SYNTAX  INTEGER {
          txLldpInitialize(1),
          txIdle(2),
          txShutdownFrame(3),
          txInfoFrame(4)
      }
      MAX-ACCESS  read-only
      STATUS  current
      DESCRIPTION
          "The transmit state of the port in LLDP Transmit State Machine."
      ::= { lldpInfoTxEntry 2 }

lldpInfoTxLocalChanged OBJECT-TYPE
      SYNTAX  INTEGER {
          true(1),
          false(2)
      }
      MAX-ACCESS  read-only
      STATUS  current
      DESCRIPTION
          "The somethingChangedLocal field of the port in LLDP Transmit 
	   State Machine."
      ::= { lldpInfoTxEntry 3 }

lldpInfoTxTTL OBJECT-TYPE
      SYNTAX  Integer32
      MAX-ACCESS  read-only
      STATUS  current
      DESCRIPTION
          "The txTTL timer of the port in LLDP Transmit State Machine."
      ::= { lldpInfoTxEntry 4 }

lldpInfoTxTxTTR OBJECT-TYPE
      SYNTAX  Integer32
      MAX-ACCESS  read-only
      STATUS  current
      DESCRIPTION
          "The txTTR timer of the port in LLDP Transmit State Machine."
      ::= { lldpInfoTxEntry 5 }

lldpInfoTxDelayWhile OBJECT-TYPE
      SYNTAX  Integer32
      MAX-ACCESS  read-only
      STATUS  current
      DESCRIPTION
          "The txDelayWhile timer of the port in LLDP Transmit State 
	   Machine."
      ::= { lldpInfoTxEntry 6 }

lldpInfoTxShutdownWhile OBJECT-TYPE
      SYNTAX  Integer32
      MAX-ACCESS  read-only
      STATUS  current
      DESCRIPTION
          "The txShutdownWhile timer of the port in LLDP Transmit State 
	   Machine."
      ::= { lldpInfoTxEntry 7 }

lldpInfoTxReinitDelay OBJECT-TYPE
      SYNTAX  Integer32
      MAX-ACCESS  read-only
      STATUS  current
      DESCRIPTION
          "The reinitDelay timer of the port in LLDP Transmit State 
	   Machine."
      ::= { lldpInfoTxEntry 8 }

lldpInfoTxHoldMultiplier OBJECT-TYPE
      SYNTAX  Integer32
      MAX-ACCESS  read-only
      STATUS  current
      DESCRIPTION
          "The msgTxHold timer of the port in LLDP Transmit State 
	   Machine."
      ::= { lldpInfoTxEntry 9 }

lldpInfoTxTransmitInterval OBJECT-TYPE
      SYNTAX  Integer32
      MAX-ACCESS  read-only
      STATUS  current
      DESCRIPTION
          "The msgTxInterval timer of the port in LLDP Transmit State 
	   Machine."
      ::= { lldpInfoTxEntry 10 }

lldpInfoTxTransmitDelay OBJECT-TYPE
      SYNTAX  Integer32
      MAX-ACCESS  read-only
      STATUS  current
      DESCRIPTION
          "The txDelay timer of the port in LLDP Transmit State Machine."
      ::= { lldpInfoTxEntry 11 }

lldpInfoTxDMAC OBJECT-TYPE
      SYNTAX  DisplayString (SIZE(1..128))
      MAX-ACCESS  read-only
      STATUS  current
      DESCRIPTION
          "The Destination MAC address of the LLDP remote devices.
	   Legend(possible values in DMAC column) :
           NB   - Nearest Bridge          - 01-80-C2-00-00-0E
           NnTB - Nearest non-TPMR Bridge - 01-80-C2-00-00-03
           NCB  - Nearest Customer Bridge - 01-80-C2-00-00-00"
      ::= { lldpInfoTxEntry 12 }

lldpInfoRxTable OBJECT-TYPE
      SYNTAX SEQUENCE OF LldpInfoRxEntry
      MAX-ACCESS not-accessible
      STATUS  current
      DESCRIPTION
              "The table of LLDP Receive State Machine Info."
      ::= { lldpInfo 3 }

lldpInfoRxEntry OBJECT-TYPE
      SYNTAX LldpInfoRxEntry
      MAX-ACCESS not-accessible
      STATUS current
      DESCRIPTION
              "LLDP Receive State Machine Info."
      INDEX   { lldpInfoRxIndex }
      ::= { lldpInfoRxTable 1 }

LldpInfoRxEntry ::= SEQUENCE {
      lldpInfoRxIndex                PortNumber,
      lldpInfoRxState                INTEGER,
      lldpInfoRxBadFrame             INTEGER,
      lldpInfoRxRcvFrame             INTEGER,
      lldpInfoRxRxInfoAge            INTEGER,
      lldpInfoRxRemoteChanged        INTEGER,
      lldpInfoRxTooManyNeighbors     INTEGER,
      lldpInfoRxSNMPNotify           INTEGER,
      lldpInfoRxRxTTL                Integer32,
      lldpInfoRxTooManyNeighborTimer Integer32,
      lldpInfoRxDMAC                 DisplayString
}

lldpInfoRxIndex OBJECT-TYPE
      SYNTAX  PortNumber
      MAX-ACCESS  read-only
      STATUS  current
      DESCRIPTION
          "The index of the row in LLDP Receive State Machine info table."
      ::= { lldpInfoRxEntry 1 }

lldpInfoRxState OBJECT-TYPE
      SYNTAX  INTEGER {
          lldpWaitPortOperational(1),
          deleteAgedInfo(2),
          rxLldpInitialize(3),
          rxWaitForFrame(4),
          rxFrame(5),
          deleteInfo(6),
          updateInfo(7)
      }
      MAX-ACCESS  read-only
      STATUS  current
      DESCRIPTION
          "The receive state of the port in LLDP Receive State Machine."
      ::= { lldpInfoRxEntry 2 }

lldpInfoRxBadFrame OBJECT-TYPE
      SYNTAX  INTEGER {
          true(1),
          false(2)
      }
      MAX-ACCESS  read-only
      STATUS  current
      DESCRIPTION
          "The badFrame field of the port in LLDP Receive State Machine."
      ::= { lldpInfoRxEntry 3 }

lldpInfoRxRcvFrame OBJECT-TYPE
      SYNTAX  INTEGER {
          true(1),
          false(2)
      }
      MAX-ACCESS  read-only
      STATUS  current
      DESCRIPTION
          "The rcvFrame field of the port in LLDP Receive State Machine."
      ::= { lldpInfoRxEntry 4 }

lldpInfoRxRxInfoAge OBJECT-TYPE
      SYNTAX  INTEGER {
          true(1),
          false(2)
      }
      MAX-ACCESS  read-only
      STATUS  current
      DESCRIPTION
          "The rxInfoAge field of the port in LLDP Receive State Machine."
      ::= { lldpInfoRxEntry 5 }

lldpInfoRxRemoteChanged OBJECT-TYPE
      SYNTAX  INTEGER {
          true(1),
          false(2)
      }
      MAX-ACCESS  read-only
      STATUS  current
      DESCRIPTION
          "The somethingChangedRemote field of the port in LLDP Receive 
	   State Machine."
      ::= { lldpInfoRxEntry 6 }

lldpInfoRxTooManyNeighbors OBJECT-TYPE
      SYNTAX  INTEGER {
          true(1),
          false(2)
      }
      MAX-ACCESS  read-only
      STATUS  current
      DESCRIPTION
          "The tooManyNeighbors field of the port in LLDP Receive 
	   State Machine."
      ::= { lldpInfoRxEntry 7 }

lldpInfoRxSNMPNotify OBJECT-TYPE
      SYNTAX  INTEGER {
          true(1),
          false(2)
      }
      MAX-ACCESS  read-only
      STATUS  current
      DESCRIPTION
          "The tooManyNeighbors field of the port in LLDP Receive 
	   State Machine."
      ::= { lldpInfoRxEntry 8 }

lldpInfoRxRxTTL OBJECT-TYPE
      SYNTAX  Integer32
      MAX-ACCESS  read-only
      STATUS  current
      DESCRIPTION
          "The rxTTL timer of the port in LLDP Receive State Machine."
      ::= { lldpInfoRxEntry 9 }

lldpInfoRxTooManyNeighborTimer OBJECT-TYPE
      SYNTAX  Integer32
      MAX-ACCESS  read-only
      STATUS  current
      DESCRIPTION
          "The tooManyNeighborsTimer timer of the port in LLDP Receive State 
	   Machine."
      ::= { lldpInfoRxEntry 10 }

lldpInfoRxDMAC OBJECT-TYPE
      SYNTAX  DisplayString (SIZE(1..128))
      MAX-ACCESS  read-only
      STATUS  current
      DESCRIPTION
          "The Destination MAC address of the LLDP remote devices.
	   Legend(possible values in DMAC column) :
           NB   - Nearest Bridge          - 01-80-C2-00-00-0E
           NnTB - Nearest non-TPMR Bridge - 01-80-C2-00-00-03
           NCB  - Nearest Customer Bridge - 01-80-C2-00-00-00"
      ::= { lldpInfoRxEntry 11 }

lldpInfoRemoteDevicesTable OBJECT-TYPE
      SYNTAX SEQUENCE OF LldpInfoRemoteDevicesEntry
      MAX-ACCESS not-accessible
      STATUS  current
      DESCRIPTION
              "The table of LLDP remote devices Info."
      ::= { lldpInfo 4 }

lldpInfoRemoteDevicesEntry OBJECT-TYPE
      SYNTAX LldpInfoRemoteDevicesEntry
      MAX-ACCESS not-accessible
      STATUS current
      DESCRIPTION
              "LLDP remote devices Info."
      INDEX   { lldpInfoRemoteDevicesIndex }
      ::= { lldpInfoRemoteDevicesTable 1 }

LldpInfoRemoteDevicesEntry ::= SEQUENCE {
      lldpInfoRemoteDevicesIndex                INTEGER,
      lldpInfoRemoteDevicesRemoteTTL            Integer32,
      lldpInfoRemoteDevicesRxChanges            INTEGER,
      lldpInfoRemoteDevicesLocalPort            DisplayString,
      lldpInfoRemoteDevicesChassisSubtype       INTEGER,
      lldpInfoRemoteDevicesChassisId            DisplayString,
      lldpInfoRemoteDevicesPortSubtype          INTEGER,
      lldpInfoRemoteDevicesPortId               DisplayString,
      lldpInfoRemoteDevicesSystemName           DisplayString,
      lldpInfoRemoteDevicesSystemDescription    DisplayString,
      lldpInfoRemoteDevicesPortDescription      DisplayString,
      lldpInfoRemoteDevicesSystemCapSupported   DisplayString,
      lldpInfoRemoteDevicesSystemCapEnabled     DisplayString,
      lldpInfoRemoteDMAC                        DisplayString
}

lldpInfoRemoteDevicesIndex OBJECT-TYPE
      SYNTAX  INTEGER  (1..256)
      MAX-ACCESS  read-only
      STATUS  current
      DESCRIPTION
          "The index of the row in LLDP remote devices info table."
      ::= { lldpInfoRemoteDevicesEntry 1 }

-- lldpInfoMsapMagicNumber OBJECT-TYPE
--       SYNTAX  Integer32
--       MAX-ACCESS  read-only
--       STATUS  current
--       DESCRIPTION
--           "The magic number of the LLDP MSAP entry."
--       ::= { lldpInfoRemoteDevicesEntry 2 }

lldpInfoRemoteDevicesRemoteTTL OBJECT-TYPE
      SYNTAX  Integer32
      MAX-ACCESS  read-only
      STATUS  current
      DESCRIPTION
          "The remote TTL of the LLDP remote devices entry."
      ::= { lldpInfoRemoteDevicesEntry 3 }

lldpInfoRemoteDevicesRxChanges OBJECT-TYPE
      SYNTAX  INTEGER {
          true(1),
          false(2)
      }
      MAX-ACCESS  read-only
      STATUS  current
      DESCRIPTION
          "The rxChanges field of the LLDP remote devices entry."
      ::= { lldpInfoRemoteDevicesEntry 4 }

lldpInfoRemoteDevicesLocalPort OBJECT-TYPE
      SYNTAX  DisplayString (SIZE(1..128))
      MAX-ACCESS  read-only
      STATUS  current
      DESCRIPTION
          "The local port alias of the LLDP remote devices entry."
      ::= { lldpInfoRemoteDevicesEntry 5 }

lldpInfoRemoteDevicesChassisSubtype OBJECT-TYPE
      SYNTAX  INTEGER {
          chassisComponent(1),
          interfaceAlias(2),
          portComponent(3),
          macAddress(4),
          networkAddress(5),
          interfaceName(6),
          locallyAssigned(7)
      }
      MAX-ACCESS  read-only
      STATUS  current
      DESCRIPTION
          "The chassis ID subtype of the LLDP remote devices entry."
      ::= { lldpInfoRemoteDevicesEntry 6 }

lldpInfoRemoteDevicesChassisId OBJECT-TYPE
      SYNTAX  DisplayString (SIZE(1..255))
      MAX-ACCESS  read-only
      STATUS  current
      DESCRIPTION
          "The chassis ID of the LLDP remote devices entry."
      ::= { lldpInfoRemoteDevicesEntry 7 }

lldpInfoRemoteDevicesPortSubtype OBJECT-TYPE
      SYNTAX  INTEGER {
          interfaceAlias(1),
          portComponent(2),
          macAddress(3),
          networkAddress(4),
          interfaceName(5),
          agentCircuitId(6),
          locallyAssigned(7)
      }
      MAX-ACCESS  read-only
      STATUS  current
      DESCRIPTION
          "The port ID subtype of the LLDP remote devices entry."
      ::= { lldpInfoRemoteDevicesEntry 8 }

lldpInfoRemoteDevicesPortId OBJECT-TYPE
      SYNTAX  DisplayString (SIZE(1..255))
      MAX-ACCESS  read-only
      STATUS  current
      DESCRIPTION
          "The port ID of the LLDP remote devices entry."
      ::= { lldpInfoRemoteDevicesEntry 9 }

lldpInfoRemoteDevicesSystemName OBJECT-TYPE
      SYNTAX  DisplayString (SIZE(0..255))
      MAX-ACCESS  read-only
      STATUS  current
      DESCRIPTION
          "The system name of the LLDP remote devices entry."
      ::= { lldpInfoRemoteDevicesEntry 10 }

lldpInfoRemoteDevicesSystemDescription OBJECT-TYPE
      SYNTAX  DisplayString (SIZE(0..255))
      MAX-ACCESS  read-only
      STATUS  current
      DESCRIPTION
          "The system description of the LLDP remote devices entry."
      ::= { lldpInfoRemoteDevicesEntry 11 }

lldpInfoRemoteDevicesPortDescription OBJECT-TYPE
      SYNTAX  DisplayString (SIZE(0..255))
      MAX-ACCESS  read-only
      STATUS  current
      DESCRIPTION
          "The port description of the LLDP remote devices entry."
      ::= { lldpInfoRemoteDevicesEntry 12 }

lldpInfoRemoteDevicesSystemCapSupported OBJECT-TYPE
      SYNTAX  DisplayString (SIZE(0..64))
      MAX-ACCESS  read-only
      STATUS  current
      DESCRIPTION
          "The supported system capabilities of the LLDP remote devices entry."
      ::= { lldpInfoRemoteDevicesEntry 13 }

lldpInfoRemoteDevicesSystemCapEnabled OBJECT-TYPE
      SYNTAX  DisplayString (SIZE(0..64))
      MAX-ACCESS  read-only
      STATUS  current
      DESCRIPTION
          "The enabled system capabilities of the LLDP remote devices entry."
      ::= { lldpInfoRemoteDevicesEntry 14 }

lldpInfoRemoteDMAC OBJECT-TYPE
      SYNTAX  DisplayString (SIZE(1..128))
      MAX-ACCESS  read-only
      STATUS  current
      DESCRIPTION
          "The Destination MAC address of the LLDP remote devices.
	   Legend(possible values in DMAC column) :
           NB   - Nearest Bridge          - 01-80-C2-00-00-0E
           NnTB - Nearest non-TPMR Bridge - 01-80-C2-00-00-03
           NCB  - Nearest Customer Bridge - 01-80-C2-00-00-00"
      ::= { lldpInfoRemoteDevicesEntry 15 }
--
-- lldpInfoRemoteDevicesManAddrTable : Management addresses of remote system
--

lldpInfoRemoteDevicesManAddrTable OBJECT-TYPE
    SYNTAX  SEQUENCE OF LldpInfoRemoteDevicesManAddrEntry
    MAX-ACCESS not-accessible
    STATUS  current
    DESCRIPTION
        "The table of LLDP remote devices management address Info."
    ::= { lldpInfo 5 }

lldpInfoRemoteDevicesManAddrEntry OBJECT-TYPE
    SYNTAX      LldpInfoRemoteDevicesManAddrEntry
    MAX-ACCESS not-accessible
    STATUS      current
    DESCRIPTION
        "LLDP remote devices management address Info."
    INDEX       { lldpInfoRemoteDevicesIndex,
                  lldpInfoRemoteDevicesManAddrSubtype,
                  lldpInfoRemoteDevicesManAddr
    }
    ::= { lldpInfoRemoteDevicesManAddrTable 1 }

LldpInfoRemoteDevicesManAddrEntry ::= SEQUENCE {
    lldpInfoRemoteDevicesManAddrSubtype         INTEGER,
    lldpInfoRemoteDevicesManAddr                DisplayString,
    lldpInfoRemoteDevicesManAddrIfSubtype       INTEGER,
    lldpInfoRemoteDevicesManAddrIfId            Integer32,
    lldpInfoRemoteDevicesManAddrOID             DisplayString
}

lldpInfoRemoteDevicesManAddrSubtype OBJECT-TYPE
      SYNTAX  INTEGER {
	  other(0),
	  ipV4(1),
	  ipV6(2),
	  nsap(3),
	  hdlc(4),
	  bbn1822(5),
	  all802(6),
	  e163(7),
	  e164(8),
	  f69(9),
	  x121(10),
	  ipx(11),
	  appletalk(12),
	  decnetIV(13),
	  banyanVines(14),
	  e164withNsap(15),
	  dns(16),
	  distinguishedname(17),
	  asnumber(18),
	  xtpoveripv4(19),
	  xtpoveripv6(20),
	  xtpnativemodextp(21),
	  reserved(65535)
      }
      MAX-ACCESS  read-only
      STATUS  current
      DESCRIPTION
          "The management address subtype of the LLDP remote devices entry."
      ::= { lldpInfoRemoteDevicesManAddrEntry 1 }

lldpInfoRemoteDevicesManAddr OBJECT-TYPE
      SYNTAX  DisplayString (SIZE(1..64))
      MAX-ACCESS  read-only
      STATUS  current
      DESCRIPTION
          "The management address of the LLDP remote devices entry."
      ::= { lldpInfoRemoteDevicesManAddrEntry 2 }

lldpInfoRemoteDevicesManAddrIfSubtype OBJECT-TYPE
      SYNTAX  INTEGER {
          unknown(1),
          ifIndex(2),
          systemPortNumber(3)
      }
      MAX-ACCESS  read-only
      STATUS  current
      DESCRIPTION
          "The interface numbering subtype of the LLDP remote devices 
	   management address entry."
      ::= { lldpInfoRemoteDevicesManAddrEntry 3 }

lldpInfoRemoteDevicesManAddrIfId OBJECT-TYPE
      SYNTAX  Integer32
      MAX-ACCESS  read-only
      STATUS  current
      DESCRIPTION
          "The interface number of the LLDP remote devices management address 
	   entry."
      ::= { lldpInfoRemoteDevicesManAddrEntry 4 }

lldpInfoRemoteDevicesManAddrOID OBJECT-TYPE
      SYNTAX  DisplayString (SIZE(0..128))
      MAX-ACCESS  read-only
      STATUS  current
      DESCRIPTION
          "The object identifier of the LLDP remote devices management address 
	   entry."
      ::= { lldpInfoRemoteDevicesManAddrEntry 5 }

lldpClearMsap OBJECT-TYPE
    SYNTAX INTEGER {
        ok(0),
        clearMsap(1)
    }
    MAX-ACCESS read-write
    STATUS current
    DESCRIPTION
        "Clear LLDP remote devices information when setting clearMsap(1).
         When read, ok(0) is always returned."
    ::= { lldpInfo 6 }

--
--  } End of LLDP Info
--

--
--  { UDLD
--

udldInfoPortTable  OBJECT-TYPE
      SYNTAX  SEQUENCE OF UdldInfoPortEntry
      MAX-ACCESS  not-accessible
      STATUS  current
      DESCRIPTION
          "The table of UDLD port info."
      ::= { udldInfo 1 }

udldInfoPortEntry  OBJECT-TYPE
      SYNTAX  UdldInfoPortEntry
      MAX-ACCESS  not-accessible
      STATUS  current
      DESCRIPTION
          "A row inside UDLD port info table."
      INDEX  { udldInfoPortIndex }
      ::= { udldInfoPortTable 1 }

UdldInfoPortEntry ::= SEQUENCE
{     udldInfoPortIndex               PortNumber
,     udldInfoPortConfig              INTEGER
,     udldInfoPortMode                INTEGER
,     udldInfoPortLink                INTEGER
,     udldInfoPortOperationalStatus   INTEGER
,     udldInfoPortBidirectionalStatus INTEGER
,     udldInfoPortInterval            INTEGER
,     udldInfoPortTimeout             INTEGER
,     udldInfoPortNeighborCount       INTEGER
}

udldInfoPortIndex  OBJECT-TYPE
      SYNTAX  PortNumber
      MAX-ACCESS  read-only
      STATUS  current
      DESCRIPTION
          "The index of the row in UDLD port configuration table."
      ::= { udldInfoPortEntry 1 }

udldInfoPortConfig OBJECT-TYPE
      SYNTAX  INTEGER
      {   enabled(1)
      ,   disabled(2)
      }
      MAX-ACCESS  read-only
      STATUS  current
      DESCRIPTION
          "The Config field of the port in UDLD port info table.
      Shows the administative state of the current port."
      ::= { udldInfoPortEntry 2 }
 
udldInfoPortMode OBJECT-TYPE
      SYNTAX  INTEGER
      {   aggresive(1)
      ,   normal(2)
      }
      MAX-ACCESS  read-only
      STATUS  current
      DESCRIPTION
          "The Mode field of the port in UDLD info port table.
      Shows the udld administrative mode for the current port."
      ::= { udldInfoPortEntry 3 }

udldInfoPortLink OBJECT-TYPE
      SYNTAX  INTEGER
      {   up(1)
      ,   down(2)
      }
      MAX-ACCESS  read-only
      STATUS  current
      DESCRIPTION
          "The Link field of the port in UDLD info port table.
      Shows the state of the link associated with the port."
      ::= { udldInfoPortEntry 4 }

udldInfoPortOperationalStatus OBJECT-TYPE
      SYNTAX  INTEGER
      {   init(1)
      ,   inactive(2)
      ,   linkup(3)
      ,   advertisement(4)
      ,   detection(5)
      ,   extDetection(6)
      ,   shutdown(7)
      }
      MAX-ACCESS  read-only
      STATUS  current
      DESCRIPTION
          "The OperationalStatus field of the port in UDLD info port table.
      Contains the udld operational state for the current port."
      ::= { udldInfoPortEntry 5 }

udldInfoPortBidirectionalStatus OBJECT-TYPE
      SYNTAX  INTEGER
      {   unknown(1)
      ,   unidirectional(2)
      ,   bidirectional(3)
      ,   loop(4)
      ,   neighborMismatch(5)
      }
      MAX-ACCESS  read-only
      STATUS  current
      DESCRIPTION
            "The BidirectionalStatus field of the port in UDLD info port table.
      Contains the udld bidirectional state for the current port."
      ::= { udldInfoPortEntry 6 }

udldInfoPortInterval OBJECT-TYPE
      SYNTAX  INTEGER
      MAX-ACCESS  read-only
      STATUS  current
      DESCRIPTION
            "The Interval field of the port in UDLD info port table.
      The duration, measured in seconds, of the interval during which
      UDLD probes are sent, after the linkup or detection phases.
      Its time unit is 1 second."
      ::= { udldInfoPortEntry 7 }

udldInfoPortTimeout OBJECT-TYPE
      SYNTAX  INTEGER
      MAX-ACCESS  read-only
      STATUS  current
      DESCRIPTION
            "The Timeout field of the port in UDLD info port table.
      Length of the detection phase, measured in seconds."
      ::= { udldInfoPortEntry 8}

udldInfoPortNeighborCount OBJECT-TYPE
      SYNTAX  INTEGER
      MAX-ACCESS  read-only
      STATUS  current
      DESCRIPTION
            "The Neighbor field of the port in UDLD info port table.
      Contains the number of udld neighbors for the current port."
      ::= { udldInfoPortEntry 9 }

udldInfoNeighborTable  OBJECT-TYPE
      SYNTAX  SEQUENCE OF UdldInfoNeighborEntry
      MAX-ACCESS  not-accessible
      STATUS  current
      DESCRIPTION
          "The table of UDLD port neighbor info."
      ::= { udldInfo 2 }

udldInfoNeighborEntry  OBJECT-TYPE
      SYNTAX  UdldInfoNeighborEntry
      MAX-ACCESS  not-accessible
      STATUS  current
      DESCRIPTION
          "A row inside UDLD port info table."
      INDEX  { udldInfoNeighborLocalPortIndex, udldInfoNeighborIndex }
      ::= { udldInfoNeighborTable 1 }

UdldInfoNeighborEntry ::= SEQUENCE
{     udldInfoNeighborLocalPortIndex   PortNumber
,     udldInfoNeighborIndex            Integer32
,     udldInfoNeighborExpiration       INTEGER
,     udldInfoNeighborDeviceName       DisplayString
,     udldInfoNeighborDeviceID         DisplayString
,     udldInfoNeighborPortID           DisplayString
}

udldInfoNeighborLocalPortIndex  OBJECT-TYPE
      SYNTAX  PortNumber
      MAX-ACCESS  read-only
      STATUS  current
      DESCRIPTION
          "The index of the port for which neighbor information
      will be returned."
      ::= { udldInfoNeighborEntry 1 }

udldInfoNeighborIndex OBJECT-TYPE
      SYNTAX  Integer32
      MAX-ACCESS  read-only
      STATUS  current
      DESCRIPTION
          "The index of the target neighbor among the port neighbors."
      ::= { udldInfoNeighborEntry 2 }

udldInfoNeighborExpiration  OBJECT-TYPE
      SYNTAX  INTEGER
      MAX-ACCESS  read-only
      STATUS  current
      DESCRIPTION
          "Hold time for the given neighbor."
      ::= { udldInfoNeighborEntry 3 }
 
udldInfoNeighborDeviceName OBJECT-TYPE
      SYNTAX  DisplayString
      MAX-ACCESS  read-only
      STATUS  current
      DESCRIPTION
          "Device name reported by neigbor."
      ::= { udldInfoNeighborEntry 4 }
 
udldInfoNeighborDeviceID OBJECT-TYPE
      SYNTAX  DisplayString
      MAX-ACCESS  read-only
      STATUS  current
      DESCRIPTION
          "Device ID reported by neigbor."
      ::= { udldInfoNeighborEntry 5 }
 
udldInfoNeighborPortID OBJECT-TYPE
      SYNTAX  DisplayString
      MAX-ACCESS  read-only
      STATUS  current
      DESCRIPTION
          "Port ID reported by neigbor."
      ::= { udldInfoNeighborEntry 6 }
--
--  } End of UDLD Info
--

-- FDB
fdbCurCfgStaticTable OBJECT-TYPE
    SYNTAX  SEQUENCE OF FdbCurCfgStaticEntry
    MAX-ACCESS  not-accessible
    STATUS  current
    DESCRIPTION
        "The table of FDB static entries."
    ::= { fdb 2 }

fdbCurCfgStaticEntry OBJECT-TYPE
    SYNTAX  FdbCurCfgStaticEntry
    MAX-ACCESS  not-accessible
    STATUS  current
    DESCRIPTION
        "A row in the fdb table."
    INDEX   { fdbCurCfgEntryIndex }
    ::= { fdbCurCfgStaticTable 1 }

FdbCurCfgStaticEntry ::= SEQUENCE {
    fdbCurCfgEntryIndex              Integer32,
    fdbCurCfgVlan                    Integer32,
    fdbCurCfgPort                    PortNumber,
    fdbCurCfgMac                     PhysAddress
    ,fdbCurCfgTrunk                   Integer32
    ,fdbCurCfgAdminkey                Integer32
    }

fdbCurCfgEntryIndex OBJECT-TYPE
    SYNTAX  Integer32
    MAX-ACCESS  read-only
    STATUS  current
    DESCRIPTION
        "The fdb entry index"
    ::= { fdbCurCfgStaticEntry 1 }

fdbCurCfgVlan OBJECT-TYPE
    SYNTAX  Integer32
    MAX-ACCESS  read-only
    STATUS  current
    DESCRIPTION
        "Add vlan for fdb entry index"
    ::= { fdbCurCfgStaticEntry 2 }

fdbCurCfgPort OBJECT-TYPE
    SYNTAX  PortNumber
    MAX-ACCESS   read-only
    STATUS  current
    DESCRIPTION
        "The MAC address port number."
    ::= { fdbCurCfgStaticEntry 3 }

fdbCurCfgMac OBJECT-TYPE
    SYNTAX  PhysAddress
    MAX-ACCESS  read-only
    STATUS  current
    DESCRIPTION
        "Add a fdb entry."
    ::= { fdbCurCfgStaticEntry 4 }

fdbCurCfgTrunk OBJECT-TYPE
    SYNTAX  Integer32 
    MAX-ACCESS   read-only
    STATUS  current
    DESCRIPTION
        "The MAC address trunk number."
    ::= { fdbCurCfgStaticEntry 5 }

fdbCurCfgAdminkey OBJECT-TYPE
    SYNTAX       Integer32 
    MAX-ACCESS   read-only
    STATUS  current
    DESCRIPTION
        "The MAC address LACP trunk adminkey."
    ::= { fdbCurCfgStaticEntry 6 }

fdbNewCfgStaticTable OBJECT-TYPE
    SYNTAX  SEQUENCE OF FdbNewCfgStaticEntry
    MAX-ACCESS  not-accessible
    STATUS  current
    DESCRIPTION
        "The table of FDB static entries."
    ::= { fdb 3 }

fdbNewCfgStaticEntry OBJECT-TYPE
    SYNTAX  FdbNewCfgStaticEntry
    MAX-ACCESS  not-accessible
    STATUS  current
    DESCRIPTION
        "A row in the fdb table."
    INDEX   { fdbNewCfgEntryIndex }
    ::= { fdbNewCfgStaticTable 1 }

FdbNewCfgStaticEntry ::= SEQUENCE {
    fdbNewCfgEntryIndex			Integer32,
    fdbNewCfgAddVlan	                Integer32,
    fdbNewCfgAddPort	                PortNumber,
    fdbNewCfgAddTrunk                   Integer32,
    fdbNewCfgAddAdminkey                Integer32,
    fdbNewCfgAddMac			PhysAddress,
    fdbNewCfgDelStaticEntry		INTEGER
    }

fdbNewCfgEntryIndex OBJECT-TYPE 
    SYNTAX  Integer32 
    MAX-ACCESS  read-only 
    STATUS  current 
    DESCRIPTION 
        "The fdb entry index" 
    ::= { fdbNewCfgStaticEntry 1 }

fdbNewCfgAddVlan OBJECT-TYPE 
    SYNTAX  Integer32 
    MAX-ACCESS  read-create
    STATUS  current 
    DESCRIPTION 
        "Add vlan for fdb entry index" 
    ::= { fdbNewCfgStaticEntry 2 }

fdbNewCfgAddPort OBJECT-TYPE
    SYNTAX  PortNumber
    MAX-ACCESS   read-create
    STATUS  current
    DESCRIPTION
        "The MAC address port number." 
    ::= { fdbNewCfgStaticEntry 3 }

fdbNewCfgAddMac OBJECT-TYPE
    SYNTAX  PhysAddress
    MAX-ACCESS  read-create
    STATUS  current
    DESCRIPTION
        "Add a fdb entry, ex:0x00 0x01 0x02 0x03 0x04 0x05"
    ::= { fdbNewCfgStaticEntry 4 }

fdbNewCfgDelStaticEntry OBJECT-TYPE
    SYNTAX  INTEGER {
        other(1),
        delete(2)
        }
    MAX-ACCESS  read-create
    STATUS  current
    DESCRIPTION
        "When set to the value of 2 (delete), the entire row is deleted.
         When read, other(1) is returned. Setting the value to anything
         other than 2(delete) has no effect on the state of the row."
    ::= { fdbNewCfgStaticEntry 5 }

fdbNewCfgAddTrunk OBJECT-TYPE
    SYNTAX  Integer32 
    MAX-ACCESS   read-create
    STATUS  current
    DESCRIPTION
        "The MAC address trunk number."
    ::= { fdbNewCfgStaticEntry 6 }

fdbNewCfgAddAdminkey OBJECT-TYPE
    SYNTAX  Integer32 
    MAX-ACCESS   read-create
    STATUS  current
    DESCRIPTION
        "The MAC address LACP trunk adminkey."
    ::= { fdbNewCfgStaticEntry 7 }

-- Multicast FDB

mcastFdbCurCfgTable OBJECT-TYPE
    SYNTAX  SEQUENCE OF McastFdbCurCfgEntry
    MAX-ACCESS  not-accessible
    STATUS  current
    DESCRIPTION
        "The table of multicast FDB static entries."
    ::= { fdb 8 }

mcastFdbCurCfgEntry OBJECT-TYPE
    SYNTAX  McastFdbCurCfgEntry
    MAX-ACCESS  not-accessible
    STATUS  current
    DESCRIPTION
        "A row in the multicast fdb table."
    INDEX   { mcastFdbCurCfgEntryIndex }
    ::= { mcastFdbCurCfgTable 1 }

McastFdbCurCfgEntry ::= SEQUENCE {
    mcastFdbCurCfgEntryIndex              Integer32,
    mcastFdbCurCfgVlan                    Integer32,
    mcastFdbCurCfgPorts                   PortNumber,
    mcastFdbCurCfgMac                     MacAddress 
    }

mcastFdbCurCfgEntryIndex OBJECT-TYPE
    SYNTAX  Integer32
    MAX-ACCESS  read-only
    STATUS  current
    DESCRIPTION
        "The multicast fdb entry index"
    ::= { mcastFdbCurCfgEntry 1 }

mcastFdbCurCfgVlan OBJECT-TYPE
    SYNTAX  Integer32
    MAX-ACCESS  read-only
    STATUS  current
    DESCRIPTION
        "Add vlan for multicast fdb entry index"
    ::= { mcastFdbCurCfgEntry 2 }

mcastFdbCurCfgPorts OBJECT-TYPE
    SYNTAX  PortNumber
    MAX-ACCESS   read-only
    STATUS  current
    DESCRIPTION
        "The multicast MAC address port list.  The ports are presented in bitmap format.
         in receiving order:

             OCTET 1  OCTET 2  .....
             xxxxxxxx xxxxxxxx .....
             ||    || |_ port 8
             ||    ||
             ||    ||___ port 7
             ||    |____ port 6
             ||      .    .   .
             ||_________ port 1
             |__________ reserved

         where x : 1 - The represented port belongs to the multicast MAC address.
                   0 - The represented port does not belong to the multicast MAC address."
    ::= { mcastFdbCurCfgEntry 3 }

mcastFdbCurCfgMac OBJECT-TYPE
    SYNTAX  MacAddress 
    MAX-ACCESS  read-only
    STATUS  current
    DESCRIPTION
        "Add a multicast fdb entry."
    ::= { mcastFdbCurCfgEntry 4 }

mcastFdbNewCfgTable OBJECT-TYPE
    SYNTAX  SEQUENCE OF McastFdbNewCfgEntry
    MAX-ACCESS  not-accessible
    STATUS  current
    DESCRIPTION
        "The table of multicast FDB static entries."
    ::= { fdb 9 }

mcastFdbNewCfgEntry OBJECT-TYPE
    SYNTAX  McastFdbNewCfgEntry
    MAX-ACCESS  not-accessible
    STATUS  current
    DESCRIPTION
        "A row in the multicast fdb table."
    INDEX   { mcastFdbNewCfgEntryIndex }
    ::= { mcastFdbNewCfgTable 1 }

McastFdbNewCfgEntry ::= SEQUENCE {
    mcastFdbNewCfgEntryIndex			Integer32,
    mcastFdbNewCfgAddVlan	                Integer32,
    mcastFdbNewCfgPorts                         OCTET STRING, 
    mcastFdbNewCfgAddPort	                PortNumber,
    mcastFdbNewCfgRemPort                       PortNumber,
    mcastFdbNewCfgAddMac			MacAddress,
    mcastFdbNewCfgDelStaticEntry       		INTEGER
    }

mcastFdbNewCfgEntryIndex OBJECT-TYPE 
    SYNTAX  Integer32 
    MAX-ACCESS  read-only 
    STATUS  current 
    DESCRIPTION 
        "The multicast fdb entry index" 
    ::= { mcastFdbNewCfgEntry 1 }

mcastFdbNewCfgAddVlan OBJECT-TYPE 
    SYNTAX  Integer32 
    MAX-ACCESS  read-create
    STATUS  current 
    DESCRIPTION 
        "Add vlan for multicast fdb entry index" 
    ::= { mcastFdbNewCfgEntry 2 }

mcastFdbNewCfgPorts OBJECT-TYPE
    SYNTAX  OCTET STRING 
    MAX-ACCESS   read-only
    STATUS  current
    DESCRIPTION
        "The multicast MAC address port list.  The ports are presented in bitmap format.
         in receiving order:

	     OCTET 1  OCTET 2  .....
             xxxxxxxx xxxxxxxx ..... 
             ||    || |_ port 8
             ||    ||  
             ||    ||___ port 7
             ||    |____ port 6
             ||      .    .   .
             ||_________ port 1
             |__________ reserved

         where x : 1 - The represented port belongs to the multicast MAC address. 
	           0 - The represented port does not belong to the multicast MAC address."
    ::= { mcastFdbNewCfgEntry 3 }

mcastFdbNewCfgAddPort OBJECT-TYPE
    SYNTAX  PortNumber
    MAX-ACCESS   read-create
    STATUS  current
    DESCRIPTION
        "The multicast MAC address port number to be added.  A '0'
         value is returned when read." 
    ::= { mcastFdbNewCfgEntry 4 }

mcastFdbNewCfgRemPort OBJECT-TYPE
    SYNTAX  PortNumber
    MAX-ACCESS   read-create
    STATUS  current
    DESCRIPTION
        "The multicast MAC address port number to be removed.  A '0'
         value is returned when read."
    ::= { mcastFdbNewCfgEntry 5 }

mcastFdbNewCfgAddMac OBJECT-TYPE
    SYNTAX  MacAddress 
    MAX-ACCESS  read-create
    STATUS  current
    DESCRIPTION
        "Add a multicast fdb entry, ex:0x00 0x01 0x02 0x03 0x04 0x05"
    ::= { mcastFdbNewCfgEntry 6 }

mcastFdbNewCfgDelStaticEntry OBJECT-TYPE
    SYNTAX  INTEGER {
        other(1),
        delete(2)
        }
    MAX-ACCESS  read-create
    STATUS  current
    DESCRIPTION
        "When set to the value of 2 (delete), the entire row is deleted.
         When read, other(1) is returned. Setting the value to anything
         other than 2(delete) has no effect on the state of the row."
    ::= { mcastFdbNewCfgEntry 7 }


--dot1x


dot1xCurStatus OBJECT-TYPE
    SYNTAX INTEGER {
	enable(0),
        disable(1)
	}
    MAX-ACCESS read-only
    STATUS current
    DESCRIPTION
	"  Dot1x  status    " 
    ::= { dot1x 1 }

dot1xNewStatus OBJECT-TYPE
    SYNTAX INTEGER {
	enable(0),
        disable(1)
	}
    MAX-ACCESS read-write
    STATUS current
    DESCRIPTION
	"  Dot1x  status    " 
    ::= { dot1x 2 }

dot1xCurCfgPortTable OBJECT-TYPE
    SYNTAX SEQUENCE OF Dot1xCurCfgPortEntry
    MAX-ACCESS not-accessible
    STATUS current
    DESCRIPTION
      "The table of 8021x configuration in the Current_config."
    ::= { dot1x 3 }

dot1xNewCfgPortTable OBJECT-TYPE
    SYNTAX SEQUENCE OF Dot1xNewCfgPortEntry
    MAX-ACCESS not-accessible
    STATUS current
    DESCRIPTION
      "The table of 8021x configuration in the new_config."
    ::= { dot1x 4 }

dot1xCurCfgPortEntry OBJECT-TYPE
    SYNTAX Dot1xCurCfgPortEntry
    MAX-ACCESS not-accessible
    STATUS current
    DESCRIPTION
      "Information about 8021x Port Config"
    INDEX { dot1xCurCfgPortIndex }
    ::= { dot1xCurCfgPortTable 1 }
 
Dot1xCurCfgPortEntry ::= SEQUENCE {
    dot1xCurCfgPortIndex                PortNumber,	
    dot1xCurCfgPortMode                 INTEGER,
    dot1xCurCfgPortQtPeriod             INTEGER,
    dot1xCurCfgPortTxPeriod             INTEGER,
    dot1xCurCfgPortSupTmout		INTEGER,
    dot1xCurCfgPortSrvTmout             INTEGER,
    dot1xCurCfgPortMaxRq 		INTEGER,
    dot1xCurCfgPortRaPeriod		INTEGER,
    dot1xCurCfgPortReAuth		INTEGER 
    ,
    dot1xCurCfgPortVlanAssign		INTEGER
    }
 
dot1xCurCfgPortIndex OBJECT-TYPE
    SYNTAX PortNumber
    MAX-ACCESS read-only
    STATUS current
    DESCRIPTION
	"The 8021x Port number for which the table is related."
    ::= { dot1xCurCfgPortEntry 1}

dot1xCurCfgPortMode OBJECT-TYPE
    SYNTAX INTEGER {
      forceUnauth(0),
      auto(1),
      forceAuth(2)	
	}
    MAX-ACCESS read-only
    STATUS current
    DESCRIPTION
	" Port authenticaton mode
	  forceUnauth(0),
          auto(1),
          forceAuth(2)
	    " 
    ::= { dot1xCurCfgPortEntry 2 }

dot1xCurCfgPortQtPeriod OBJECT-TYPE
    SYNTAX INTEGER (0..65535)
    MAX-ACCESS read-only
    STATUS current
    DESCRIPTION
	"Quiet period (0-65535) " 
    ::= { dot1xCurCfgPortEntry 3 }

dot1xCurCfgPortTxPeriod OBJECT-TYPE
    SYNTAX INTEGER (1..65535)
    MAX-ACCESS read-only
    STATUS current
    DESCRIPTION
	" Tx Period     " 
    ::= { dot1xCurCfgPortEntry 4 }

dot1xCurCfgPortSupTmout OBJECT-TYPE
    SYNTAX INTEGER (1..65535)
    MAX-ACCESS read-only
    STATUS current
    DESCRIPTION
	"   Supplicant timeout (1..65535)  " 
    ::= { dot1xCurCfgPortEntry 5 }

dot1xCurCfgPortSrvTmout OBJECT-TYPE
    SYNTAX INTEGER (1..65535)
    MAX-ACCESS read-only
    STATUS current
    DESCRIPTION
	"  Server timeout (1..65535)   " 
    ::= { dot1xCurCfgPortEntry 6 }

dot1xCurCfgPortMaxRq OBJECT-TYPE
    SYNTAX INTEGER (1..10)
    MAX-ACCESS read-only
    STATUS current
    DESCRIPTION
	" Maximum numer of requests   (1..10)   " 
    ::= { dot1xCurCfgPortEntry 7 }

dot1xCurCfgPortRaPeriod OBJECT-TYPE
    SYNTAX INTEGER (0..604800)
    MAX-ACCESS read-only
    STATUS current
    DESCRIPTION
	"  Reautentication period (0..604800)    " 
    ::= { dot1xCurCfgPortEntry 8 }


dot1xCurCfgPortReAuth OBJECT-TYPE
    SYNTAX INTEGER {
	off(0),
        on(1)
	}
    MAX-ACCESS read-only
    STATUS current
    DESCRIPTION
	"  ReAuthentication state
	off(0),
        on(1)	
	    " 
    ::= { dot1xCurCfgPortEntry 9 }

dot1xCurCfgPortVlanAssign OBJECT-TYPE
    SYNTAX INTEGER {
	off(0),
        on(1)
	}
    MAX-ACCESS read-only
    STATUS current
    DESCRIPTION
	"  Vlan assignment state
	off(0),
        on(1)	
	    " 
    ::= { dot1xCurCfgPortEntry 10 }

dot1xNewCfgPortEntry OBJECT-TYPE
    SYNTAX Dot1xNewCfgPortEntry
    MAX-ACCESS not-accessible
    STATUS current
    DESCRIPTION
      "Information about 8021x Port Config"
    INDEX { dot1xNewCfgPortIndex }
    ::= { dot1xNewCfgPortTable 1 }
 
Dot1xNewCfgPortEntry ::= SEQUENCE {
    dot1xNewCfgPortIndex                PortNumber,	
    dot1xNewCfgPortMode                 INTEGER,
    dot1xNewCfgPortQtPeriod             INTEGER,
    dot1xNewCfgPortTxPeriod             INTEGER,
    dot1xNewCfgPortSupTmout		INTEGER,
    dot1xNewCfgPortSrvTmout             INTEGER,
    dot1xNewCfgPortMaxRq 		INTEGER,
    dot1xNewCfgPortRaPeriod		INTEGER,
    dot1xNewCfgPortReAuth		INTEGER ,
    dot1xNewCfgPortDefault		INTEGER ,
    dot1xNewCfgPortApplyGlobal   	INTEGER 
    ,
    dot1xNewCfgPortVlanAssign		INTEGER
    }
 
dot1xNewCfgPortIndex OBJECT-TYPE
    SYNTAX PortNumber
    MAX-ACCESS read-only
    STATUS current
    DESCRIPTION
	"The 8021x Port number for which the table is related."
    ::= { dot1xNewCfgPortEntry 1}

dot1xNewCfgPortMode OBJECT-TYPE
    SYNTAX INTEGER {
	forceUnauth(0),
	auto(1),
        forceAuth(2)
	}
    MAX-ACCESS read-create
    STATUS current
    DESCRIPTION
	" Port authentication mode 
	  forceUnauth(0),
	  auto(1),
          forceAuth(2)	     " 
    ::= { dot1xNewCfgPortEntry 2 }

dot1xNewCfgPortQtPeriod OBJECT-TYPE
    SYNTAX INTEGER (0..65535)
    MAX-ACCESS read-create
    STATUS current
    DESCRIPTION
	" Quiet period (0..65535)     " 
    ::= { dot1xNewCfgPortEntry 3 }

dot1xNewCfgPortTxPeriod OBJECT-TYPE
    SYNTAX INTEGER (1..65535)
    MAX-ACCESS read-create
    STATUS current
    DESCRIPTION
	" Tx Period  (1..65535)   " 
    ::= { dot1xNewCfgPortEntry 4 }

dot1xNewCfgPortSupTmout OBJECT-TYPE
    SYNTAX INTEGER (1..65535)
    MAX-ACCESS read-create
    STATUS current
    DESCRIPTION
	" Supplicant Timeout (1..65535)    " 
    ::= { dot1xNewCfgPortEntry 5 }

dot1xNewCfgPortSrvTmout OBJECT-TYPE
    SYNTAX INTEGER (1..65535)
    MAX-ACCESS read-create
    STATUS current
    DESCRIPTION
	"  Server Timeout  (1..65535)   " 
    ::= { dot1xNewCfgPortEntry 6 }

dot1xNewCfgPortMaxRq OBJECT-TYPE
    SYNTAX INTEGER (1..10)
    MAX-ACCESS read-create
    STATUS current
    DESCRIPTION
	" Maximum number of requests  (1..10)    " 
    ::= { dot1xNewCfgPortEntry 7 }

dot1xNewCfgPortRaPeriod OBJECT-TYPE
    SYNTAX INTEGER (1..604800)
    MAX-ACCESS read-create
    STATUS current
    DESCRIPTION
	" Reauthentication period (1..604800)    " 
    ::= { dot1xNewCfgPortEntry 8 }


dot1xNewCfgPortReAuth OBJECT-TYPE
    SYNTAX INTEGER {
	off(0),
        on(1)
	}
    MAX-ACCESS read-create
    STATUS current
    DESCRIPTION
	"  Reauthentication state
	   off(0),
           on(1)	    " 
    ::= { dot1xNewCfgPortEntry 9 }



dot1xNewCfgPortDefault OBJECT-TYPE
    SYNTAX INTEGER {
	other(0),
        apply(1)
	}
    MAX-ACCESS read-create
    STATUS current
    DESCRIPTION
	"  Port default settings    " 
    ::= { dot1xNewCfgPortEntry 10 }


dot1xNewCfgPortApplyGlobal OBJECT-TYPE
    SYNTAX INTEGER {
	other(0),
        apply(1)
	}
    MAX-ACCESS read-create
    STATUS current
    DESCRIPTION
	" Apply Global config     " 
    ::= { dot1xNewCfgPortEntry 11 }

dot1xNewCfgPortVlanAssign OBJECT-TYPE
    SYNTAX INTEGER {
	off(0),
        on(1)
	}
    MAX-ACCESS read-create
    STATUS current
    DESCRIPTION
	"Enable/Disable the assignment of vlan from radius server when the
     port is successfully autheticated.
	 Vlan assignment state
	       off(0),
           on(1)	    " 
    ::= { dot1xNewCfgPortEntry 12 }


dot1xCurCfgGuestVlanNumber OBJECT-TYPE
    SYNTAX INTEGER (1..4094) 
    MAX-ACCESS read-only
    STATUS current
    DESCRIPTION 
    	" 8021.x Guest VLAN number"
    ::= { dot1xCurCfgGuestVlan 1 }

dot1xCurCfgGuestVlanStatus OBJECT-TYPE
    SYNTAX INTEGER {
        enabled(1),
        disabled(2)
    }
    MAX-ACCESS read-only
    STATUS current
    DESCRIPTION 
    	" 8021.x Guest VLAN status 
	  enabled(1),
	  disabled(2)"
    ::= { dot1xCurCfgGuestVlan 2 }

dot1xCurCfgGlobalMode OBJECT-TYPE
    SYNTAX INTEGER {
      forceUnauth(0),
      auto(1),
      forceAuth(2)	
	}
    MAX-ACCESS read-only
    STATUS current
    DESCRIPTION
	"  Autehtication Mode
	   forceUnauth(0),
           auto(1),
           forceAuth(2)	    " 
    ::= { dot1xCurCfgGlobalTable 3 }

dot1xCurCfgGlobalQtPeriod OBJECT-TYPE
    SYNTAX INTEGER (0..65535)
    MAX-ACCESS read-only
    STATUS current
    DESCRIPTION
	" Quiet period  (0..65535)    " 
    ::= { dot1xCurCfgGlobalTable 4 }

dot1xCurCfgGlobalTxPeriod OBJECT-TYPE
    SYNTAX INTEGER (1..65535)
    MAX-ACCESS read-only
    STATUS current
    DESCRIPTION
	" Tx period  (1..65535)    " 
    ::= { dot1xCurCfgGlobalTable 5 }

dot1xCurCfgGlobalSupTmout OBJECT-TYPE
    SYNTAX INTEGER (1..65535)
    MAX-ACCESS read-only
    STATUS current
    DESCRIPTION
	"  Supplicant timeout (1..65535)    " 
    ::= { dot1xCurCfgGlobalTable 6 }

dot1xCurCfgGlobalSrvTmout OBJECT-TYPE
    SYNTAX INTEGER (1..65535)
    MAX-ACCESS read-only
    STATUS current
    DESCRIPTION
	"  Server timeout (1..65535)    " 
    ::= { dot1xCurCfgGlobalTable 7 }

dot1xCurCfgGlobalMaxRq OBJECT-TYPE
    SYNTAX INTEGER (1..10)
    MAX-ACCESS read-only
    STATUS current
    DESCRIPTION
	" Maximum number of requests  (1..10)    " 
    ::= { dot1xCurCfgGlobalTable 8 }

dot1xCurCfgGlobalRaPeriod OBJECT-TYPE
    SYNTAX INTEGER (0..604800)
    MAX-ACCESS read-only
    STATUS current
    DESCRIPTION
	" Reauthentication period  (0..604800)    " 
    ::= { dot1xCurCfgGlobalTable 9 }


dot1xCurCfgGlobalReAuth OBJECT-TYPE
    SYNTAX INTEGER {
	off(0),
        on(1)
	}
    MAX-ACCESS read-only
    STATUS current
    DESCRIPTION
	"      " 
    ::= { dot1xCurCfgGlobalTable 10 }

dot1xCurCfgGlobalVlanAssign OBJECT-TYPE
    SYNTAX INTEGER {
	off(0),
        on(1)
	}
    MAX-ACCESS read-only
    STATUS current
    DESCRIPTION
	"Vlan assignment status" 
    ::= { dot1xCurCfgGlobalTable 12 }
dot1xNewCfgGuestVlanNumber OBJECT-TYPE
    SYNTAX INTEGER (0..4094)
    MAX-ACCESS read-write
    STATUS current
    DESCRIPTION
        " 8021.x Guest VLAN number "
    ::= { dot1xNewCfgGuestVlan 1 }

dot1xNewCfgGuestVlanStatus OBJECT-TYPE
    SYNTAX INTEGER {
        enabled(1),
        disabled(2)
    }
    MAX-ACCESS read-write
    STATUS current
    DESCRIPTION
        " 8021.x Guest VLAN status
	  enabled(1),
	  disabled(2)"
    ::= { dot1xNewCfgGuestVlan 2 }

dot1xNewCfgGlobalMode OBJECT-TYPE
    SYNTAX INTEGER {
	forceUnauth(0),
	auto(1),
        forceAuth(2)
	}
    MAX-ACCESS read-create
    STATUS current
    DESCRIPTION
	"  Authentication Mode     " 
    ::= { dot1xNewCfgGlobalTable 3 }

dot1xNewCfgGlobalQtPeriod OBJECT-TYPE
    SYNTAX INTEGER (0..65535)
    MAX-ACCESS read-create
    STATUS current
    DESCRIPTION
	" Quiet Period (0..65535)     " 
    ::= { dot1xNewCfgGlobalTable 4 }

dot1xNewCfgGlobalTxPeriod OBJECT-TYPE
    SYNTAX INTEGER (1..65535)
    MAX-ACCESS read-create
    STATUS current
    DESCRIPTION
	" Tx Period (1..65535)    " 
    ::= { dot1xNewCfgGlobalTable 5 }

dot1xNewCfgGlobalSupTmout OBJECT-TYPE
    SYNTAX INTEGER (1..65535)
    MAX-ACCESS read-create
    STATUS current
    DESCRIPTION
	" Supplicand timeout (1..65535)    " 
    ::= { dot1xNewCfgGlobalTable 6 }

dot1xNewCfgGlobalSrvTmout OBJECT-TYPE
    SYNTAX INTEGER (1..65535)
    MAX-ACCESS read-create
    STATUS current
    DESCRIPTION
	" Server timeout (1..65535)     " 
    ::= { dot1xNewCfgGlobalTable 7 }

dot1xNewCfgGlobalMaxRq OBJECT-TYPE
    SYNTAX INTEGER (1..10)
    MAX-ACCESS read-create
    STATUS current
    DESCRIPTION
	" Maximum number of requests (1..10)     " 
    ::= { dot1xNewCfgGlobalTable 8 }

dot1xNewCfgGlobalRaPeriod OBJECT-TYPE
    SYNTAX INTEGER (1..604800)
    MAX-ACCESS read-create
    STATUS current
    DESCRIPTION
	"  Reauthentication period (1..604800)   " 
    ::= { dot1xNewCfgGlobalTable 9 }


dot1xNewCfgGlobalReAuth OBJECT-TYPE
    SYNTAX INTEGER {
	off(0),
        on(1)
	}
    MAX-ACCESS read-create
    STATUS current
    DESCRIPTION
	"  Reauthentication status    " 
    ::= { dot1xNewCfgGlobalTable 10 }

dot1xNewCfgGlobalDefault OBJECT-TYPE
    SYNTAX INTEGER {
        other(0),
        apply(1)
        }
    MAX-ACCESS read-create
    STATUS current
    DESCRIPTION
        "  Restore default 802.1x configuration    "
    ::= { dot1xNewCfgGlobalTable 11 }

dot1xNewCfgGlobalVlanAssign OBJECT-TYPE
    SYNTAX INTEGER {
	off(0),
        on(1)
	}
    MAX-ACCESS read-create
    STATUS current
    DESCRIPTION
	"Enable/Disable the assignment of vlan from radius server when the
     port is successfully autheticated."
    ::= { dot1xNewCfgGlobalTable 12 }

dot1xInfoPortTable OBJECT-TYPE
    SYNTAX SEQUENCE OF Dot1xInfoPortEntry
    MAX-ACCESS not-accessible
    STATUS current
    DESCRIPTION
      "The table of 8021x configuration in the Current_config."
    ::= { dot1xInfo 1 }

dot1xInfoPortEntry OBJECT-TYPE
    SYNTAX Dot1xInfoPortEntry
    MAX-ACCESS not-accessible
    STATUS current
    DESCRIPTION
      "Information about 8021x Port Config"
    INDEX { dot1xInfoPortIndex }
    ::= { dot1xInfoPortTable 1 }
 
Dot1xInfoPortEntry ::= SEQUENCE {
    dot1xInfoPortIndex                PortNumber,	
    dot1xInfoPortAuthMode                 INTEGER,
    dot1xInfoPortAuthStatus             INTEGER,
    dot1xInfoPortAuthPAEState		INTEGER,
    dot1xInfoPortBackAuthState             INTEGER   
    ,   
    dot1xInfoPortAssignedVlan              INTEGER   
    }
 
dot1xInfoPortIndex OBJECT-TYPE
    SYNTAX PortNumber
    MAX-ACCESS read-only
    STATUS current
    DESCRIPTION
	"The 8021x Port number for which the table is related."
    ::= { dot1xInfoPortEntry 1}

dot1xInfoPortAuthMode OBJECT-TYPE
    SYNTAX INTEGER {
      forceUnauth(0),
      auto(1),
      forceAuth(2)	
	}
    MAX-ACCESS read-only
    STATUS current
    DESCRIPTION
	" Authentication mode     " 
    ::= { dot1xInfoPortEntry 2 }

dot1xInfoPortAuthStatus OBJECT-TYPE
    SYNTAX INTEGER {
	authorized(0),
	unauthorized(1)
	}
    MAX-ACCESS read-only
    STATUS current
    DESCRIPTION
	" Authentication status     " 
    ::= { dot1xInfoPortEntry 3 }

    
dot1xInfoPortAuthPAEState OBJECT-TYPE
    SYNTAX INTEGER {
	initialize(0),
	disconnected(1),
 	connecting(2),
   	authenticating(3),
    	authenticated(4),
   	aborting(5),
    	held(6),
   	forceauth(7),
    	forceunauth(8)

	}
    MAX-ACCESS read-only
    STATUS current
    DESCRIPTION
	"  Authenticator PAE State    " 
    ::= { dot1xInfoPortEntry 5 }

dot1xInfoPortBackAuthState OBJECT-TYPE
    SYNTAX INTEGER {
	request(0),
	response(1),
	success(2),
   	fail(3),
    	timeout(4),
   	idle(5),
    	initialize(6)

	} 
    MAX-ACCESS read-only
    STATUS current
    DESCRIPTION
	" Backend authenticator PAE state     " 
    ::= { dot1xInfoPortEntry 6 }

dot1xInfoPortAssignedVlan OBJECT-TYPE
    SYNTAX INTEGER
    MAX-ACCESS read-only
    STATUS current
    DESCRIPTION
        "Vlan assigned from radius server.Value of
    0 indicates , no vlan assigned via Radius"
    ::= { dot1xInfoPortEntry 7 }

dot1xSystemCapability OBJECT-TYPE
    SYNTAX INTEGER {
	authenticator(0),
	supplicant(1),
        authenticatorAndSupplicant(2),
        unknown(3)
 	}
    MAX-ACCESS read-only
    STATUS current
    DESCRIPTION
	"  System capability    " 
    ::= { dot1xSystemInfo 1 }



dot1xSystemStatus OBJECT-TYPE
    SYNTAX INTEGER {
	enabled(0),
	disabled(1)
	}
    MAX-ACCESS read-only
    STATUS current
    DESCRIPTION
	"  System status    " 
    ::= { dot1xSystemInfo 2 }

dot1xSystemProtoVersion OBJECT-TYPE
    SYNTAX INTEGER 
    MAX-ACCESS read-only
    STATUS current
    DESCRIPTION
	"  Protocol version   " 
    ::= { dot1xSystemInfo 3 }


oamInfoPortTable OBJECT-TYPE
    SYNTAX SEQUENCE OF OAMInfoPortEntry
    MAX-ACCESS not-accessible
    STATUS current
    DESCRIPTION
      "The table of OAM port information."
    ::= { oamInfo 1 }

oamInfoPortEntry OBJECT-TYPE
    SYNTAX OAMInfoPortEntry
    MAX-ACCESS not-accessible
    STATUS current
    DESCRIPTION
      "Information about OAM Port"
    INDEX { oamInfoPortIndex }
    ::= { oamInfoPortTable 1 }
 
OAMInfoPortEntry ::= SEQUENCE {
    oamInfoPortIndex                PortNumber,	
    oamInfoPortLocalState           INTEGER,
    oamInfoPortLocalMode            INTEGER,
    oamInfoPortLocalLinkStatus	    INTEGER,
    oamInfoPortLocalStable  	    INTEGER,
    oamInfoPortLocalSatisfied 	    INTEGER,
    oamInfoPortLocalEvaluating	    INTEGER,
    oamInfoPortRemoteMode  	    INTEGER,
    oamInfoPortRemoteMAC  	    PhysAddress,
    oamInfoPortRemoteStable  	    INTEGER,
    oamInfoPortRemoteStateValid     INTEGER,	
    oamInfoPortRemoteEvaluating     INTEGER
    }
 
oamInfoPortIndex OBJECT-TYPE
    SYNTAX PortNumber
    MAX-ACCESS read-only
    STATUS current
    DESCRIPTION
	"The OAM Port number for which the table is related."
    ::= { oamInfoPortEntry 1}

oamInfoPortLocalState OBJECT-TYPE
    SYNTAX INTEGER {
      enabled(0),
      disabled(1)
    }
    MAX-ACCESS read-only
    STATUS current
    DESCRIPTION
	" OAM local port state" 
    ::= { oamInfoPortEntry 2 }

oamInfoPortLocalMode OBJECT-TYPE
    SYNTAX INTEGER {
      active(0),
      passive(1)
    }
    MAX-ACCESS read-only
    STATUS current
    DESCRIPTION
	" OAM local port mode" 
    ::= { oamInfoPortEntry 3 }
    
oamInfoPortLocalLinkStatus OBJECT-TYPE
    SYNTAX INTEGER {
      ok(0),
      fail(1)
    }
    MAX-ACCESS read-only
    STATUS current
    DESCRIPTION
	" OAM local port link status" 
    ::= { oamInfoPortEntry 4 }

oamInfoPortLocalStable OBJECT-TYPE
    SYNTAX INTEGER {
      true(0),
      false(1)
    }
    MAX-ACCESS read-only
    STATUS current
    DESCRIPTION
	" OAM local port stable" 
    ::= { oamInfoPortEntry 5 }

oamInfoPortLocalSatisfied OBJECT-TYPE
    SYNTAX INTEGER {
      true(0),
      false(1)
    }
    MAX-ACCESS read-only
    STATUS current
    DESCRIPTION
	" OAM local port satisfied" 
    ::= { oamInfoPortEntry 6 }

oamInfoPortLocalEvaluating OBJECT-TYPE
    SYNTAX INTEGER {
      true(0),
      false(1)
    }
    MAX-ACCESS read-only
    STATUS current
    DESCRIPTION
	" OAM local port evaluating" 
    ::= { oamInfoPortEntry 7 }

oamInfoPortRemoteMode OBJECT-TYPE
    SYNTAX INTEGER {
      active(0),
      passive(1)
    }
    MAX-ACCESS read-only
    STATUS current
    DESCRIPTION
	" OAM remote port mode" 
    ::= { oamInfoPortEntry 8 }

oamInfoPortRemoteMAC OBJECT-TYPE
    SYNTAX  PhysAddress
    MAX-ACCESS read-only
    STATUS current
    DESCRIPTION
	" OAM remote port MAC address" 
    ::= { oamInfoPortEntry 9 }

oamInfoPortRemoteStable OBJECT-TYPE
    SYNTAX INTEGER {
      true(0),
      false(1)
    }
    MAX-ACCESS read-only
    STATUS current
    DESCRIPTION
	" OAM remote port stable" 
    ::= { oamInfoPortEntry 10 }

oamInfoPortRemoteStateValid OBJECT-TYPE
    SYNTAX INTEGER {
      true(0),
      false(1)
    }
    MAX-ACCESS read-only
    STATUS current
    DESCRIPTION
	" OAM remote port state valid" 
    ::= { oamInfoPortEntry 11 }
	
oamInfoPortRemoteEvaluating OBJECT-TYPE
    SYNTAX INTEGER {
      true(0),
      false(1)
    }
    MAX-ACCESS read-only
    STATUS current
    DESCRIPTION
	" OAM remote port evaluating" 
    ::= { oamInfoPortEntry 12 }

--
-- OAM Stats
--
oamStatsPortTable OBJECT-TYPE
    SYNTAX SEQUENCE OF OAMStatsPortEntry
    MAX-ACCESS not-accessible
    STATUS current
    DESCRIPTION
      "The table of OAM port statistics."
    ::= { oamStats 1 }

oamStatsPortEntry OBJECT-TYPE
    SYNTAX OAMStatsPortEntry
    MAX-ACCESS not-accessible
    STATUS current
    DESCRIPTION
      "Statistics about OAM Port"
    INDEX { oamStatsPortIndex }
    ::= { oamStatsPortTable 1 }


OAMStatsPortEntry ::= SEQUENCE {
    oamStatsPortIndex                  PortNumber,
    oamStatsPortInfoTx                 INTEGER,
    oamStatsPortInfoRx                 INTEGER,
    oamStatsPortUnsupTx                INTEGER,
    oamStatsPortUnsupRx                INTEGER,
    oamStatsPortLocalLinkFaults        INTEGER,
    oamStatsPortLocalCriticalEvents    INTEGER,
    oamStatsPortLocalDyingGasps        INTEGER,
    oamStatsPortRemoteLinkFaults       INTEGER,
    oamStatsPortRemoteCriticalEvents   INTEGER,
    oamStatsPortRemoteDyingGasps       INTEGER
    }

oamStatsPortIndex OBJECT-TYPE
    SYNTAX PortNumber
    MAX-ACCESS read-only
    STATUS current
    DESCRIPTION
        "The OAM Port number for which the table is related."
    ::= { oamStatsPortEntry 1}

oamStatsPortInfoTx OBJECT-TYPE
    SYNTAX INTEGER
    MAX-ACCESS read-only
    STATUS current
    DESCRIPTION
        "The number of transmitted OAM information packets"
    ::= { oamStatsPortEntry 2}

oamStatsPortInfoRx OBJECT-TYPE
    SYNTAX INTEGER
    MAX-ACCESS read-only
    STATUS current
    DESCRIPTION
        "The number of received OAM information packets"
    ::= { oamStatsPortEntry 3}

oamStatsPortUnsupTx OBJECT-TYPE
    SYNTAX INTEGER
    MAX-ACCESS read-only
    STATUS current
    DESCRIPTION
        "The number of transmitted OAM unsupported packets"
    ::= { oamStatsPortEntry 4}

oamStatsPortUnsupRx OBJECT-TYPE
    SYNTAX INTEGER
    MAX-ACCESS read-only
    STATUS current
    DESCRIPTION
        "The number of received OAM unsupported packets"
    ::= { oamStatsPortEntry 5}

oamStatsPortLocalLinkFaults  OBJECT-TYPE
    SYNTAX INTEGER
    MAX-ACCESS read-only
    STATUS current
    DESCRIPTION
        "The number of local OAM link fault packets"
    ::= { oamStatsPortEntry 6}

oamStatsPortLocalCriticalEvents  OBJECT-TYPE
    SYNTAX INTEGER
    MAX-ACCESS read-only
    STATUS current
    DESCRIPTION
        "The number of local OAM critical event packets"
    ::= { oamStatsPortEntry 7}

oamStatsPortLocalDyingGasps  OBJECT-TYPE
    SYNTAX INTEGER
    MAX-ACCESS read-only
    STATUS current
    DESCRIPTION
        "The number of local OAM dying gasp packets"
    ::= { oamStatsPortEntry 8}

oamStatsPortRemoteLinkFaults  OBJECT-TYPE
    SYNTAX INTEGER
    MAX-ACCESS read-only
    STATUS current
    DESCRIPTION
        "The number of remote OAM link fault packets"
    ::= { oamStatsPortEntry 9}

oamStatsPortRemoteCriticalEvents  OBJECT-TYPE
    SYNTAX INTEGER
    MAX-ACCESS read-only
    STATUS current
    DESCRIPTION
        "The number of remote OAM critical event packets"
    ::= { oamStatsPortEntry 10}

oamStatsPortRemoteDyingGasps  OBJECT-TYPE
    SYNTAX INTEGER
    MAX-ACCESS read-only
    STATUS current
    DESCRIPTION
        "The number of remote OAM dying gasp packets"
    ::= { oamStatsPortEntry 11}

-- Trunk Group Information

trunkGroupInfoTable OBJECT-TYPE
    SYNTAX SEQUENCE OF TrunkGroupInfoTableEntry
    MAX-ACCESS not-accessible
    STATUS current
    DESCRIPTION
        "The table of trunk group information."
    ::= { trunkGroupInfo 1 }

trunkGroupInfoTableEntry OBJECT-TYPE
    SYNTAX TrunkGroupInfoTableEntry
    MAX-ACCESS not-accessible
    STATUS current
    DESCRIPTION
        "A row in trunk group information table."
    INDEX { trunkGroupInfoIndex }
    ::= { trunkGroupInfoTable 1 }

TrunkGroupInfoTableEntry ::= SEQUENCE {
    trunkGroupInfoIndex       Integer32,
    trunkGroupInfoState       INTEGER,
    trunkGroupInfoProtocol    INTEGER,
    trunkGroupInfoPorts       OCTET STRING
    }

trunkGroupInfoIndex OBJECT-TYPE
    SYNTAX  Integer32
    MAX-ACCESS  read-only
    STATUS  current
    DESCRIPTION
        "The identifier of the trunk group."
    ::= { trunkGroupInfoTableEntry 1 }

trunkGroupInfoState OBJECT-TYPE
    SYNTAX  INTEGER  {
        enabled(1),
        disabled(2)
        }
    MAX-ACCESS  read-only
    STATUS  current
    DESCRIPTION
        "Trunk group state."
    ::= { trunkGroupInfoTableEntry 2 }


trunkGroupInfoPorts OBJECT-TYPE
    SYNTAX  OCTET STRING
    MAX-ACCESS  read-only
    STATUS  current
    DESCRIPTION
        "The port list in the trunk group. The ports are presented in
         bitmap format.

         in receiving order:

             OCTET 1  OCTET 2  .....
             xxxxxxxx xxxxxxxx .....
             ||    || |_ port 8
             ||    ||
             ||    ||___ port 7
             ||    |____ port 6
             ||      .    .   .
             ||_________ port 1
             |__________ reserved

         where x : 1 - The represented port belongs to the trunk group
                   0 - The represented port does not belong to the trunk group"
    ::= { trunkGroupInfoTableEntry 3 }

trunkGroupInfoProtocol OBJECT-TYPE
    SYNTAX  INTEGER  {
        static(1),
        lacp(2)
        }
    MAX-ACCESS  read-only
    STATUS  current
    DESCRIPTION
        "Trunk group protocol
         Static - static trunk group
         Lacp - dynamic trunk group"
    ::= { trunkGroupInfoTableEntry 4 }

trunkGroupInfoPortTable OBJECT-TYPE
    SYNTAX  SEQUENCE OF TrunkGroupInfoPortTableEntry
    MAX-ACCESS  not-accessible
    STATUS  current
    DESCRIPTION
        "The table of Trunk Group Info."
    ::= {trunkGroupInfo 2 }

trunkGroupInfoPortTableEntry OBJECT-TYPE
    SYNTAX  TrunkGroupInfoPortTableEntry
    MAX-ACCESS  not-accessible
    STATUS  current
    DESCRIPTION
        "A row in the Trunk Info table."
    INDEX  { trunkGroupInfoPortTrunkId, trunkGroupInfoPortPortId }
    ::= { trunkGroupInfoPortTable 1 }

TrunkGroupInfoPortTableEntry ::= SEQUENCE {
    trunkGroupInfoPortTrunkId   Integer32,
    trunkGroupInfoPortPortId    PortNumber,
    trunkGroupInfoPortStatus    INTEGER
    }

trunkGroupInfoPortTrunkId OBJECT-TYPE
    SYNTAX  Integer32
    MAX-ACCESS  read-only
    STATUS  current
    DESCRIPTION
        "The Trunk identifier."
    ::= { trunkGroupInfoPortTableEntry 1 }

trunkGroupInfoPortPortId OBJECT-TYPE
    SYNTAX  PortNumber
    MAX-ACCESS  read-only
    STATUS  current
    DESCRIPTION
        "The Port identifier."
    ::= { trunkGroupInfoPortTableEntry 2 }

trunkGroupInfoPortStatus OBJECT-TYPE
    SYNTAX  INTEGER{
        down(0),

        blocking(1),
        forwarding(2)

        }
    MAX-ACCESS  read-only
    STATUS  current
    DESCRIPTION
        "The Port Status."
    ::= { trunkGroupInfoPortTableEntry 3 }


-- LACP Statistics

lacpStatsTable OBJECT-TYPE
    SYNTAX SEQUENCE OF LacpStatsTableEntry
    MAX-ACCESS not-accessible
    STATUS current
    DESCRIPTION
        "The table of LACP Stats."
	::= {lacpStats 1}

lacpStatsTableEntry OBJECT-TYPE
    SYNTAX LacpStatsTableEntry
    MAX-ACCESS not-accessible
    STATUS current
    DESCRIPTION
        "Lacp status info."
    INDEX { lacpStatsIndex }
    ::= { lacpStatsTable 1 }

LacpStatsTableEntry ::= SEQUENCE {
   lacpStatsIndex PortNumber,
   lacpdusRx Integer32,
   markerpdusRx Integer32,
   markerresponsepdusRx Integer32,
   unknownRx Integer32,
   illegalRx Integer32,
   lacpdusTx Integer32,
   markerpdusTx Integer32,
   markerresponsepdusTx Integer32
   ,lacpClearStats INTEGER
}

lacpStatsIndex OBJECT-TYPE
  SYNTAX PortNumber
  MAX-ACCESS read-only
  STATUS current
  DESCRIPTION
	"Index"
  ::= {lacpStatsTableEntry 1}

lacpdusRx OBJECT-TYPE
  SYNTAX Integer32
  MAX-ACCESS read-only
  STATUS current
  DESCRIPTION
	"Valid LACPDUs received"
  ::= {lacpStatsTableEntry 2}

markerpdusRx OBJECT-TYPE
  SYNTAX Integer32
  MAX-ACCESS read-only
  STATUS current
  DESCRIPTION
	"Valid Marker PDUs received"
  ::= {lacpStatsTableEntry 3}

markerresponsepdusRx OBJECT-TYPE
  SYNTAX Integer32
  MAX-ACCESS read-only
  STATUS current
  DESCRIPTION
	"Valid Marker Rsp PDUs received"
  ::= {lacpStatsTableEntry 4}

unknownRx OBJECT-TYPE
  SYNTAX Integer32
  MAX-ACCESS read-only
  STATUS current
  DESCRIPTION
	"Unknown version/TLV type"
  ::= {lacpStatsTableEntry 5}

illegalRx OBJECT-TYPE
  SYNTAX Integer32
  MAX-ACCESS read-only
  STATUS current
  DESCRIPTION
	"Illegal subtype received"
  ::= {lacpStatsTableEntry 6}

lacpdusTx OBJECT-TYPE
  SYNTAX Integer32
  MAX-ACCESS read-only
  STATUS current
  DESCRIPTION
	"LACPDUs transmitted"
  ::= {lacpStatsTableEntry 7}

markerpdusTx OBJECT-TYPE
  SYNTAX Integer32
  MAX-ACCESS read-only
  STATUS current
  DESCRIPTION
	"Market PDUs transmitted"
  ::= {lacpStatsTableEntry 8}

markerresponsepdusTx OBJECT-TYPE
  SYNTAX Integer32
  MAX-ACCESS read-only
  STATUS current
  DESCRIPTION
	"Marker Rsp PDUs transmitted "
  ::= {lacpStatsTableEntry 9}

lacpClearStats  OBJECT-TYPE
    SYNTAX  INTEGER {
        ok(1),
        clear(2)
        }
    MAX-ACCESS  read-write
    STATUS  current 
    DESCRIPTION 
        "Setting this to clear(2) results in clearing the LACP statistics."
    ::= { lacpStatsTableEntry 10 }


-- FDB Statistics


fdbStatsCurrent OBJECT-TYPE
    SYNTAX  Gauge32
    MAX-ACCESS  read-only
    STATUS  current
    DESCRIPTION
        "Current number of entries in the Forwarding Database."
    ::= { fdbStats 3 }

fdbStatsHiwat OBJECT-TYPE
    SYNTAX  Integer32
    MAX-ACCESS  read-only
    STATUS  current
    DESCRIPTION
        "Highest number of entries recorded at any given time in the 
         Forwarding Database."
    ::= { fdbStats 4 }


fdbStatsClear OBJECT-TYPE
    SYNTAX INTEGER {
      ok(1),
      clear(2)
      }
    MAX-ACCESS  read-write
    STATUS  current
    DESCRIPTION
        "Clear FDB statistics"
    ::= { fdbStats 11 }

-- STP Statistics

stgStatsPortTable OBJECT-TYPE
    SYNTAX SEQUENCE OF StgStatsPortTableEntry
    MAX-ACCESS not-accessible
    STATUS current
    DESCRIPTION
        "The table of Spanning Tree Group port statistics."
    ::= { stpStats 1 }

stgStatsPortTableEntry OBJECT-TYPE
    SYNTAX StgStatsPortTableEntry
    MAX-ACCESS not-accessible
    STATUS current
    DESCRIPTION
        "Statistics about port of a particular Spanning Tree Group."
    INDEX { stgStatsStpIndex, stgStatsPortIndex }
    ::= { stgStatsPortTable 1 }

StgStatsPortTableEntry ::= SEQUENCE {
    stgStatsStpIndex            Integer32,
    stgStatsPortIndex	        PortNumber,
    stgStatsPortRcvCfgBpdus     Counter32,
    stgStatsPortRcvTcnBpdus     Counter32,
    stgStatsPortXmtCfgBpdus     Counter32,
    stgStatsPortXmtTcnBpdus     Counter32 
    }

stgStatsStpIndex OBJECT-TYPE
    SYNTAX Integer32  
    MAX-ACCESS read-only
    STATUS current
    DESCRIPTION
        "The identifier of a particular Spanning Tree Group."
    ::= { stgStatsPortTableEntry 1 }

stgStatsPortIndex OBJECT-TYPE
    SYNTAX PortNumber
    MAX-ACCESS read-only
    STATUS current
    DESCRIPTION
        "The port identifier of a particular Spanning Tree Group."
    ::= { stgStatsPortTableEntry 2 }

stgStatsPortRcvCfgBpdus OBJECT-TYPE
    SYNTAX Counter32 
    MAX-ACCESS read-only
    STATUS current
    DESCRIPTION
        "Number of Configuration BPDU's received on this port."
    ::= { stgStatsPortTableEntry 3 }

stgStatsPortRcvTcnBpdus OBJECT-TYPE
    SYNTAX Counter32 
    MAX-ACCESS read-only
    STATUS current
    DESCRIPTION
        "Number of TCN BPDU's received on this port."
    ::= { stgStatsPortTableEntry 4 }

stgStatsPortXmtCfgBpdus OBJECT-TYPE
    SYNTAX Counter32 
    MAX-ACCESS read-only
    STATUS current
    DESCRIPTION
        "Number of Configuration BPDU's trasmitted from the port."
    ::= { stgStatsPortTableEntry 5 }

stgStatsPortXmtTcnBpdus OBJECT-TYPE
    SYNTAX Counter32 
    MAX-ACCESS read-only
    STATUS current
    DESCRIPTION
        "Number of TCN BPDU's trasmitted from the port."
    ::= { stgStatsPortTableEntry 6 }

fdbClear OBJECT-TYPE
    SYNTAX  INTEGER {
        ok(1),
        clear(2)
        }
    MAX-ACCESS  read-write
    STATUS  current 
    DESCRIPTION
        "Setting this value to clear(2) clears the entire master FDB."
    ::= { fdbInfo 1 }


--  FDB table
fdbTable OBJECT-TYPE
    SYNTAX  SEQUENCE OF FdbEntry
    MAX-ACCESS  not-accessible
    STATUS  current
    DESCRIPTION
        "The table of FDB entries."
    ::= { fdbInfo 2 }

fdbEntry OBJECT-TYPE
    SYNTAX  FdbEntry
    MAX-ACCESS  not-accessible
    STATUS  current
    DESCRIPTION
        "A row in the FDB table"
    INDEX   { fdbMacAddr }
    ::= { fdbTable 1 }

FdbEntry ::= SEQUENCE {
    fdbMacAddr            MacAddress,
    fdbVlan       	  Integer32,
    fdbSrcPort            PortNumber,
    fdbSrcTrunk           Integer32,
    fdbState              INTEGER
    ,fdbStatus             Integer32
    }

fdbMacAddr OBJECT-TYPE
    SYNTAX  MacAddress
    MAX-ACCESS  read-only
    STATUS  current
    DESCRIPTION
        "The MAC address for the FDB entry."
    ::= { fdbEntry 1 }

fdbVlan OBJECT-TYPE 
    SYNTAX  Integer32 
    MAX-ACCESS  read-only 
    STATUS  current 
    DESCRIPTION 
        "The VLAN ID for the FDB entry." 
    ::= { fdbEntry 2 }

fdbSrcPort OBJECT-TYPE  
    SYNTAX  PortNumber 
    MAX-ACCESS  read-only  
    STATUS  current  
    DESCRIPTION  
       "Either the value '0', or the port number of the port on which a frame 
        having a source address equal to the value of the corresponding 
        instance has been seen.  A value of '0' indicates that the port 
        number has not been learned but that the bridge does have some
        forwarding/filtering information about this address."
    ::= { fdbEntry 3 }

fdbState OBJECT-TYPE  
    SYNTAX  INTEGER {
	unknown(1),
	forward(2),
	trunk(3)
        }
    MAX-ACCESS  read-only  
    STATUS  current  
    DESCRIPTION  
        "The state of the FDB entry. The meanings of the values are :
         unknown(1) : the MAC address has not yet been learned by the switch
                      but has only been seen as a destination address
         forward(2) : the MAC address has been learned by the switch
         trunk(3)   : frames with this MAC address are forwarded to trunk
                      group"
    ::= { fdbEntry 4 }


fdbSrcTrunk OBJECT-TYPE
    SYNTAX  Integer32
    MAX-ACCESS  read-only
    STATUS  current
    DESCRIPTION
       "Either the value '0', or the trunk number of the trunk on which a frame
        having a source address equal to the value of the corresponding
        instance has been seen.  A value of '0' indicates that the source
        address is not associated with a trunk."
    ::= { fdbEntry 7 }

fdbStatus OBJECT-TYPE
    SYNTAX  Integer32
    MAX-ACCESS  read-only
    STATUS  current
    DESCRIPTION
       "'1' if it is permanent 
        '0' if it is not permanent"
    ::= { fdbEntry 8 }

--  Multicast FDB table
mcastFdbTable OBJECT-TYPE
    SYNTAX  SEQUENCE OF McastFdbEntry
    MAX-ACCESS  not-accessible
    STATUS  current
    DESCRIPTION
        "The table of static multicast FDB entries."
    ::= { fdbInfo 3 }

mcastFdbEntry OBJECT-TYPE
    SYNTAX  McastFdbEntry
    MAX-ACCESS  not-accessible
    STATUS  current
    DESCRIPTION
        "A row in the static multicast FDB table"
    INDEX   { mcastFdbEntryIndex }
    ::= { mcastFdbTable 1 }

McastFdbEntry ::= SEQUENCE {
    mcastFdbEntryIndex         Integer32,
    mcastFdbMacAddr            MacAddress,
    mcastFdbVlan               Integer32,
    mcastFdbSrcPorts           PortNumber
    }

mcastFdbEntryIndex OBJECT-TYPE
    SYNTAX  Integer32
    MAX-ACCESS  read-only
    STATUS  current
    DESCRIPTION
        "The static multicast fdb entry index"
    ::= { mcastFdbEntry 1 }

mcastFdbMacAddr OBJECT-TYPE
    SYNTAX  MacAddress
    MAX-ACCESS  read-only
    STATUS  current
    DESCRIPTION
        "The static multicast MAC address for the FDB entry."
    ::= { mcastFdbEntry 2 }

mcastFdbVlan OBJECT-TYPE 
    SYNTAX  Integer32 
    MAX-ACCESS  read-only 
    STATUS  current 
    DESCRIPTION 
        "The VLAN ID for the FDB entry." 
    ::= { mcastFdbEntry 3 }

mcastFdbSrcPorts OBJECT-TYPE
    SYNTAX  PortNumber
    MAX-ACCESS   read-only
    STATUS  current
    DESCRIPTION
        "The multicast MAC address port list.  The ports are presented in bitmap format.
         in receiving order:

             OCTET 1  OCTET 2  .....
             xxxxxxxx xxxxxxxx .....
             ||    || |_ port 8
             ||    ||
             ||    ||___ port 7
             ||    |____ port 6
             ||      .    .   .
             ||_________ port 1
             |__________ reserved

         where x : 1 - The represented port belongs to the multicast MAC address.
                   0 - The represented port does not belong to the multicast MAC address."
    ::= { mcastFdbEntry 4 }

-- STP Information

stpInfoTable OBJECT-TYPE
    SYNTAX SEQUENCE OF StpInfoTableEntry
    MAX-ACCESS not-accessible
    STATUS current
    DESCRIPTION
        "The table of Spanning Tree Group information."
    ::= { stpInfo 1 }

stpInfoTableEntry OBJECT-TYPE
    SYNTAX StpInfoTableEntry
    MAX-ACCESS not-accessible
    STATUS current
    DESCRIPTION
        "Information about a particular Spanning Tree Group."
    INDEX { stpInfoIndex }
    ::= { stpInfoTable 1 }

StpInfoTableEntry ::= SEQUENCE {
    stpInfoIndex              Integer32,
    stpInfoTimeSinceTopChange TimeTicks,
    stpInfoTopChanges         Counter32,
    stpInfoDesignatedRoot     BridgeId,
    stpInfoRootCost           Integer32,
    stpInfoRootPort           PortNumber,
    stpInfoMaxAge             Integer32,
    stpInfoHelloTime          Integer32,
    stpInfoForwardDelay       Integer32,
    stpInfoHoldTime           Integer32
    }

stpInfoIndex OBJECT-TYPE
    SYNTAX Integer32
    MAX-ACCESS read-only
    STATUS current
    DESCRIPTION
        "The identifier of a particular Spanning Tree Group.  This is also
         index to the entLogicalTable of Entity MIB."
    ::= { stpInfoTableEntry 1 }

stpInfoTimeSinceTopChange OBJECT-TYPE
    SYNTAX  TimeTicks
    MAX-ACCESS  read-only
    STATUS  current
    DESCRIPTION
        "The time (in hundredths of a second) since the last time a topology 
         change was detected by the bridge entity."
    ::= { stpInfoTableEntry 2 }

stpInfoTopChanges OBJECT-TYPE
    SYNTAX  Counter32
    MAX-ACCESS  read-only
    STATUS  current
    DESCRIPTION
        "The total number of topology changes detected by this bridge since 
         the management entity was last reset or initialized."
    ::= { stpInfoTableEntry 3 }

stpInfoDesignatedRoot OBJECT-TYPE
    SYNTAX  BridgeId
    MAX-ACCESS  read-only
    STATUS  current
    DESCRIPTION
        "The bridge identifier of the root of the spanning tree as determined 
         by the Spanning Tree Protocol as executed by this node.  This value 
         is used as the Root Identifier parameter in all Configuration Bridge 
         PDUs originated by this node."
    ::= { stpInfoTableEntry 4 }

stpInfoRootCost OBJECT-TYPE
    SYNTAX  Integer32
    MAX-ACCESS  read-only
    STATUS  current
    DESCRIPTION
        "The cost of the path to the root as seen from this bridge."
    ::= { stpInfoTableEntry 5 }

stpInfoRootPort OBJECT-TYPE
    SYNTAX  PortNumber
    MAX-ACCESS  read-only
    STATUS  current
    DESCRIPTION
        "The port number of the port which offers the lowest cost path from 
         this bridge to the root bridge."
    ::= { stpInfoTableEntry 6 }

stpInfoMaxAge OBJECT-TYPE
    SYNTAX  Integer32
    MAX-ACCESS  read-only
    STATUS  current
    DESCRIPTION
        "The maximum age of Spanning Tree Protocol information learned from 
         the network on any port before it is discarded, in units of 
         hundredths of a second.  This is the actual value that this bridge is
         currently using."
    ::= { stpInfoTableEntry 7 }

stpInfoHelloTime OBJECT-TYPE
    SYNTAX  Integer32
    MAX-ACCESS  read-only
    STATUS  current
    DESCRIPTION
        "The amount of time between the transmission of Configuration bridge 
         PDUs by this node on any port when it is the root of the spanning 
         tree or trying to become so, in units of hundredths of a second.
         This is the actual value that this bridge is currently using."
    ::= { stpInfoTableEntry 8 }

stpInfoForwardDelay OBJECT-TYPE
     SYNTAX  Integer32
     MAX-ACCESS  read-only
     STATUS  current
     DESCRIPTION
         "This time value, measured in units of hundredths of a second, 
          controls how fast a port changes its spanning state when moving 
          towards the Forwarding state.  The value determines how long the port
          stays in each of the Listening and Learning states, which precede 
          the Forwarding state.  This value is also used, when a topology 
          change has been detected and is underway, to age all dynamic entries
          in the Forwarding Database."
    ::= { stpInfoTableEntry 9 }

stpInfoHoldTime OBJECT-TYPE
    SYNTAX  Integer32
    MAX-ACCESS  read-only
    STATUS  current
    DESCRIPTION
        "This time value determines the interval length during which no more 
         than two Configuration bridge PDUs shall be transmitted by this node,
         in units of hundredths of a second."
    ::= { stpInfoTableEntry 10 }

stpInfoPortTable OBJECT-TYPE
    SYNTAX SEQUENCE OF StpInfoPortTableEntry
    MAX-ACCESS not-accessible
    STATUS current
    DESCRIPTION
        "The table of Spanning Tree Group port information."
    ::= { stpInfo 2 }

stpInfoPortTableEntry OBJECT-TYPE
    SYNTAX StpInfoPortTableEntry
    MAX-ACCESS not-accessible
    STATUS current
    DESCRIPTION
        "Information about port configuration for a particular Spanning Tree
         Group."
    INDEX { stpInfoPortStpIndex, stpInfoPortIndex }
    ::= { stpInfoPortTable 1 }

StpInfoPortTableEntry ::= SEQUENCE {
    stpInfoPortStpIndex           Integer32,
    stpInfoPortIndex              PortNumber,
    stpInfoPortState              INTEGER,
    stpInfoPortDesignatedRoot     BridgeId,
    stpInfoPortDesignatedCost     Integer32,
    stpInfoPortDesignatedBridge   BridgeId,
    stpInfoPortDesignatedPort     OCTET STRING,
    stpInfoPortForwardTransitions Counter32,
    stpInfoPortRole               INTEGER,
    stpInfoPortLinkType           INTEGER,
    stpInfoPortEdge               INTEGER,
    stpInfoPortExtGuard           INTEGER,
    stpInfoPortPathCost           Integer32,
    stpInfoPortPriority           Integer32
   }

stpInfoPortStpIndex OBJECT-TYPE
    SYNTAX Integer32
    MAX-ACCESS read-only
    STATUS current
    DESCRIPTION
        "The identifier of a particular Spanning Tree Group."
    ::= { stpInfoPortTableEntry 1 }

stpInfoPortIndex OBJECT-TYPE
    SYNTAX PortNumber
    MAX-ACCESS read-only
    STATUS current
    DESCRIPTION
        "The port identifier of a particular Spanning Tree Group."
    ::= { stpInfoPortTableEntry 2 }

stpInfoPortState OBJECT-TYPE
    SYNTAX  INTEGER {
        disabled(1),
        blocking(2),
        listening(3),
        learning(4),
        forwarding(5),
        discarding(7),
        broken(6),
        na(8)
        }
    MAX-ACCESS  read-only
    STATUS  current
    DESCRIPTION
        "The port's current state as defined by application of the Spanning 
         Tree Protocol.  This state controls what action a port takes on
         reception of a frame.  If the bridge has detected a port that is 
         malfunctioning it will place that port into the broken(6) state.  
         For ports which are disabled, this object will have a value of 
         disabled(1). If port is not controlled by STP, this object will have
         a value of na (8)."
    ::= { stpInfoPortTableEntry 3 }

stpInfoPortDesignatedRoot OBJECT-TYPE
    SYNTAX  BridgeId
    MAX-ACCESS  read-only
    STATUS  current
    DESCRIPTION
        "The unique Bridge Identifier of the Bridge recorded as the Root in 
         the Configuration BPDUs transmitted by the Designated Bridge for the
         segment to which the port is attached."
    ::= { stpInfoPortTableEntry 4 }

stpInfoPortDesignatedCost OBJECT-TYPE
    SYNTAX  Integer32
    MAX-ACCESS  read-only
    STATUS  current
    DESCRIPTION
        "The path cost of the Designated Port of the segment connected to this
         port.  This value is compared to the Root Path Cost field in received
         bridge PDUs."
    ::= { stpInfoPortTableEntry 5 }

stpInfoPortDesignatedBridge OBJECT-TYPE
    SYNTAX  BridgeId
    MAX-ACCESS  read-only
    STATUS  current
    DESCRIPTION
        "The Bridge Identifier of the bridge which this port considers to be 
         the Designated Bridge for this port's segment."
    ::= { stpInfoPortTableEntry 6 }

stpInfoPortDesignatedPort OBJECT-TYPE
    SYNTAX  OCTET STRING (SIZE (2))
    MAX-ACCESS  read-only
    STATUS  current
    DESCRIPTION
        "The Port Identifier of the port on the Designated Bridge for this 
         port's segment."
    ::= { stpInfoPortTableEntry 7 }

stpInfoPortForwardTransitions OBJECT-TYPE
    SYNTAX  Counter32
    MAX-ACCESS  read-only
    STATUS  current
    DESCRIPTION
        "The number of times this port has transitioned from the Learning 
         state to the Forwarding state."
    ::= { stpInfoPortTableEntry 8 }

stpInfoPortPathCost OBJECT-TYPE
    SYNTAX  Integer32
    MAX-ACCESS  read-only
    STATUS  current
    DESCRIPTION
        "The path cost of the port."
    ::= { stpInfoPortTableEntry 9 }

stpInfoPortRole OBJECT-TYPE
    SYNTAX  INTEGER {
        disabled(1),
        alternate(2),
        backup(3),
        root(4),
        designated(5),
        master(6),
        unknown(7)
        }
    MAX-ACCESS  read-only
    STATUS  current
    DESCRIPTION
        "The port role. Returns unknown(7) when MSTP/RSTP is not enabled,
         otherwise returns appropriate port role."
    ::= { stpInfoPortTableEntry 10 }

stpInfoPortLinkType OBJECT-TYPE
    SYNTAX  INTEGER {
        p2p(1),
        shared(2),
        unknown(3)
        }
    MAX-ACCESS  read-only
    STATUS  current
    DESCRIPTION
        "The point-to-point status of the LAN segment attached
         to this port.  A value of p2p (1) indicates that this port is being
         treated as if it is connected to a point-to-point link.
         A value of shared(2) indicates that this port is being treated as
         having a shared media connection."
    ::= { stpInfoPortTableEntry 11 }

stpInfoPortEdge OBJECT-TYPE
    SYNTAX  INTEGER {
        enabled(1),
        disabled(2)
        }
    MAX-ACCESS  read-only
    STATUS  current
    DESCRIPTION
        "The port is an edge port or not. Returns disabled(2) when the port is
	 not an edge port and returns enabled(1) when it is an edge port."
    ::= { stpInfoPortTableEntry 12 }

stpInfoPortExtGuard OBJECT-TYPE
    SYNTAX  INTEGER {
        loop-inc(1),
        root-inc(2),
        normal(0)
        }
    MAX-ACCESS  read-only
    STATUS  current
    DESCRIPTION
        "Current STP guard state. Not include BPDU Guard."
    ::= { stpInfoPortTableEntry 13 }

stpInfoPortPriority OBJECT-TYPE
    SYNTAX Integer32
    MAX-ACCESS read-only
    STATUS current
    DESCRIPTION
        "The four most significant bits of the Port Identifier of the 
         Spanning Tree instance can be modified by setting this value."
    ::= { stpInfoPortTableEntry 14 }



-- LACP information

lacpInfoAggrTable OBJECT-TYPE
    SYNTAX SEQUENCE OF LacpInfoAggrTableEntry
    MAX-ACCESS not-accessible
    STATUS current
    DESCRIPTION
        "The table of LACP aggregator information."
    ::= { lacpInfo 1 }

lacpInfoAggrTableEntry OBJECT-TYPE
    SYNTAX LacpInfoAggrTableEntry
    MAX-ACCESS not-accessible
    STATUS current
    DESCRIPTION
        "Information about a LACP aggregator."
    INDEX { lacpInfoAggrIndex }
    ::= { lacpInfoAggrTable 1 }

LacpInfoAggrTableEntry ::= SEQUENCE {
    lacpInfoAggrIndex           PortNumber,
    lacpInfoAggrId		Integer32,
    lacpInfoAggrMac		DisplayString,
    lacpInfoAggrActSysPrio	Integer32,
    lacpInfoAggrActSysId	DisplayString,
    lacpInfoAggrIndivState	INTEGER,
    lacpInfoAggrActAdminKey	Integer32,
    lacpInfoAggrActOperKey	Integer32,
    lacpInfoAggrPartSysPrio	Integer32,
    lacpInfoAggrPartSysId	DisplayString,
    lacpInfoAggrPartOperKey	Integer32,
    lacpInfoAggrReadyState	INTEGER,
    lacpInfoAggrNumPorts	Integer32
    ,lacpInfoAggrMinLinks 	Integer32
    }

lacpInfoAggrIndex OBJECT-TYPE
    SYNTAX PortNumber
    MAX-ACCESS read-only
    STATUS current
    DESCRIPTION
        "The aggregator identifier."
    ::= { lacpInfoAggrTableEntry 1 }

lacpInfoAggrId OBJECT-TYPE 
    SYNTAX  Integer32
    MAX-ACCESS  read-only
    STATUS  current
    DESCRIPTION
        "LACP aggregator ID"
    ::= { lacpInfoAggrTableEntry 2 }

lacpInfoAggrMac OBJECT-TYPE 
    SYNTAX  DisplayString
    MAX-ACCESS  read-only
    STATUS  current
    DESCRIPTION
        "LACP aggregator MAC address"
    ::= { lacpInfoAggrTableEntry 3 }

lacpInfoAggrActSysPrio OBJECT-TYPE 
    SYNTAX  Integer32
    MAX-ACCESS  read-only
    STATUS  current
    DESCRIPTION
        "LACP aggregator actor system priority"
    ::= { lacpInfoAggrTableEntry 4 }

lacpInfoAggrActSysId OBJECT-TYPE 
    SYNTAX  DisplayString
    MAX-ACCESS  read-only
    STATUS  current
    DESCRIPTION
        "LACP aggregator actor system ID"
    ::= { lacpInfoAggrTableEntry 5 }

lacpInfoAggrIndivState OBJECT-TYPE 
    SYNTAX  INTEGER {
        true(1),
        false(2)
        }
    MAX-ACCESS  read-only
    STATUS  current
    DESCRIPTION
        "LACP aggregator individual state"
    ::= { lacpInfoAggrTableEntry 6 }

lacpInfoAggrActAdminKey OBJECT-TYPE 
    SYNTAX  Integer32
    MAX-ACCESS  read-only
    STATUS  current
    DESCRIPTION
        "LACP aggregator actor admin key"
    ::= { lacpInfoAggrTableEntry 7 }

lacpInfoAggrActOperKey OBJECT-TYPE 
    SYNTAX  Integer32
    MAX-ACCESS  read-only
    STATUS  current
    DESCRIPTION
        "LACP aggregator actor oper key"
    ::= { lacpInfoAggrTableEntry 8 }

lacpInfoAggrPartSysPrio OBJECT-TYPE 
    SYNTAX  Integer32
    MAX-ACCESS  read-only
    STATUS  current
    DESCRIPTION
        "LACP aggregator partner system priority"
    ::= { lacpInfoAggrTableEntry 9 }

lacpInfoAggrPartSysId OBJECT-TYPE 
    SYNTAX  DisplayString
    MAX-ACCESS  read-only
    STATUS  current
    DESCRIPTION
        "LACP aggregator partner system ID"
    ::= { lacpInfoAggrTableEntry 10 }

lacpInfoAggrPartOperKey OBJECT-TYPE 
    SYNTAX  Integer32
    MAX-ACCESS  read-only
    STATUS  current
    DESCRIPTION
        "LACP aggregator partner oper key"
    ::= { lacpInfoAggrTableEntry 11 }

lacpInfoAggrReadyState OBJECT-TYPE 
    SYNTAX  INTEGER {
        true(1),
        false(2)
        }
    MAX-ACCESS  read-only
    STATUS  current
    DESCRIPTION
        "LACP aggregator ready state"
    ::= { lacpInfoAggrTableEntry 12 }

lacpInfoAggrNumPorts OBJECT-TYPE 
    SYNTAX  Integer32
    MAX-ACCESS  read-only
    STATUS  current
    DESCRIPTION
        "Number of ports in aggregator"
    ::= { lacpInfoAggrTableEntry 13 }


lacpInfoAggrMinLinks OBJECT-TYPE 
    SYNTAX  Integer32
    MAX-ACCESS  read-only
    STATUS  current
    DESCRIPTION
        "Min Links of ports in aggregator"
    ::= { lacpInfoAggrTableEntry 15 }
	
lacpInfoPort OBJECT IDENTIFIER ::= { lacpInfo 2 }

lacpInfoPortGeneralTable OBJECT-TYPE
    SYNTAX SEQUENCE OF LacpInfoPortGeneralTableEntry
    MAX-ACCESS not-accessible
    STATUS current
    DESCRIPTION
        "The table of LACP port general information."
    ::= { lacpInfoPort 1 }

lacpInfoPortGeneralTableEntry OBJECT-TYPE
    SYNTAX LacpInfoPortGeneralTableEntry
    MAX-ACCESS not-accessible
    STATUS current
    DESCRIPTION
        "General information about a LACP port."
    INDEX { lacpInfoPortGeneralIndex }
    ::= { lacpInfoPortGeneralTable 1 }

LacpInfoPortGeneralTableEntry ::= SEQUENCE {
    lacpInfoPortGeneralIndex		PortNumber,
    lacpInfoPortLacpEna 		INTEGER,
    lacpInfoPortAdminEna	 	INTEGER,
    lacpInfoPortActSysId		DisplayString,
    lacpInfoPortActSysPrio		Integer32,
    lacpInfoPortActAdminKey 		Integer32,
    lacpInfoPortActOperKey 		Integer32,
    lacpInfoPortActPortNum 		Integer32,
    lacpInfoPortActPortPrio 		Integer32,
    lacpInfoPortIndivState 		INTEGER,
    lacpInfoSelAggrId 			Integer32,
    lacpInfoAttAggrId 			Integer32,
    lacpInfoPortReadyN 			INTEGER,
    lacpInfoPortNtt 			INTEGER,
    lacpInfoPortSelected 		INTEGER,
    lacpInfoPortMoved 			INTEGER,
    lacpInfoCollDetState 		INTEGER,
    lacpInfoPortRxState 		DisplayString, 
    lacpInfoPortMuxState 		DisplayString,
    lacpInfoPortPerState 		DisplayString,
    lacpInfoPortPerTraTimer		Integer32,
    lacpInfoPortCurWhileTimer		Integer32,
    lacpInfoPortOperState		INTEGER
    }

lacpInfoPortGeneralIndex OBJECT-TYPE
    SYNTAX PortNumber
    MAX-ACCESS read-only
    STATUS current
    DESCRIPTION
        "The port identifier."
    ::= { lacpInfoPortGeneralTableEntry 1 }

lacpInfoPortLacpEna OBJECT-TYPE 
    SYNTAX  INTEGER {
        true(1),
        false(2)
        }
    MAX-ACCESS  read-only
    STATUS  current
    DESCRIPTION
        "LACP enabled on port"
    ::= { lacpInfoPortGeneralTableEntry 2 }

lacpInfoPortAdminEna OBJECT-TYPE 
    SYNTAX  INTEGER {
        true(1),
        false(2)
        }
    MAX-ACCESS  read-only
    STATUS  current
    DESCRIPTION
        "LACP port admin enabled"
    ::= { lacpInfoPortGeneralTableEntry 3 }

lacpInfoPortActSysId OBJECT-TYPE
    SYNTAX  DisplayString
    MAX-ACCESS  read-only
    STATUS  current
    DESCRIPTION
        "LACP port actor system ID"
    ::= { lacpInfoPortGeneralTableEntry 4 }

lacpInfoPortActSysPrio OBJECT-TYPE
    SYNTAX  Integer32
    MAX-ACCESS  read-only
    STATUS  current
    DESCRIPTION
        "LACP port actor system priority"
    ::= { lacpInfoPortGeneralTableEntry 5 }

lacpInfoPortActAdminKey OBJECT-TYPE
    SYNTAX  Integer32
    MAX-ACCESS  read-only
    STATUS  current
    DESCRIPTION
        "LACP port actor admin key"
    ::= { lacpInfoPortGeneralTableEntry 6 }

lacpInfoPortActOperKey OBJECT-TYPE
    SYNTAX  Integer32
    MAX-ACCESS  read-only
    STATUS  current
    DESCRIPTION
        "LACP port actor oper key"
    ::= { lacpInfoPortGeneralTableEntry 7 }

lacpInfoPortActPortNum OBJECT-TYPE
    SYNTAX  Integer32
    MAX-ACCESS  read-only
    STATUS  current
    DESCRIPTION
        "LACP port number"
    ::= { lacpInfoPortGeneralTableEntry 8 }

lacpInfoPortActPortPrio OBJECT-TYPE
    SYNTAX  Integer32
    MAX-ACCESS  read-only
    STATUS  current
    DESCRIPTION
        "LACP port priority"
    ::= { lacpInfoPortGeneralTableEntry 9 }

lacpInfoPortIndivState OBJECT-TYPE 
    SYNTAX  INTEGER {
        true(1),
        false(2)
        }
    MAX-ACCESS  read-only
    STATUS  current
    DESCRIPTION
        "LACP port individual state"
    ::= { lacpInfoPortGeneralTableEntry 10 }

lacpInfoSelAggrId OBJECT-TYPE 
    SYNTAX  Integer32
    MAX-ACCESS  read-only
    STATUS  current
    DESCRIPTION
        "LACP port selected aggregator ID"
    ::= { lacpInfoPortGeneralTableEntry 11 }

lacpInfoAttAggrId OBJECT-TYPE 
    SYNTAX  Integer32
    MAX-ACCESS  read-only
    STATUS  current
    DESCRIPTION
        "LACP port attached aggregator ID"
    ::= { lacpInfoPortGeneralTableEntry 12 }

lacpInfoPortReadyN OBJECT-TYPE
    SYNTAX  INTEGER {
        true(1),
        false(2)
        }
    MAX-ACCESS read-only
    STATUS  current
    DESCRIPTION
        "True value for Ready_N flag indicates that the wait while timer 
         has expired and it is waiting to attach to an aggregator. 
         There is one Ready_N value for each port."
    ::= { lacpInfoPortGeneralTableEntry 13 }

lacpInfoPortNtt OBJECT-TYPE
    SYNTAX  INTEGER {
        true(1),
        false(2)
        }
    MAX-ACCESS read-only
    STATUS  current
    DESCRIPTION
        "Need to transmit flag. True indicates that there is new protocol 
         information that should be transmitted on the link."
    ::= { lacpInfoPortGeneralTableEntry 14 }

lacpInfoPortSelected OBJECT-TYPE
    SYNTAX  INTEGER {
        selected(1),
        unselected(2),
        standby(3)
        , suspended(4)
        , individual(5)
        }
    MAX-ACCESS  read-only
    STATUS  current
    DESCRIPTION
        "Selected flag value indicates that the selection logic has selected
         an appropriate Aggregator. A value of unselected indicates that no 
         aggregator is currently selected. A value of standby indicates that
         although the selection logic has selected an appropriate Aggregator,
         aggregation restrictions currently prevent the port from being 
         enabled as part of the aggregation, and so the port is being held
         in standby condition. 
         A value of suspended indicates that the port in a LACP port-channel 
         cannot be aggregated due to, for example, not receiveing LACPDU. 
         A value of individual indicates that the port works as a normal link-up 
         port due to not receiving LACPDU.
         " 
    ::= { lacpInfoPortGeneralTableEntry 15 }

lacpInfoPortMoved OBJECT-TYPE
    SYNTAX  INTEGER {
        true(1),
        false(2)
        }
    MAX-ACCESS read-only
    STATUS  current
    DESCRIPTION
        "Port Moved flag is set to true if the receive machine for a port 
         is in the port_disabled state, and the combination of partner oper
         system and partner oper port number in use by the port has been 
         used by received in an incoming LACPDU on a different port."
    ::= { lacpInfoPortGeneralTableEntry 16 }

lacpInfoCollDetState OBJECT-TYPE 
    SYNTAX  INTEGER {
        on(1),
        off(2)
        }
    MAX-ACCESS  read-only
    STATUS  current
    DESCRIPTION
        "LACP port collision and detection state"
    ::= { lacpInfoPortGeneralTableEntry 17 }

lacpInfoPortRxState OBJECT-TYPE 
    SYNTAX  DisplayString 
    MAX-ACCESS  read-only
    STATUS  current
    DESCRIPTION
        "LACP port RX machine state"
    ::= { lacpInfoPortGeneralTableEntry 18 }

lacpInfoPortMuxState OBJECT-TYPE 
    SYNTAX  DisplayString
    MAX-ACCESS  read-only
    STATUS  current
    DESCRIPTION
        "LACP port Mux machine state"
    ::= { lacpInfoPortGeneralTableEntry 19 }

lacpInfoPortPerState OBJECT-TYPE 
    SYNTAX  DisplayString
    MAX-ACCESS  read-only
    STATUS  current
    DESCRIPTION
        "LACP port periodic machine state"
    ::= { lacpInfoPortGeneralTableEntry 20 }

lacpInfoPortPerTraTimer OBJECT-TYPE
    SYNTAX  Integer32
    MAX-ACCESS  read-only
    STATUS  current
    DESCRIPTION
        "Periodic Transmit Timer"
    ::= { lacpInfoPortGeneralTableEntry 21 }

lacpInfoPortCurWhileTimer OBJECT-TYPE
    SYNTAX Integer32 
    MAX-ACCESS  read-only
    STATUS  current
    DESCRIPTION
        "Current While Timer"
    ::= { lacpInfoPortGeneralTableEntry 22 }

lacpInfoPortOperState OBJECT-TYPE
    SYNTAX  INTEGER {
        disabled(1),
        up(2),
        down(3)
        }
    MAX-ACCESS  read-only
    STATUS  current
    DESCRIPTION
        "The current operational state of LACP on the port."
    ::= { lacpInfoPortGeneralTableEntry 23 }


lacpInfoPortAdminTable OBJECT-TYPE
    SYNTAX SEQUENCE OF LacpInfoPortAdminTableEntry
    MAX-ACCESS not-accessible
    STATUS current
    DESCRIPTION
        "The table of LACP port admin information."
    ::= { lacpInfoPort 2 }

lacpInfoPortAdminTableEntry OBJECT-TYPE
    SYNTAX LacpInfoPortAdminTableEntry
    MAX-ACCESS not-accessible
    STATUS current
    DESCRIPTION
        "Admin information about a LACP port."
    INDEX { lacpInfoPortAdminIndex }
    ::= { lacpInfoPortAdminTable 1 }

LacpInfoPortAdminTableEntry ::= SEQUENCE {
    lacpInfoPortAdminIndex		PortNumber,
    lacpInfoPortActAdPortState 		DisplayString,
    lacpInfoPortActAdActiv 		INTEGER,
    lacpInfoPortActAdSync 		INTEGER,
    lacpInfoPortActAdDef 		INTEGER,
    lacpInfoPortActAdTimeout 		INTEGER,
    lacpInfoPortActAdColl 		INTEGER,
    lacpInfoPortActAdExp 		INTEGER,
    lacpInfoPortActAdAggr 		INTEGER,
    lacpInfoPortActAdDist 		INTEGER
    }

lacpInfoPortAdminIndex OBJECT-TYPE
    SYNTAX PortNumber
    MAX-ACCESS read-only
    STATUS current
    DESCRIPTION
        "The port identifier."
    ::= { lacpInfoPortAdminTableEntry 1 }


lacpInfoPortActAdPortState OBJECT-TYPE
    SYNTAX  DisplayString
    MAX-ACCESS  read-only
    STATUS  current
    DESCRIPTION
        "The state of Actor Administrator Port. This is a octet mask
         with the following bits: Activity, Synchronization, Defaulted, 
         Timeout, Collecting, Expired, Aggregation and Distributing.
         If all of them are 0 then the state is showed as 0x0, else it is
         displayed a blank state which mean is not a NULL state"
    ::= { lacpInfoPortAdminTableEntry 7 }

lacpInfoPortActAdActiv OBJECT-TYPE
    SYNTAX  INTEGER {
        active(1),
        passive(2)
        }
    MAX-ACCESS  read-only
    STATUS  current
    DESCRIPTION
        "The state of Actor Administrator Port Activity"
    ::= { lacpInfoPortAdminTableEntry 8 }

lacpInfoPortActAdSync OBJECT-TYPE
    SYNTAX  INTEGER {
        true(1),
        false(2)
        }
    MAX-ACCESS  read-only
    STATUS  current
    DESCRIPTION
        "The state of Actor Administrator Port Synchronization"
    ::= { lacpInfoPortAdminTableEntry 9 }

lacpInfoPortActAdDef OBJECT-TYPE
    SYNTAX  INTEGER {
        true(1),
        false(2)
        }
    MAX-ACCESS  read-only
    STATUS  current
    DESCRIPTION
        "The state of Actor Administrator Port Defaulted"
    ::= { lacpInfoPortAdminTableEntry 10 }

lacpInfoPortActAdTimeout OBJECT-TYPE 
    SYNTAX  INTEGER {
        short(1),
        long(2)
        }
    MAX-ACCESS  read-only
    STATUS  current
    DESCRIPTION
        "The state of Actor Administrator Port Timeout"
    ::= { lacpInfoPortAdminTableEntry 11 }

lacpInfoPortActAdColl OBJECT-TYPE 
    SYNTAX  INTEGER {
        true(1),
        false(2)
        }
    MAX-ACCESS  read-only
    STATUS  current
    DESCRIPTION
        "The state of Actor Administrator Port Collecting"
    ::= { lacpInfoPortAdminTableEntry 12 }

lacpInfoPortActAdExp OBJECT-TYPE 
    SYNTAX  INTEGER {
        true(1),
        false(2)
        }
    MAX-ACCESS  read-only
    STATUS  current
    DESCRIPTION
        "The state of Actor Administrator Port Expired"
    ::= { lacpInfoPortAdminTableEntry 13 }

lacpInfoPortActAdAggr OBJECT-TYPE 
    SYNTAX  INTEGER {
        true(1),
        false(2)
        }
    MAX-ACCESS  read-only
    STATUS  current
    DESCRIPTION
        "The state of Actor Administrator Port Aggregation"
    ::= { lacpInfoPortAdminTableEntry 14 }

lacpInfoPortActAdDist OBJECT-TYPE 
    SYNTAX  INTEGER {
        true(1),
        false(2)
        }
    MAX-ACCESS  read-only
    STATUS  current
    DESCRIPTION
        "The state of Actor Administrator Port Distributing"
    ::= { lacpInfoPortAdminTableEntry 15 }



lacpInfoPortOperTable OBJECT-TYPE
    SYNTAX SEQUENCE OF LacpInfoPortOperTableEntry
    MAX-ACCESS not-accessible
    STATUS current
    DESCRIPTION
        "The table of LACP port oper information."
    ::= { lacpInfoPort 3 }

lacpInfoPortOperTableEntry OBJECT-TYPE
    SYNTAX LacpInfoPortOperTableEntry
    MAX-ACCESS not-accessible
    STATUS current
    DESCRIPTION
        "Oper information about a LACP port."
    INDEX { lacpInfoPortOperIndex }
    ::= { lacpInfoPortOperTable 1 }

LacpInfoPortOperTableEntry ::= SEQUENCE {
    lacpInfoPortOperIndex		PortNumber,
    lacpInfoPortPartOpSysPrio 		Integer32,
    lacpInfoPortPartOpSysId 		DisplayString,
    lacpInfoPortPartOpKey 		Integer32,
    lacpInfoPortPartOpPortNum 		Integer32,
    lacpInfoPortPartOpPortPrio 		Integer32,
    lacpInfoPortActOpPortState 		DisplayString,
    lacpInfoPortActOpActiv 		INTEGER,
    lacpInfoPortActOpSync 		INTEGER,
    lacpInfoPortActOpDef 		INTEGER,
    lacpInfoPortActOpTimeout 		INTEGER,
    lacpInfoPortActOpColl 		INTEGER,
    lacpInfoPortActOpExp 		INTEGER,
    lacpInfoPortActOpAggr 		INTEGER,
    lacpInfoPortActOpDist 		INTEGER,
    lacpInfoPortPartOpPortState 	DisplayString,
    lacpInfoPortPartOpActiv 		INTEGER,
    lacpInfoPortPartOpSync 		INTEGER,
    lacpInfoPortPartOpDef 		INTEGER,
    lacpInfoPortPartOpTimeout 		INTEGER,
    lacpInfoPortPartOpColl 		INTEGER,
    lacpInfoPortPartOpExp 		INTEGER,
    lacpInfoPortPartOpAggr 		INTEGER,
    lacpInfoPortPartOpDist 		INTEGER 
    }

lacpInfoPortOperIndex OBJECT-TYPE
    SYNTAX PortNumber
    MAX-ACCESS read-only
    STATUS current
    DESCRIPTION
        "The port identifier."
    ::= { lacpInfoPortOperTableEntry 1 }

lacpInfoPortPartOpSysPrio OBJECT-TYPE
    SYNTAX  Integer32
    MAX-ACCESS  read-only
    STATUS  current
    DESCRIPTION
        "The value of Partner Operator Port System Priority"
    ::= { lacpInfoPortOperTableEntry 2 }

lacpInfoPortPartOpSysId OBJECT-TYPE
    SYNTAX  DisplayString
    MAX-ACCESS  read-only
    STATUS  current
    DESCRIPTION
        "The value of Partner Operator Port System ID"
    ::= { lacpInfoPortOperTableEntry 3 }

lacpInfoPortPartOpKey OBJECT-TYPE
    SYNTAX  Integer32
    MAX-ACCESS  read-only
    STATUS  current
    DESCRIPTION
        "The value of Partner Operator Port Key"
    ::= { lacpInfoPortOperTableEntry 4 }

lacpInfoPortPartOpPortNum OBJECT-TYPE
    SYNTAX  Integer32
    MAX-ACCESS  read-only
    STATUS  current
    DESCRIPTION
        "The Partner Operator Port Number"
    ::= { lacpInfoPortOperTableEntry 5 }

lacpInfoPortPartOpPortPrio OBJECT-TYPE
    SYNTAX  Integer32
    MAX-ACCESS  read-only
    STATUS  current
    DESCRIPTION
        "The value of Partner Operator Port Priority"
    ::= { lacpInfoPortOperTableEntry 6 }

lacpInfoPortActOpPortState OBJECT-TYPE
    SYNTAX  DisplayString
    MAX-ACCESS  read-only
    STATUS  current
    DESCRIPTION
        "The state of Actor Operator Port. This is a octet mask
         with the following bits: Activity, Synchronization, Defaulted, 
         Timeout, Collecting, Expired, Aggregation and Distributing.
         If all of them are 0 then the state is showed as 0x0, else it is
         displayed a blank state which mean is not a NULL state"
    ::= { lacpInfoPortOperTableEntry 7 }

lacpInfoPortActOpActiv OBJECT-TYPE
    SYNTAX  INTEGER {
        active(1),
        passive(2)
        }
    MAX-ACCESS  read-only
    STATUS  current
    DESCRIPTION
        "The state of Actor Operator Port Activity"
    ::= { lacpInfoPortOperTableEntry 8 }

lacpInfoPortActOpSync OBJECT-TYPE
    SYNTAX  INTEGER {
        true(1),
        false(2)
        }
    MAX-ACCESS  read-only
    STATUS  current
    DESCRIPTION
        "The state of Actor Operator Port Synchronization"
    ::= { lacpInfoPortOperTableEntry 9 }

lacpInfoPortActOpDef OBJECT-TYPE
    SYNTAX  INTEGER {
        true(1),
        false(2)
        }
    MAX-ACCESS  read-only
    STATUS  current
    DESCRIPTION
        "The state of Actor Operator Port Defaulted"
    ::= { lacpInfoPortOperTableEntry 10 }

lacpInfoPortActOpTimeout OBJECT-TYPE 
    SYNTAX  INTEGER {
        short(1),
        long(2)
        }
    MAX-ACCESS  read-only
    STATUS  current
    DESCRIPTION
        "The state of Actor Operator Port Timeout"
    ::= { lacpInfoPortOperTableEntry 11 }

lacpInfoPortActOpColl OBJECT-TYPE 
    SYNTAX  INTEGER {
        true(1),
        false(2)
        }
    MAX-ACCESS  read-only
    STATUS  current
    DESCRIPTION
        "The state of Actor Operator Port Collecting"
    ::= { lacpInfoPortOperTableEntry 12 }

lacpInfoPortActOpExp OBJECT-TYPE 
    SYNTAX  INTEGER {
        true(1),
        false(2)
        }
    MAX-ACCESS  read-only
    STATUS  current
    DESCRIPTION
        "The state of Actor Operator Port Expired"
    ::= { lacpInfoPortOperTableEntry 13 }

lacpInfoPortActOpAggr OBJECT-TYPE 
    SYNTAX  INTEGER {
        true(1),
        false(2)
        }
    MAX-ACCESS  read-only
    STATUS  current
    DESCRIPTION
        "The state of Actor Operator Port Aggregation"
    ::= { lacpInfoPortOperTableEntry 14 }

lacpInfoPortActOpDist OBJECT-TYPE 
    SYNTAX  INTEGER {
        true(1),
        false(2)
        }
    MAX-ACCESS  read-only
    STATUS  current
    DESCRIPTION
        "The state of Actor Operator Port Distributing"
    ::= { lacpInfoPortOperTableEntry 15 }

lacpInfoPortPartOpPortState OBJECT-TYPE
    SYNTAX  DisplayString
    MAX-ACCESS  read-only
    STATUS  current
    DESCRIPTION
        "The state of Partner Operator Port. This is a octet mask
         with the following bits: Activity, Synchronization, Defaulted, 
         Timeout, Collecting, Expired, Aggregation and Distributing.
         If all of them are 0 then the state is showed as 0x0, else it is
         displayed a blank state which mean is not a NULL state"
    ::= { lacpInfoPortOperTableEntry 16 }

lacpInfoPortPartOpActiv OBJECT-TYPE
    SYNTAX  INTEGER {
        active(1),
        passive(2)
        }
    MAX-ACCESS  read-only
    STATUS  current
    DESCRIPTION
        "The state of Partner Operator Port Activity"
    ::= { lacpInfoPortOperTableEntry 17 }

lacpInfoPortPartOpSync OBJECT-TYPE
    SYNTAX  INTEGER {
        true(1),
        false(2)
        }
    MAX-ACCESS  read-only
    STATUS  current
    DESCRIPTION
        "The state of Partner Operator Port Synchronization"
    ::= { lacpInfoPortOperTableEntry 18 }

lacpInfoPortPartOpDef OBJECT-TYPE
    SYNTAX  INTEGER {
        true(1),
        false(2)
        }
    MAX-ACCESS  read-only
    STATUS  current
    DESCRIPTION
        "The state of Partner Operator Port Defaulted"
    ::= { lacpInfoPortOperTableEntry 19 }

lacpInfoPortPartOpTimeout OBJECT-TYPE 
    SYNTAX  INTEGER {
        short(1),
        long(2)
        }
    MAX-ACCESS  read-only
    STATUS  current
    DESCRIPTION
        "The state of Partner Operator Port Timeout"
    ::= { lacpInfoPortOperTableEntry 20 }

lacpInfoPortPartOpColl OBJECT-TYPE 
    SYNTAX  INTEGER {
        true(1),
        false(2)
        }
    MAX-ACCESS  read-only
    STATUS  current
    DESCRIPTION
        "The state of Partner Operator Port Collecting"
    ::= { lacpInfoPortOperTableEntry 21 }

lacpInfoPortPartOpExp OBJECT-TYPE 
    SYNTAX  INTEGER {
        true(1),
        false(2)
        }
    MAX-ACCESS  read-only
    STATUS  current
    DESCRIPTION
        "The state of Partner Operator Port Expired"
    ::= { lacpInfoPortOperTableEntry 22 }

lacpInfoPortPartOpAggr OBJECT-TYPE 
    SYNTAX  INTEGER {
        true(1),
        false(2)
        }
    MAX-ACCESS  read-only
    STATUS  current
    DESCRIPTION
        "The state of Partner Operator Port Aggregation"
    ::= { lacpInfoPortOperTableEntry 23 }

lacpInfoPortPartOpDist OBJECT-TYPE 
    SYNTAX  INTEGER {
        true(1),
        false(2)
        }
    MAX-ACCESS  read-only
    STATUS  current
    DESCRIPTION
        "The state of Partner Operator Port Distributing"
    ::= { lacpInfoPortOperTableEntry 24 }


-- CIST Information

cistRoot OBJECT-TYPE
    SYNTAX  BridgeId
    MAX-ACCESS  read-only
    STATUS  current
    DESCRIPTION
        "The bridge identifier of the Root of the common spanning
         tree as determined by the Spanning Tree Protocol
         as executed by this node.  This value is used as
         the CIST Root Identifier parameter in all Configuration
         Bridge PDUs originated by this node."
    ::= { cistGeneralInfo 1 } 

cistRootPathCost OBJECT-TYPE
    SYNTAX  Integer32
    MAX-ACCESS  read-only
    STATUS  current
    DESCRIPTION
        "The cost of the path to the CIST Root as seen from this bridge."
    ::= { cistGeneralInfo 2 } 

cistRootPort OBJECT-TYPE
    SYNTAX  PortNumber
    MAX-ACCESS  read-only
    STATUS  current
    DESCRIPTION 
        "The Port Number of the Port which offers the lowest path cost from 
        this bridge to the CIST Root Bridge."
    ::= { cistGeneralInfo 3 } 

cistBridgeHelloTime OBJECT-TYPE
    SYNTAX  Integer32
    MAX-ACCESS  read-only
    STATUS  current
    DESCRIPTION
        "The amount of time between the transmission of Configuration bridge
         PDUs in seconds."
    ::= { cistGeneralInfo 4 } 

cistBridgeMaxAge OBJECT-TYPE
    SYNTAX  Integer32
    MAX-ACCESS  read-only
    STATUS  current
    DESCRIPTION
        "The value in seconds that all bridges use for MaxAge when this bridge
         is acting as the root."
    ::= { cistGeneralInfo 5 } 

cistBridgeForwardDelay OBJECT-TYPE
    SYNTAX  Integer32
    MAX-ACCESS  read-only
    STATUS  current
    DESCRIPTION
        "The value in seconds that all bridges use for ForwardDelay when this 
         bridge is acting as the root."
    ::= { cistGeneralInfo 6 } 

cistRegionalRoot OBJECT-TYPE
    SYNTAX  BridgeId
    MAX-ACCESS  read-only
    STATUS  current
    DESCRIPTION
        "The bridge identifier of the Root of the Multiple
         spanning tree region as determined by the Spanning Tree
         Protocol as executed by this node.  This value is used as
         the CIST Regional Root Identifier parameter in all Configuration
         Bridge PDUs originated by this node."
   ::= { cistGeneralInfo 7 } 

cistRegionalPathCost OBJECT-TYPE
    SYNTAX  Integer32
    MAX-ACCESS  read-only
    STATUS  current
    DESCRIPTION
        "The Cost of the path to the CIST Regional Root as seen from this 
         bridge."
   ::= { cistGeneralInfo 8 } 

mstpDigest OBJECT-TYPE
    SYNTAX  DisplayString (SIZE(0..63))
    MAX-ACCESS  read-only
    STATUS  current
    DESCRIPTION
        "The digest of the mstp."
    ::= { cistGeneralInfo 9 }


-- CIST Port Information Table
cistInfoPortTable OBJECT-TYPE
    SYNTAX SEQUENCE OF CistInfoPortTableEntry
    MAX-ACCESS not-accessible
    STATUS current
    DESCRIPTION
        "The table of CIST Port information."
    ::= { cistInfo 2 }

cistInfoPortTableEntry OBJECT-TYPE
    SYNTAX CistInfoPortTableEntry
    MAX-ACCESS not-accessible
    STATUS current
    DESCRIPTION
        "Information about a particular CIST Port."
    INDEX { cistInfoPortIndex }
    ::= { cistInfoPortTable 1 }

CistInfoPortTableEntry ::= SEQUENCE {
    cistInfoPortIndex            PortNumber,
    cistInfoPortPriority         Integer32,
    cistInfoPortPathCost         Integer32,
    cistInfoPortState            INTEGER,
    cistInfoPortRole             INTEGER,
    cistInfoPortDesignatedBridge BridgeId,
    cistInfoPortDesignatedPort   OCTET STRING,
    cistInfoPortLinkType         INTEGER,
    cistInfoPortHelloTime        Integer32,
    cistInfoPortEdge              INTEGER
    }

cistInfoPortIndex OBJECT-TYPE
    SYNTAX PortNumber
    MAX-ACCESS read-only
    STATUS current
    DESCRIPTION
        "The port number of the port for which this entry contains spanning
         tree configuration."
    ::= { cistInfoPortTableEntry 1 }

cistInfoPortPriority OBJECT-TYPE
    SYNTAX Integer32
    MAX-ACCESS read-only
    STATUS current
    DESCRIPTION
        "The four most significant bits of the Port Identifier of the 
         Spanning Tree instance can be modified by setting this value."
    ::= { cistInfoPortTableEntry 2 }

cistInfoPortPathCost OBJECT-TYPE
    SYNTAX Integer32
    MAX-ACCESS read-only
    STATUS current
    DESCRIPTION
        "The contribution of this port to the path cost of paths towards 
         the CIST Root which include this port."
    ::= { cistInfoPortTableEntry 3 }

cistInfoPortState OBJECT-TYPE
    SYNTAX INTEGER {
        disabled (1),
        discarding (2),
        learning (4),
        forwarding (5)
        }
    MAX-ACCESS read-only
    STATUS current
    DESCRIPTION
        "Current state of the Port as defined by the Common    
         spanning tree protocol." 
    ::= { cistInfoPortTableEntry 4 }

cistInfoPortRole OBJECT-TYPE
    SYNTAX INTEGER {
        disabled(1),
        alternate(2),
        backup(3),
        root(4),
        designated(5),
        master(6),
        unknown(7)
        }
    MAX-ACCESS read-only
    STATUS current
    DESCRIPTION
          "Selected Port Role of the port for this spanning tree instance."
    ::= { cistInfoPortTableEntry 5 }

cistInfoPortDesignatedBridge OBJECT-TYPE
    SYNTAX  BridgeId
    MAX-ACCESS  read-only
    STATUS  current
    DESCRIPTION
        "The unique Bridge Identifier of the bridge which this port  
         considers to be the Designated Bridge for the port's segment."   
    ::= { cistInfoPortTableEntry 6 }

cistInfoPortDesignatedPort OBJECT-TYPE
    SYNTAX  OCTET STRING (SIZE (2))
    MAX-ACCESS  read-only
    STATUS  current
      DESCRIPTION
          "The Port identifier of the port on the Designated Bridge    
           for this port's segment."                                           
    ::= { cistInfoPortTableEntry 7 }

cistInfoPortLinkType OBJECT-TYPE
    SYNTAX INTEGER {
        p2p(1),
        shared(2),
        unknown(3)
        }
    MAX-ACCESS read-only
    STATUS current
    DESCRIPTION
        "The point-to-point status of the LAN segment attached 
         to this port.  A value of p2p (1) indicates that this port is being
         treated as if it is connected to a point-to-point link. 
         A value of shared(2) indicates that this port is being treated as 
         having a shared media connection."
    ::= { cistInfoPortTableEntry 8 }

cistInfoPortHelloTime OBJECT-TYPE
    SYNTAX Integer32
    MAX-ACCESS read-only
    STATUS current
    DESCRIPTION
        "CIST port Hello Time"
    ::= { cistInfoPortTableEntry 9 }

cistInfoPortEdge OBJECT-TYPE
    SYNTAX  INTEGER {
        enabled(1),
        disabled(2)
        }
    MAX-ACCESS  read-only
    STATUS  current
    DESCRIPTION
        "The port is an edge port or not. Returns disabled(2) when the port is
         not an edge port and returns enabled(1) when it is an edge port."
    ::= { cistInfoPortTableEntry 10 }


-- General Information



-- VLAN information
vlanInfoTable OBJECT-TYPE
    SYNTAX SEQUENCE OF VlanInfoTableEntry
    MAX-ACCESS not-accessible
    STATUS current
    DESCRIPTION
        "The table of VLAN information."
    ::= { vlanInfo 1 }

vlanInfoTableEntry OBJECT-TYPE
    SYNTAX VlanInfoTableEntry
    MAX-ACCESS not-accessible
    STATUS current
    DESCRIPTION
        "Information about a particular VLAN."
    INDEX { vlanInfoId }
    ::= { vlanInfoTable 1 }

VlanInfoTableEntry ::= SEQUENCE {
    vlanInfoId                INTEGER,
    vlanInfoName 	      DisplayString,
    vlanInfoStatus            INTEGER,
    vlanInfoPorts             OCTET STRING
    }

vlanInfoId OBJECT-TYPE
    SYNTAX  INTEGER  (1..4090)
    MAX-ACCESS read-only
    STATUS current
    DESCRIPTION
        "The VLAN identifier."
    ::= { vlanInfoTableEntry 1 }

vlanInfoName OBJECT-TYPE
    SYNTAX  DisplayString (SIZE(0..32))
    MAX-ACCESS  read-only
    STATUS  current
    DESCRIPTION
        "The VLAN name."
    ::= { vlanInfoTableEntry 2 }

vlanInfoStatus OBJECT-TYPE
    SYNTAX  INTEGER  {
	enabled(2),
	disabled(3)
	}
    MAX-ACCESS  read-only
    STATUS  current
    DESCRIPTION
        "Enable or disable, VLAN state information"
    ::= { vlanInfoTableEntry 3 }




vlanInfoPorts OBJECT-TYPE
    SYNTAX  OCTET STRING
    MAX-ACCESS  read-only
    STATUS  current
    DESCRIPTION
        "The port list information in the VLAN. The ports are presented 
         in bitmap format.
	 in receiving order:

	     OCTET 1  OCTET 2  .....
             xxxxxxxx xxxxxxxx ..... 
             ||    || |_ port 8
             ||    ||  
             ||    ||___ port 7
             ||    |____ port 6
             ||      .    .   .
             ||_________ port 1
             |__________ reserved

         where x : 1 - The represented port belongs to the VLAN
		   0 - The represented port does not belong to the VLAN"
    ::= { vlanInfoTableEntry 7 }

-- L2 Operational commands




-- ----------------------------------------------------------------------------
--                                                                           --
--                    Virtual Link Aggregation (VLAG)                        --
--                                                                           --
-- ----------------------------------------------------------------------------

-- ----------------------------------------------------------------------------
-- Global VLAG Configuration
-- ----------------------------------------------------------------------------
vlagCurIslCfgPortChannel         OBJECT-TYPE
    SYNTAX      INTEGER (0..65535)
    MAX-ACCESS  read-only
    STATUS      current
    DESCRIPTION
                "Current vLAG ISL portchannel"
    DEFVAL      { 0 }
    ::= { vlagIslCfg 1 }

vlagNewIslCfgPortChannel         OBJECT-TYPE
    SYNTAX      INTEGER (0..65535)
    MAX-ACCESS  read-write
    STATUS      current
    DESCRIPTION
                "This object is used to change the vLAG ISL portchannel."
    DEFVAL      { 0 }
    ::= { vlagIslCfg 2 }

vlagCurIslCfgAdminKey         OBJECT-TYPE
    SYNTAX      INTEGER (0..65535)
    MAX-ACCESS  read-only
    STATUS      current
    DESCRIPTION
                "Current vLAG ISL admin key."
    DEFVAL      { 0 }
    ::= { vlagIslCfg 3 }

vlagNewIslCfgAdminKey         OBJECT-TYPE
    SYNTAX      INTEGER (0..65535)
    MAX-ACCESS  read-write
    STATUS      current
    DESCRIPTION
                "This object is used to change the vLAG ISL admin key."
    DEFVAL      { 0 }
    ::= { vlagIslCfg 4 }

vlagCurCfgSwitchPriority         OBJECT-TYPE
    SYNTAX      INTEGER (0..65535)
    MAX-ACCESS  read-only
    STATUS      current
    DESCRIPTION
                "Current vLAG switch priority"
    DEFVAL      { 0 }
    ::= { vlagCfg 4 }

vlagNewCfgSwitchPriority         OBJECT-TYPE
    SYNTAX      INTEGER (0..65535)
    MAX-ACCESS  read-write
    STATUS      current
    DESCRIPTION
                "This object is used to change the vLAG priority of this switch."
    DEFVAL      { 0 }
    ::= { vlagCfg 5 }

-- Static Trunk table
vlagCurCfgTrunkTable             OBJECT-TYPE
    SYNTAX      SEQUENCE OF VlagCurCfgTrunkTableEntry
    MAX-ACCESS  not-accessible
    STATUS      current
    DESCRIPTION
                "A table of objects of the vLAG groups configured in this
                 switch."
    ::= { vlagCfg 6 }

vlagCurCfgTrunkTableEntry        OBJECT-TYPE
    SYNTAX      VlagCurCfgTrunkTableEntry
    MAX-ACCESS  not-accessible
    STATUS      current
    DESCRIPTION
                "The configuration objects for an vLAG group."
    INDEX       { vlagCurCfgTrunkIndex }
    ::= { vlagCurCfgTrunkTable 1 }

VlagCurCfgTrunkTableEntry ::=    SEQUENCE {
    vlagCurCfgTrunkIndex              Integer32,
    vlagCurCfgTrunkState              INTEGER
    }

vlagCurCfgTrunkIndex             OBJECT-TYPE
    SYNTAX      Integer32
    MAX-ACCESS  read-only
    STATUS      current
    DESCRIPTION
                "The identifier of the trunk group."
    ::= { vlagCurCfgTrunkTableEntry 1 }

vlagCurCfgTrunkState             OBJECT-TYPE
    SYNTAX      INTEGER {
                    enabled(1),
                    disabled(2)
                }
    MAX-ACCESS  read-only
    STATUS      current
    DESCRIPTION "The current administrative state of the vLAG group."
    DEFVAL      { disabled }
    ::= { vlagCurCfgTrunkTableEntry 2 }

vlagNewCfgTrunkTable             OBJECT-TYPE
    SYNTAX      SEQUENCE OF VlagNewCfgTrunkTableEntry
    MAX-ACCESS  not-accessible
    STATUS      current
    DESCRIPTION
                "A table of objects of the vLAG groups configured in this
                 switch."
    ::= { vlagCfg 7 }

vlagNewCfgTrunkTableEntry        OBJECT-TYPE
    SYNTAX      VlagNewCfgTrunkTableEntry
    MAX-ACCESS  not-accessible
    STATUS      current
    DESCRIPTION
                "The configuration objects for an vLAG group."
    INDEX       { vlagNewCfgTrunkIndex }
    ::= { vlagNewCfgTrunkTable 1 }

VlagNewCfgTrunkTableEntry ::=    SEQUENCE {
    vlagNewCfgTrunkIndex              Integer32,
    vlagNewCfgTrunkState              INTEGER
    }

vlagNewCfgTrunkIndex             OBJECT-TYPE
    SYNTAX      Integer32
    MAX-ACCESS  read-write
    STATUS      current
    DESCRIPTION
                "The identifier of the trunk group."
    ::= { vlagNewCfgTrunkTableEntry 1 }

vlagNewCfgTrunkState             OBJECT-TYPE
    SYNTAX      INTEGER {
                    enabled(1),
                    disabled(2)
                }
    MAX-ACCESS  read-write
    STATUS      current
    DESCRIPTION "The new administrative state of the vLAG group."
    DEFVAL      { disabled }
    ::= { vlagNewCfgTrunkTableEntry 2 }


-- Dynamic Trunk table
vlagCurCfgLacpTable             OBJECT-TYPE
    SYNTAX      SEQUENCE OF VlagCurCfgLacpTableEntry
    MAX-ACCESS  not-accessible
    STATUS      current
    DESCRIPTION
                "A table of objects of the vLAG groups configured in this
                 switch."
    ::= { vlagCfg 8 }

vlagCurCfgLacpTableEntry        OBJECT-TYPE
    SYNTAX      VlagCurCfgLacpTableEntry
    MAX-ACCESS  not-accessible
    STATUS      current
    DESCRIPTION
                "The configuration objects for an vLAG group."
    INDEX       { vlagCurCfgLacpKey }
    ::= { vlagCurCfgLacpTable 1 }

VlagCurCfgLacpTableEntry ::=    SEQUENCE {
    vlagCurCfgLacpKey                INTEGER,
    vlagCurCfgLacpState              INTEGER
    }

vlagCurCfgLacpKey             OBJECT-TYPE
    SYNTAX      INTEGER (1..65535)
    MAX-ACCESS  read-only
    STATUS      current
    DESCRIPTION
                "The identifier of the trunk group."
    ::= { vlagCurCfgLacpTableEntry 1 }

vlagCurCfgLacpState             OBJECT-TYPE
    SYNTAX      INTEGER {
                    enabled(1),
                    disabled(2)
                }
    MAX-ACCESS  read-only
    STATUS      current
    DESCRIPTION "The current administrative state of the vLAG group."
    DEFVAL      { disabled }
    ::= { vlagCurCfgLacpTableEntry 2 }

vlagNewCfgLacpTable             OBJECT-TYPE
    SYNTAX      SEQUENCE OF VlagNewCfgLacpTableEntry
    MAX-ACCESS  not-accessible
    STATUS      current
    DESCRIPTION
                "A table of objects of the vLAG groups configured in this
                 switch."
    ::= { vlagCfg 9 }

vlagNewCfgLacpTableEntry        OBJECT-TYPE
    SYNTAX      VlagNewCfgLacpTableEntry
    MAX-ACCESS  not-accessible
    STATUS      current
    DESCRIPTION
                "The configuration objects for an vLAG group."
    INDEX       { vlagNewCfgLacpKey }
    ::= { vlagNewCfgLacpTable 1 }

VlagNewCfgLacpTableEntry ::=    SEQUENCE {
    vlagNewCfgLacpKey                INTEGER,
    vlagNewCfgLacpState              INTEGER
    }

vlagNewCfgLacpKey             OBJECT-TYPE
    SYNTAX      INTEGER (1..65535)
    MAX-ACCESS  read-only
    STATUS      current
    DESCRIPTION
                "The identifier of the trunk group."
    ::= { vlagNewCfgLacpTableEntry 1 }

vlagNewCfgLacpState             OBJECT-TYPE
    SYNTAX      INTEGER {
                    enabled(1),
                    disabled(2)
                }
    MAX-ACCESS  read-write
    STATUS      current
    DESCRIPTION "The new administrative state of the vLAG group."
    DEFVAL      { disabled }
    ::= { vlagNewCfgLacpTableEntry 2 }

vlagCurCfgHlthchkPeerIp            OBJECT-TYPE
    SYNTAX      IpAddress
    MAX-ACCESS  read-only
    STATUS      current
    DESCRIPTION
                "The current Health check Peer ip address."
    DEFVAL { '00000000'h }    -- 0.0.0.0
    ::= { vlagCfg 10 }

vlagNewCfgHlthchkPeerIp            OBJECT-TYPE
    SYNTAX      IpAddress
    MAX-ACCESS  read-write
    STATUS      current
    DESCRIPTION
                "The New Health check Peer ip address."
    DEFVAL { '00000000'h }    -- 0.0.0.0
    ::= { vlagCfg 11 }

vlagCurCfgTierId                    OBJECT-TYPE
    SYNTAX      INTEGER (0..512)
    MAX-ACCESS  read-only
    STATUS      current
    DESCRIPTION
                "Current vLAG Tier ID"
    DEFVAL      { 0 }
    ::= { vlagCfg 12 }

vlagNewCfgTierId                    OBJECT-TYPE
    SYNTAX      INTEGER (0..512)
    MAX-ACCESS  read-write
    STATUS      current
    DESCRIPTION
                "This object is used to change the vLAG Tier ID of this switch.
                vLAG consist of 2 vLAG peer switches connected by ISL link, the
                system formed by the switches is referred to as a vLAG tier.
                This object is used to specify the vLAG tier. And the tier id 
                is used to generate vLAG system MAC."
    DEFVAL      { 0 }
    ::= { vlagCfg 13 }

vlagCurCfgStartupDelayInterval            OBJECT-TYPE
    SYNTAX      INTEGER (0..3600)
    MAX-ACCESS  read-only
    STATUS      current
    DESCRIPTION
                "Current vLAG Startup delay interval"
    DEFVAL      { 120 }
    ::= { vlagCfg 14 }

vlagNewCfgStartupDelayInterval            OBJECT-TYPE
    SYNTAX      INTEGER (0..3600)
    MAX-ACCESS  read-write
    STATUS      current
    DESCRIPTION
                "This object is used to change the vLAG startup Delay Timer
                interval. The Timer is used to prevent traffic lost for the
                vLAG ports may be up before the ISL is up. The Timer is st-
                arted when the ISL is up and the role has been elected. And
                when the timer expires, all vLAG ports will be up. Before 
                and during the timer running, all vLAG ports should be err-
                disabled."
    DEFVAL      { 120 }
    ::= { vlagCfg 15 }

vlagCurCfgGlobalEnable             OBJECT-TYPE
    SYNTAX      INTEGER {
                    enabled(1),
                    disabled(2)
                } 
    MAX-ACCESS  read-only
    STATUS      current
    DESCRIPTION
                "Current vLAG global status on switch."
    DEFVAL      { disabled }
    ::= { vlagCfg 16 }

vlagNewCfgGlobalEnable             OBJECT-TYPE
    SYNTAX      INTEGER {
                    enabled(1),
                    disabled(2)
                }
    MAX-ACCESS  read-write
    STATUS      current
    DESCRIPTION
                "Set true to enable vLAG globally or
                 Set false to disable vLAG globally on switch."
    DEFVAL      { disabled }
    ::= { vlagCfg 17 }

vlagCurCfgHlthchkConnectRetryInterval    OBJECT-TYPE
    SYNTAX      INTEGER (1..300)
    MAX-ACCESS  read-only
    STATUS      current
    DESCRIPTION
                "In case of healtcheck TCP connection can not be 
                 established, interval at which the retry attempt 
                 will be made to connect to the peer."
    DEFVAL      { 30 }
    ::= { vlagCfg 18 }

vlagNewCfgHlthchkConnectRetryInterval    OBJECT-TYPE
    SYNTAX      INTEGER (1..300)
    MAX-ACCESS  read-write
    STATUS      current
    DESCRIPTION
                "In case of healtcheck TCP connection can not be 
                 established, interval at which the retry attempt 
                 will be made to connect to the peer."
    DEFVAL      { 30 }
    ::= { vlagCfg 19 }

vlagCurCfgHlthchkKeepaliveAttempts       OBJECT-TYPE
    SYNTAX      INTEGER (1..24)
    MAX-ACCESS  read-only
    STATUS      current
    DESCRIPTION
                "Number of keepalive attempts made before declaring 
                 peer is down. Within this time, atleast one of the 
                 keepalive message should have been received from the peer."
    DEFVAL      { 3 }
    ::= { vlagCfg 20 }

vlagNewCfgHlthchkKeepaliveAttempts           OBJECT-TYPE
    SYNTAX      INTEGER (1..24)
    MAX-ACCESS  read-write
    STATUS      current
    DESCRIPTION
                "Number of keepalive attempts made before declaring 
                 peer is down.Within this time, atleast one of the 
                 keepalive message should have been received from the peer."
    DEFVAL      { 3 }
    ::= { vlagCfg 21 }

vlagCurCfgHlthchkKeepaliveInterval     OBJECT-TYPE
    SYNTAX      INTEGER (2..300)
    MAX-ACCESS  read-only
    STATUS      current
    DESCRIPTION
                "Interval between keepalives sent over healthcheck 
                 TCP session to keep the session alive."
    DEFVAL      { 5 }
    ::= { vlagCfg 22 }

vlagNewCfgHlthchkKeepaliveInterval     OBJECT-TYPE
    SYNTAX      INTEGER (2..300)
    MAX-ACCESS  read-write
    STATUS      current
    DESCRIPTION
                "Interval between keepalives sent over healthcheck 
                 TCP session to keep the session alive."
    DEFVAL      { 5 }
    ::= { vlagCfg 23 }

vlagCurCfgAutoRecoveryInterval            OBJECT-TYPE
    SYNTAX      INTEGER (240..3600)
    MAX-ACCESS  read-only
    STATUS      current
    DESCRIPTION
                "Current vLAG Auto Recovery interval"
    DEFVAL      { 300 }
    ::= { vlagCfg 24 }

vlagNewCfgAutoRecoveryInterval            OBJECT-TYPE
    SYNTAX      INTEGER (240..3600)
    MAX-ACCESS  read-write
    STATUS      current
    DESCRIPTION
                "This object is used to change the vLAG Auto Recovery Timer
                interval. The Timer is used to prevent all vlag ports stay 
                in ErrDisabled state when booting two vLAG switches but one
                can not be up."
    DEFVAL      { 300 }
    ::= { vlagCfg 25 }


-- ----------------------------------------------------------------------------
-- Global VLAG Info
-- ----------------------------------------------------------------------------
vlagInfoState             OBJECT-TYPE
    SYNTAX      INTEGER  {
                    true(1),
                    false(2)
                   }
    MAX-ACCESS  read-only
    STATUS      current
    DESCRIPTION "The current running state of vLAG."
    ::= { vlagInfoSystem 1 }

vlagInfoAdminRole    OBJECT-TYPE
    SYNTAX INTEGER  {
                    unelected(0),
                    primary(1),
                    secondary(2)
                   }
    MAX-ACCESS read-only
    STATUS current
    DESCRIPTION
        "The current running role of the switch. 
        Role can be Primary(1), secondary(2) and unelected(3).
        Primary role indicates that the this switch controls the centralized
        operation in a vLAG domain. Secondary role indicates that this 
        switch can take up the primary role when primary is not available.
        Unelected indicates that switches are not detected by one another"
    ::= {vlagInfoSystem 2 }

vlagInfoISLId    OBJECT-TYPE
    SYNTAX Integer32
    MAX-ACCESS read-only
    STATUS current
    DESCRIPTION
        "vLAG ISL trunk id."
    ::= {vlagInfoSystem 3 }

vlagInfoLocalMac    OBJECT-TYPE
    SYNTAX PhysAddress
    MAX-ACCESS read-only
    STATUS current
    DESCRIPTION
        "Local vLAG MAC address."
    ::= {vlagInfoSystem 4 }

vlagInfoLocalPriority    OBJECT-TYPE
    SYNTAX Integer32
    MAX-ACCESS read-only
    STATUS current
    DESCRIPTION
        "Local vLAG Priority."
    ::= {vlagInfoSystem 5 }

vlagInfoRemoteMac    OBJECT-TYPE
    SYNTAX PhysAddress
    MAX-ACCESS read-only
    STATUS current
    DESCRIPTION
        "Remote vLAG MAC address."
    ::= {vlagInfoSystem 6 }

vlagInfoRemotePriority    OBJECT-TYPE
    SYNTAX Integer32
    MAX-ACCESS read-only
    STATUS current
    DESCRIPTION
        "Remote vLAG Priority."
    ::= {vlagInfoSystem 7 }

vlagInfoHlthchkStatus    OBJECT-TYPE
    SYNTAX      INTEGER  {
                    true(1),
                    false(2)
                   }
    MAX-ACCESS  read-only
    STATUS      current
    DESCRIPTION "The current health check running status."
    ::= { vlagInfoSystem 8 }

vlagInfoStartupDelayInterval    OBJECT-TYPE
    SYNTAX Integer32
    MAX-ACCESS read-only
    STATUS current
    DESCRIPTION
        "Startup Delay Timer Interval. The value may be 
        different from vlagCurCfgStartupDelayInterval for
        the configuration of the interval after the timer
        is started can only take effect next startup."
    ::= {vlagInfoSystem 9 }

vlagInfoStartupDelayStatus    OBJECT-TYPE
    SYNTAX INTEGER {
        unstarted(1),
        running(2),
        finished(3)
    }
    MAX-ACCESS read-only
    STATUS current
    DESCRIPTION
        "Startup Delay Timer Status."
    ::= {vlagInfoSystem 10 }

vlagInfoSystemMac   OBJECT-TYPE
    SYNTAX PhysAddress
    MAX-ACCESS read-only
    STATUS current
    DESCRIPTION
        "System vLAG MAC address"
    ::= {vlagInfoSystem 11 }

vlagInfoOperaRole    OBJECT-TYPE
    SYNTAX INTEGER  {
                    unelected(0),
                    primary(1),
                    secondary(2)
                   }
    MAX-ACCESS read-only
    STATUS current
    DESCRIPTION
        "vLAG switch operational role."
    ::= {vlagInfoSystem 12 }

vlagInfoAutoRecoveryInterval    OBJECT-TYPE
    SYNTAX Integer32
    MAX-ACCESS read-only
    STATUS current
    DESCRIPTION
        "Auto Recovery Timer Interval. The value may be 
        different from vlagCurCfgAutoRecoveryInterval for
        the configuration of the interval after the timer
        is started can only take effect next startup."
    ::= {vlagInfoSystem 13 }

vlagInfoAutoRecoveryStatus    OBJECT-TYPE
    SYNTAX INTEGER {
        unstarted(1),
        running(2),
        finished(3)
    }
    MAX-ACCESS read-only
    STATUS current
    DESCRIPTION
        "Auto Recovery Timer Status."
    ::= {vlagInfoSystem 14 }

vlagInfoInstanceTable             OBJECT-TYPE
    SYNTAX      SEQUENCE OF VlagInfoInstanceEntry
    MAX-ACCESS  not-accessible
    STATUS      current
    DESCRIPTION
                "A table of objects of the running vLAG instances." 
    ::= { vlagInfoGroup 1 }

vlagInfoInstanceEntry        OBJECT-TYPE
    SYNTAX      VlagInfoInstanceEntry
    MAX-ACCESS  not-accessible
    STATUS      current
    DESCRIPTION
                "The configuration objects for an vLAG group."
    INDEX       { vlagInstanceId }
    ::= { vlagInfoInstanceTable 1 }

VlagInfoInstanceEntry ::=    SEQUENCE {
    vlagInstanceId                   Integer32,
    vlagInstanceTrunkId              Integer32,
    vlagInstanceAdminKey             Integer32,
    vlagInstanceState                INTEGER
    }

vlagInstanceId             OBJECT-TYPE
    SYNTAX      Integer32
    MAX-ACCESS  read-only
    STATUS      current
    DESCRIPTION
                "The identifier of this instance."
    ::= { vlagInfoInstanceEntry 1 }

vlagInstanceTrunkId             OBJECT-TYPE
    SYNTAX      Integer32
    MAX-ACCESS  read-only
    STATUS      current
    DESCRIPTION
                "The trunk id of this vLAG instance."
    ::= { vlagInfoInstanceEntry 2 }

vlagInstanceAdminKey            OBJECT-TYPE
    SYNTAX      Integer32
    MAX-ACCESS  read-only
    STATUS      current
    DESCRIPTION
                "AdminKey of this vLAG instance. Applicable only incase of
    dynamic trunks."
    ::= { vlagInfoInstanceEntry 3 }

vlagInstanceState             OBJECT-TYPE
    SYNTAX      INTEGER {
                    down(1),
                    localUp(2),
                    remoteUp(3),
                    formed(4)
                }
    MAX-ACCESS  read-only
    STATUS      current
    DESCRIPTION "The current running state of the vLAG instance."
    DEFVAL      { down }
    ::= { vlagInfoInstanceEntry 4 }

vlagInfoIslId     OBJECT-TYPE
    SYNTAX        Integer32
    MAX-ACCESS    read-only
    STATUS        current
    DESCRIPTION   "vLAG ISL Id"
    ::= {vlagInfoIslGroup 1 }

vlagInfoIslProtocol  OBJECT-TYPE
    SYNTAX        INTEGER  {
                     static(1),
                     lacp(2)
                  }
    MAX-ACCESS    read-only
    STATUS        current
    DESCRIPTION   "vLAG ISL trunk group state
         Static - static trunk group
         Lacp - dynamic trunk group"
    ::= {vlagInfoIslGroup 3 }

vlagInfoIslPortchannel    OBJECT-TYPE
    SYNTAX        Integer32
    MAX-ACCESS    read-only
    STATUS        current 
    DESCRIPTION   "vLAG ISL portchannel number" 
    ::= {vlagInfoIslGroup 4 }

vlagInfoIslAdminkey    OBJECT-TYPE
    SYNTAX        Integer32
    MAX-ACCESS    read-only
    STATUS        current
    DESCRIPTION   "vLAG ISL lacp admin key"
    ::= {vlagInfoIslGroup 5 }

vlagInfoIslPorts    OBJECT-TYPE
    SYNTAX        OCTET STRING
    MAX-ACCESS    read-only
    STATUS        current
    DESCRIPTION   "The port list that forms the ISL. The ports are presented
                  in bitmap format.

             OCTET 1  OCTET 2  .....
             xxxxxxxx xxxxxxxx ..... 
             ||    || |_ port 8
             ||    ||  
             ||    ||___ port 7
             ||    |____ port 6
             ||      .    .   .
             ||_________ port 1
             |__________ reserved

         where x : 1 - The represented port belongs to ISL
                   0 - The represented port does not belong to ISL"
    ::= {vlagInfoIslGroup 6 }

vlagInfoIslPortState    OBJECT-TYPE
    SYNTAX        OCTET STRING
    MAX-ACCESS    read-only
    STATUS        current
    DESCRIPTION   "The ISL member ports' protocol state. The ports' protocol
                  state are presented in bitmap format.

             OCTET 1  OCTET 2  .....
             xxxxxxxx xxxxxxxx ..... 
             ||    || |_ port 8
             ||    ||  
             ||    ||___ port 7
             ||    |____ port 6
             ||      .    .   .
             ||_________ port 1
             |__________ reserved

         where x : 1 - The represented port belongs to ISL and protocol state is up
                   0 - The represented port does not belong to ISL or protocol state is down"
    ::= {vlagInfoIslGroup 7 }

vlagInfoIslPortLinkState    OBJECT-TYPE
    SYNTAX        OCTET STRING
    MAX-ACCESS    read-only
    STATUS        current
    DESCRIPTION   "The ISL member ports' link state. The ports' link state are
                  presented in bitmap format.

             OCTET 1  OCTET 2  .....
             xxxxxxxx xxxxxxxx .....
             ||    || |_ port 8
             ||    ||
             ||    ||___ port 7
             ||    |____ port 6
             ||      .    .   .
             ||_________ port 1
             |__________ reserved

         where x : 1 - The represented port belongs to ISL and link state is up
                   0 - The represented port does not belong to ISL or link state is down"
    ::= {vlagInfoIslGroup 8 }

-- ----------------------------------------------------------------------------
-- Global VLAG Statistics
-- ----------------------------------------------------------------------------
-- vlagStatsSystem   OBJECT IDENTIFIER ::= { vlagStats 1 }
-- vlagStatsIsl      OBJECT IDENTIFIER ::= { vlagStats 2 }
-- vlagStatsHealth   OBJECT IDENTIFIER ::= { vlagStats 3 }
-- vlagStatsLacp     OBJECT IDENTIFIER ::= { vlagStats 4 }
-- vlagStatsPdu      OBJECT IDENTIFIER ::= { vlagStats 5 }
-- vlagStatsIgmp     OBJECT IDENTIFIER ::= { vlagStats 6 }

vlagStatsClear                           OBJECT-TYPE
    SYNTAX      INTEGER {
                    clear(1),
                    other(2)
                }
    MAX-ACCESS  read-write
    STATUS      current
    DESCRIPTION
                "Setting this object to 'clear' will reset all statistics
                 objects of VLAG. A get action of this object will always
                 return 'other'. Setting this object to 'other' is not
                 allowed."
    ::= { vlagStatsSystem 1 }

vlagStatsIslInOctets OBJECT-TYPE
      SYNTAX  Counter32
      MAX-ACCESS  read-only
      STATUS  current
      DESCRIPTION
              "The total number of vlag ISL octets received."
      ::= { vlagStatsIsl 1 }

vlagStatsIslInPackets OBJECT-TYPE
      SYNTAX  Counter32
      MAX-ACCESS  read-only
      STATUS  current
      DESCRIPTION
              "The total number of vlag ISL packets received."
      ::= { vlagStatsIsl 2 }

vlagStatsIslOutOctets OBJECT-TYPE
      SYNTAX  Counter32
      MAX-ACCESS  read-only
      STATUS  current
      DESCRIPTION
              "The total number of vlag ISL octets sent."
      ::= { vlagStatsIsl 3 }

vlagStatsIslOutPackets OBJECT-TYPE
      SYNTAX  Counter32
      MAX-ACCESS  read-only
      STATUS  current
      DESCRIPTION
              "The total number of vlag ISL packets sent."
      ::= { vlagStatsIsl 4 }

vlagStatsPduSentRoleElection OBJECT-TYPE
      SYNTAX  Counter32
      MAX-ACCESS  read-only
      STATUS  current
      DESCRIPTION
              "The total number of vlag PDUs sent for role elections"
      ::= { vlagStatsPdu 1 }

vlagStatsPduSentSystemInfo OBJECT-TYPE
      SYNTAX  Counter32
      MAX-ACCESS  read-only
      STATUS  current
      DESCRIPTION
              "The total number of vlag PDUs sent for system info"
      ::= { vlagStatsPdu 2 }

vlagStatsPduSentFdbDynamicAdd OBJECT-TYPE
      SYNTAX  Counter32
      MAX-ACCESS  read-only
      STATUS  current
      DESCRIPTION
              "The total number of vlag PDUs sent for addition of FDB dynamic entry"
      ::= { vlagStatsPdu 7 }

vlagStatsPduSentFdbDynamicDel OBJECT-TYPE
      SYNTAX  Counter32
      MAX-ACCESS  read-only
      STATUS  current
      DESCRIPTION
              "The total number of vlag PDUs sent for deletion of FDB dynamic entry"
      ::= { vlagStatsPdu 8 }

vlagStatsPduSentFdbInactiveAdd OBJECT-TYPE
      SYNTAX  Counter32
      MAX-ACCESS  read-only
      STATUS  current
      DESCRIPTION
              "The total number of vlag PDUs sent for addition of FDB inactive entry"
      ::= { vlagStatsPdu 9 }

vlagStatsPduSentFdbInactiveDel OBJECT-TYPE
      SYNTAX  Counter32
      MAX-ACCESS  read-only
      STATUS  current
      DESCRIPTION
              "The total number of vlag PDUs sent for deletion of FDB inactive entry"
      ::= { vlagStatsPdu 10 }

vlagStatsPduSentHlthCheck OBJECT-TYPE
      SYNTAX  Counter32
      MAX-ACCESS  read-only
      STATUS  current
      DESCRIPTION
              "The total number of vlag PDUs sent for Health check"
      ::= { vlagStatsPdu 13 }

vlagStatsPduSentOther OBJECT-TYPE
      SYNTAX  Counter32
      MAX-ACCESS  read-only
      STATUS  current
      DESCRIPTION
              "The total number of vlag PDUs sent for others"
      ::= { vlagStatsPdu 15 }

vlagStatsPduSentUnknown OBJECT-TYPE
      SYNTAX  Counter32
      MAX-ACCESS  read-only
      STATUS  current
      DESCRIPTION
              "The total number of vlag PDUs sent for unknowns"
      ::= { vlagStatsPdu 16 }

vlagStatsPduRcvRoleElection OBJECT-TYPE
      SYNTAX  Counter32
      MAX-ACCESS  read-only
      STATUS  current
      DESCRIPTION
              "The total number of vlag PDUs received for role elections"
      ::= { vlagStatsPdu 17 }

vlagStatsPduRcvSystemInfo OBJECT-TYPE
      SYNTAX  Counter32
      MAX-ACCESS  read-only
      STATUS  current
      DESCRIPTION
              "The total number of vlag PDUs received for system info"
      ::= { vlagStatsPdu 18 }

vlagStatsPduRcvFdbDynamicAdd OBJECT-TYPE
      SYNTAX  Counter32
      MAX-ACCESS  read-only
      STATUS  current
      DESCRIPTION
              "The total number of vlag PDUs received for addition of FDB dynamic entry"
      ::= { vlagStatsPdu 23 }

vlagStatsPduRcvFdbDynamicDel OBJECT-TYPE
      SYNTAX  Counter32
      MAX-ACCESS  read-only
      STATUS  current
      DESCRIPTION
              "The total number of vlag PDUs received for deletion of FDB dynamic entry"
      ::= { vlagStatsPdu 24 }

vlagStatsPduRcvFdbInactiveAdd OBJECT-TYPE
      SYNTAX  Counter32
      MAX-ACCESS  read-only
      STATUS  current
      DESCRIPTION
              "The total number of vlag PDUs received for addition of FDB inactive entry"
      ::= { vlagStatsPdu 25 }

vlagStatsPduRcvFdbInactiveDel OBJECT-TYPE
      SYNTAX  Counter32
      MAX-ACCESS  read-only
      STATUS  current
      DESCRIPTION
              "The total number of vlag PDUs received for deletion of FDB inactive entry"
      ::= { vlagStatsPdu 26 }

vlagStatsPduRcvHlthCheck OBJECT-TYPE
      SYNTAX  Counter32
      MAX-ACCESS  read-only
      STATUS  current
      DESCRIPTION
              "The total number of vlag PDUs received for Health check"
      ::= { vlagStatsPdu 29 }

vlagStatsPduRcvOther OBJECT-TYPE
      SYNTAX  Counter32
      MAX-ACCESS  read-only
      STATUS  current
      DESCRIPTION
              "The total number of vlag PDUs received for others"
      ::= { vlagStatsPdu 31 }

vlagStatsPduRcvUnknown OBJECT-TYPE
      SYNTAX  Counter32
      MAX-ACCESS  read-only
      STATUS  current
      DESCRIPTION
              "The total number of vlag PDUs received for unknowns"
      ::= { vlagStatsPdu 32 }

vlagStatsPduSentPeerInstanceEnable OBJECT-TYPE
      SYNTAX  Counter32
      MAX-ACCESS  read-only
      STATUS  current
      DESCRIPTION
              "The total number of vlag PDUs sent for peer instance enable"
      ::= { vlagStatsPdu 33 }

vlagStatsPduSentPeerInstanceDisable OBJECT-TYPE
      SYNTAX  Counter32
      MAX-ACCESS  read-only
      STATUS  current
      DESCRIPTION
              "The total number of vlag PDUs sent for peer instance disable"
      ::= { vlagStatsPdu 34 }

vlagStatsPduSentISLHello OBJECT-TYPE
      SYNTAX  Counter32
      MAX-ACCESS  read-only
      STATUS  current
      DESCRIPTION
              "The total number of vlag PDUs sent for ISL hello"
      ::= { vlagStatsPdu 35 }

vlagStatsPduRcvISLHello OBJECT-TYPE
      SYNTAX  Counter32
      MAX-ACCESS  read-only
      STATUS  current
      DESCRIPTION
              "The total number of vlag PDUs received for ISL hello"
      ::= { vlagStatsPdu 36 }

vlagStatsPduRcvPeerInstanceEnable OBJECT-TYPE
      SYNTAX  Counter32
      MAX-ACCESS  read-only
      STATUS  current
      DESCRIPTION
              "The total number of vlag PDUs received for peer instance enable"
      ::= { vlagStatsPdu 37 }

vlagStatsPduRcvPeerInstanceDisable OBJECT-TYPE
      SYNTAX  Counter32
      MAX-ACCESS  read-only
      STATUS  current
      DESCRIPTION
              "The total number of vlag PDUs received for peer instance disable"
      ::= { vlagStatsPdu 38 }

vlagStatsIgmpReportsForwarded OBJECT-TYPE
      SYNTAX  Counter32
      MAX-ACCESS  read-only
      STATUS  current
      DESCRIPTION
              "The total number of IGMP reports forwarded to the peer"
      ::= { vlagStatsIgmp 1 }

vlagStatsIgmpLeavesForwarded OBJECT-TYPE
      SYNTAX  Counter32
      MAX-ACCESS  read-only
      STATUS  current
      DESCRIPTION
              "The total number of IGMP leaves forwarded to the peer"
      ::= { vlagStatsIgmp 2 }


-- ----------------------------------------------------------------------------
-- { INSERT:  ecp    
-- ----------------------------------------------------------------------------


-- ------------------------------------------------------------------------- --
-- ECP Configuration                                                         {
-- ------------------------------------------------------------------------- --
ecpCurCfgRetrans OBJECT-TYPE
    SYNTAX INTEGER
    MAX-ACCESS  read-only
    STATUS  current
    DESCRIPTION
        "The ECP retransmission interval in millisecond"
    ::= { ecpCfg 1 }

ecpNewCfgRetrans OBJECT-TYPE
    SYNTAX INTEGER (100..9000)
    MAX-ACCESS  read-write
    STATUS current
    DESCRIPTION
        "The ECP retransmission interval in millisecond"
    ::= { ecpCfg 2 }
-- ------------------------------------------------------------------------- --
-- ECP Configuration (end)                                                   }
-- ------------------------------------------------------------------------- --


-- ------------------------------------------------------------------------- --
-- ECP Information                                                           {
-- ------------------------------------------------------------------------- --
ecpChnlInfoTable OBJECT-TYPE
    SYNTAX SEQUENCE OF EcpChnlInfoEntry
    MAX-ACCESS not-accessible
    STATUS current
    DESCRIPTION
        "The table of ECP channel Info."
    ::= { ecpInfo 1 }

ecpChnlInfoEntry OBJECT-TYPE
    SYNTAX EcpChnlInfoEntry
    MAX-ACCESS not-accessible
    STATUS current
    DESCRIPTION
        "Information about ECP channel."
    INDEX { ecpChnlInfoEntryIndex }
    ::= { ecpChnlInfoTable 1 }

EcpChnlInfoEntry ::= SEQUENCE {
    ecpChnlInfoEntryIndex   Integer32
    ,ecpChnlPort            Integer32
    ,ecpChnlStag            Integer32           
    ,ecpChnlSndlen          Integer32
    ,ecpChnlSndnxt          Integer32
    ,ecpChnlRcvlast         Integer32
    ,ecpChnlStateMachine    Integer32
    ,ecpChnlRxCnt           Integer32
    ,ecpChnlTxCnt           Integer32
    ,ecpChnlRxDrop          Integer32
    ,ecpChnlTxDrop          Integer32
    ,ecpChnlState           INTEGER
    ,ecpChnlAckErr          Integer32
    }

ecpChnlInfoEntryIndex OBJECT-TYPE
    SYNTAX  Integer32
    MAX-ACCESS read-only
    STATUS  current
    DESCRIPTION
        "The index of the ecp chnl info table."
    ::= { ecpChnlInfoEntry 1 }

ecpChnlPort OBJECT-TYPE
    SYNTAX  Integer32
    MAX-ACCESS read-only
    STATUS  current
    DESCRIPTION
        "The ecp channel port info."
    ::= { ecpChnlInfoEntry 2 }

ecpChnlStag OBJECT-TYPE
    SYNTAX  Integer32
    MAX-ACCESS read-only
    STATUS  current
    DESCRIPTION
        "The ecp channel stag info."
    ::= { ecpChnlInfoEntry 3 }

ecpChnlSndlen OBJECT-TYPE
    SYNTAX  Integer32
    MAX-ACCESS read-only
    STATUS  current
    DESCRIPTION
        "The ecp channel send length info."
    ::= { ecpChnlInfoEntry 4 }

ecpChnlSndnxt OBJECT-TYPE
    SYNTAX  Integer32
    MAX-ACCESS read-only
    STATUS  current
    DESCRIPTION
        "The ecp channel send next info."
    ::= { ecpChnlInfoEntry 5 }

ecpChnlRcvlast OBJECT-TYPE
    SYNTAX  Integer32
    MAX-ACCESS read-only
    STATUS  current
    DESCRIPTION
        "The ecp channel recv last sequence info."
    ::= { ecpChnlInfoEntry 6 }

ecpChnlStateMachine OBJECT-TYPE
    SYNTAX  Integer32
    MAX-ACCESS read-only
    STATUS  current
    DESCRIPTION
        "The ecp channel state machineinfo."
    ::= { ecpChnlInfoEntry 7 }

ecpChnlRxCnt OBJECT-TYPE
    SYNTAX  Integer32
    MAX-ACCESS read-only
    STATUS  current
    DESCRIPTION
        "The ecp channel Rx count info."
    ::= { ecpChnlInfoEntry 8 }

ecpChnlTxCnt OBJECT-TYPE
    SYNTAX  Integer32
    MAX-ACCESS read-only
    STATUS  current
    DESCRIPTION
        "The ecp channel Tx count info."
    ::= { ecpChnlInfoEntry 9 }

ecpChnlRxDrop OBJECT-TYPE
    SYNTAX  Integer32
    MAX-ACCESS read-only
    STATUS  current
    DESCRIPTION
        "The ecp channel RxDrop info."
    ::= { ecpChnlInfoEntry 10 }

ecpChnlTxDrop OBJECT-TYPE
    SYNTAX  Integer32
    MAX-ACCESS read-only
    STATUS  current
    DESCRIPTION
        "The ecp channel TxDrop info."
    ::= { ecpChnlInfoEntry 11 }

ecpChnlState OBJECT-TYPE
    SYNTAX INTEGER {
        enabled(1),
        disabled(0)
        }
    MAX-ACCESS read-only
    STATUS  current
    DESCRIPTION
        "The ecp channel state info."
    ::= { ecpChnlInfoEntry 12 }

ecpChnlAckErr OBJECT-TYPE
    SYNTAX  Integer32
    MAX-ACCESS read-only
    STATUS  current
    DESCRIPTION
        "The ecp channel ACK error info."
    ::= { ecpChnlInfoEntry 13 }
-- ------------------------------------------------------------------------- --
-- ECP Information (end)                                                     }
-- ------------------------------------------------------------------------- --


-- ------------------------------------------------------------------------- --
-- ECP Operation                                                             {
-- ------------------------------------------------------------------------- --

-- ------------------------------------------------------------------------- --
-- ECP Operation (end)                                                       }
-- ------------------------------------------------------------------------- --


-- ----------------------------------------------------------------------------
--                                                                           --
--                    Service Location Protocol (SLP)                        --
--                                                                           --
-- ----------------------------------------------------------------------------

-- ----------------------------------------------------------------------------
-- Global SLP Configuration
-- ----------------------------------------------------------------------------

slpCfg           OBJECT IDENTIFIER ::= { layer2Configs 20 }

slpCurCfgGlobalEnable             OBJECT-TYPE
    SYNTAX      INTEGER {
                    enabled(1),
                    disabled(2)
                }
    MAX-ACCESS  read-only
    STATUS      current
    DESCRIPTION
                "Current SLP global status on switch."
    DEFVAL      { disabled }
    ::= { slpCfg 1 }

slpNewCfgGlobalEnable             OBJECT-TYPE
    SYNTAX      INTEGER {
                    enabled(1),
                    disabled(2)
                }
    MAX-ACCESS  read-write
    STATUS      current
    DESCRIPTION
                "Set to enabled to enable SLP globally or
                 Set to disabled to disable SLP globally on switch."
    DEFVAL      { disabled }
    ::= { slpCfg 2 }

slpCurCfgActiveDaDisEnable             OBJECT-TYPE
    SYNTAX      INTEGER {
                    enabled(1),
                    disabled(2)
                }
    MAX-ACCESS  read-only
    STATUS      current
    DESCRIPTION
                "Current SLP active directory agent discovery status on switch."
    DEFVAL      { disabled }
    ::= { slpCfg 3 }

slpNewCfgActiveDaDisEnable             OBJECT-TYPE
    SYNTAX      INTEGER {
                    enabled(1),
                    disabled(2)
                }
    MAX-ACCESS  read-write
    STATUS      current
    DESCRIPTION
                "Set to enabled to enable SLP active directory agent discovery or
                 Set to disabled to disable SLP active directory agent discovery on switch."
    DEFVAL      { disabled }
    ::= { slpCfg 4 }

slpCurCfgActiveDaDisStartWaitTime    OBJECT-TYPE
    SYNTAX      INTEGER (1..10)
    MAX-ACCESS  read-only
    STATUS      current
    DESCRIPTION
                "Current SLP active directory agent discovery start wait time measured in seconds."
    DEFVAL      { 3 }
    ::= { slpCfg 5 }

slpNewCfgActiveDaDisStartWaitTime    OBJECT-TYPE
    SYNTAX      INTEGER (1..10)
    MAX-ACCESS  read-write
    STATUS      current
    DESCRIPTION
                "This object is used to change the SLP active directory agent 
                 discovery start wait time measured in seconds."
    DEFVAL      { 3 }
    ::= { slpCfg 6 }



-- ----------------------------------------------------------------------------
-- Global SLP Info
-- ----------------------------------------------------------------------------
slpInfo                 OBJECT IDENTIFIER ::= { layer2Info 18 }
slpInfoSystem           OBJECT IDENTIFIER ::= { slpInfo 1 }
slpInfoDirectoryAgents  OBJECT IDENTIFIER ::= { slpInfo 2 }
slpInfoUserAgents       OBJECT IDENTIFIER ::= { slpInfo 3 }

slpInfoProtocolVersion    OBJECT-TYPE
    SYNTAX      Integer32
    MAX-ACCESS  read-only
    STATUS      current
    DESCRIPTION
                "SLP protocol version."
    DEFVAL      { 2 }
    ::= { slpInfoSystem 1 }

slpInfoListeningPort    OBJECT-TYPE
    SYNTAX      INTEGER (0..65535)
    MAX-ACCESS  read-only
    STATUS      current
    DESCRIPTION
                "SLP listening port."
    DEFVAL      { 427 }
    ::= { slpInfoSystem 2 }

slpInfoListeningIPInterfaceTable        OBJECT-TYPE
    SYNTAX      SEQUENCE OF SlpInfoListeningIPInterfaceEntry
    MAX-ACCESS  not-accessible
    STATUS      current
    DESCRIPTION
                "A table with all the SLP listening IP interfaces."
    ::= { slpInfoSystem 3 }

slpInfoListeningIPInterfaceEntry        OBJECT-TYPE
    SYNTAX      SlpInfoListeningIPInterfaceEntry 
    MAX-ACCESS  not-accessible
    STATUS      current
    DESCRIPTION
                "The configuration objects for a SLP listening IP interface."
    INDEX       { listeningIPInterfaceId }
    ::= { slpInfoListeningIPInterfaceTable 1 }

SlpInfoListeningIPInterfaceEntry ::=    SEQUENCE {
    listeningIPInterfaceId                   Integer32,
    listeningIPInterfaceAddress              IpAddress
    }

listeningIPInterfaceId          OBJECT-TYPE
    SYNTAX      Integer32
    MAX-ACCESS  read-only
    STATUS      current
    DESCRIPTION
                "The identifier of this IP interface."
    ::= { slpInfoListeningIPInterfaceEntry 1 }

listeningIPInterfaceAddress     OBJECT-TYPE
    SYNTAX      IpAddress
    MAX-ACCESS  read-only
    STATUS      current
    DESCRIPTION
                "The adddress of this IP interface."
    ::= { slpInfoListeningIPInterfaceEntry 2 }

slpInfoDirectoryAgentsTable        OBJECT-TYPE
    SYNTAX      SEQUENCE OF SlpInfoDirectoryAgentEntry
    MAX-ACCESS  not-accessible
    STATUS      current
    DESCRIPTION
                "A table with all the SLP Directory Agents."
    ::= { slpInfoDirectoryAgents 1 }

slpInfoDirectoryAgentEntry        OBJECT-TYPE
    SYNTAX      SlpInfoDirectoryAgentEntry
    MAX-ACCESS  not-accessible
    STATUS      current
    DESCRIPTION
                "The configuration objects for a Directory Agent entry."
    INDEX       { directoryAgentAddress }
    ::= { slpInfoDirectoryAgentsTable 1 }

SlpInfoDirectoryAgentEntry ::=    SEQUENCE {
    directoryAgentAddress              IpAddress,
    directoryAgentPort                 Integer32,
    directoryAgentTime                 Integer32
    }

directoryAgentAddress           OBJECT-TYPE
    SYNTAX      IpAddress
    MAX-ACCESS  read-only
    STATUS      current
    DESCRIPTION
                "The IP adddress of this Directory Agent."
    ::= { slpInfoDirectoryAgentEntry 1 }

directoryAgentPort              OBJECT-TYPE
    SYNTAX      Integer32
    MAX-ACCESS  read-only
    STATUS      current
    DESCRIPTION
                "The port of this Directory Agent. Communication can be done
                 using TCP or UDP."
    ::= { slpInfoDirectoryAgentEntry 2 }

directoryAgentTime              OBJECT-TYPE
    SYNTAX      Integer32
    MAX-ACCESS  read-only
    STATUS      current
    DESCRIPTION
                "The time elapsed from the moment when this Directory Agent 
                 was learned measured in seconds."
    ::= { slpInfoDirectoryAgentEntry 3 }

slpInfoUserAgentsTable        OBJECT-TYPE
    SYNTAX      SEQUENCE OF SlpInfoUserAgentEntry
    MAX-ACCESS  not-accessible
    STATUS      current
    DESCRIPTION
                "A table with all the SLP User Agents."
    ::= { slpInfoUserAgents 1 }

slpInfoUserAgentEntry        OBJECT-TYPE
    SYNTAX      SlpInfoUserAgentEntry
    MAX-ACCESS  not-accessible
    STATUS      current
    DESCRIPTION
                "The configuration objects for a User Agent entry."
    INDEX       { userAgentAddress }
    ::= { slpInfoUserAgentsTable 1 }

SlpInfoUserAgentEntry ::=    SEQUENCE {
    userAgentAddress              IpAddress,
    userAgentPort                 Integer32,
    userAgentTime                 Integer32
    }

userAgentAddress           OBJECT-TYPE
    SYNTAX      IpAddress
    MAX-ACCESS  read-only
    STATUS      current
    DESCRIPTION
                "The IP adddress of this User Agent."
    ::= { slpInfoUserAgentEntry 1 }

userAgentPort              OBJECT-TYPE
    SYNTAX      Integer32
    MAX-ACCESS  read-only
    STATUS      current
    DESCRIPTION
                "The port of this User Agent. Communication can be done
                 using TCP or UDP."
    ::= { slpInfoUserAgentEntry 2 }

userAgentTime              OBJECT-TYPE
    SYNTAX      Integer32
    MAX-ACCESS  read-only
    STATUS      current
    DESCRIPTION
                "The time elapsed from the moment when this User Agent was learned 
                 measured in seconds."
    ::= { slpInfoUserAgentEntry 3 }

slpDirectoryAgentsClear                           OBJECT-TYPE
    SYNTAX      INTEGER {
                    clear(1),
                    other(2)
                }
    MAX-ACCESS  read-write
    STATUS      current
    DESCRIPTION
                "Setting this object to 'clear' will reset all directory agents
                 settings of SLP. A get action of this object will always
                 return 'other'. Setting this object to 'other' is not
                 allowed."
    ::= { slpInfo 4 }

-- ----------------------------------------------------------------------------
-- Global SLP Statistics
-- ----------------------------------------------------------------------------
slpStats                OBJECT IDENTIFIER ::= { layer2Stats 12 }

slpCountersClear                           OBJECT-TYPE
    SYNTAX      INTEGER {
                    clear(1),
                    other(2)
                }
    MAX-ACCESS  read-write
    STATUS      current
    DESCRIPTION
                "Setting this object to 'clear' will reset all SLP counters.
                 A get action of this object will always return 'other'. 
                 Setting this object to 'other' is not allowed."
    ::= { slpStats 3 }

slpStatsTxCountersTable        OBJECT-TYPE
    SYNTAX      SEQUENCE OF SlpStatsTxCounterEntry
    MAX-ACCESS  not-accessible
    STATUS      current
    DESCRIPTION
                "A table with all the SLP Send counters."
    ::= { slpStats 1 }

slpStatsTxCounterEntry        OBJECT-TYPE
    SYNTAX      SlpStatsTxCounterEntry
    MAX-ACCESS  not-accessible
    STATUS      current
    DESCRIPTION
                "The configuration objects for a SLP Send counter entry."
    INDEX       { slpTxCounterIndex }
    ::= { slpStatsTxCountersTable 1 }

SlpStatsTxCounterEntry ::=    SEQUENCE {
    slpTxCounterIndex             Integer32,
    slpTxCounterName              DisplayString,
    slpTxCounterUnicast           Integer32,
    slpTxCounterMulticast         Integer32
    }

slpTxCounterIndex         OBJECT-TYPE
     SYNTAX      Integer32
     MAX-ACCESS  read-only
     STATUS      current
     DESCRIPTION
                 "The index of this counter."
     ::= { slpStatsTxCounterEntry 1 }

slpTxCounterName           OBJECT-TYPE
    SYNTAX      DisplayString (SIZE (0..255))
    MAX-ACCESS  read-only
    STATUS      current
    DESCRIPTION
                "The name of this counter."
    ::= { slpStatsTxCounterEntry 2 }

slpTxCounterUnicast         OBJECT-TYPE
    SYNTAX      Integer32
    MAX-ACCESS  read-only
    STATUS      current
    DESCRIPTION
                "The unicast value of this counter."
    ::= { slpStatsTxCounterEntry 3 }

slpTxCounterMulticast       OBJECT-TYPE
    SYNTAX      Integer32
    MAX-ACCESS  read-only
    STATUS      current
    DESCRIPTION
                "The multicast value of this counter."
    ::= { slpStatsTxCounterEntry 4 }

slpStatsRxCountersTable        OBJECT-TYPE
    SYNTAX      SEQUENCE OF SlpStatsRxCounterEntry
    MAX-ACCESS  not-accessible
    STATUS      current
    DESCRIPTION
                "A table with all the SLP Receive counters."
    ::= { slpStats 2 }

slpStatsRxCounterEntry        OBJECT-TYPE
    SYNTAX      SlpStatsRxCounterEntry
    MAX-ACCESS  not-accessible
    STATUS      current
    DESCRIPTION
                "The configuration objects for a SLP Receive counter entry."
    INDEX       { slpRxCounterIndex }
    ::= { slpStatsRxCountersTable 1 }

SlpStatsRxCounterEntry ::=    SEQUENCE {
    slpRxCounterIndex             Integer32,
    slpRxCounterName              DisplayString,
    slpRxCounterUnicast           Integer32,
    slpRxCounterMulticast         Integer32
    }

slpRxCounterIndex         OBJECT-TYPE
    SYNTAX      Integer32
    MAX-ACCESS  read-only
    STATUS      current
    DESCRIPTION
                "The index this counter."
    ::= { slpStatsRxCounterEntry 1 }

slpRxCounterName           OBJECT-TYPE
    SYNTAX      DisplayString (SIZE (0..255))
    MAX-ACCESS  read-only
    STATUS      current
    DESCRIPTION
                "The name of this counter."
    ::= { slpStatsRxCounterEntry 2 }

slpRxCounterUnicast         OBJECT-TYPE
    SYNTAX      Integer32
    MAX-ACCESS  read-only
    STATUS      current
    DESCRIPTION
                "The unicast value of this counter."
    ::= { slpStatsRxCounterEntry 3 }

slpRxCounterMulticast       OBJECT-TYPE
    SYNTAX      Integer32
    MAX-ACCESS  read-only
    STATUS      current
    DESCRIPTION
                "The multicast value of this counter."
    ::= { slpStatsRxCounterEntry 4 }


-- ----------------------------------------------------------------------------
-- } INSERT:  layer2
-- ----------------------------------------------------------------------------

layer3                  OBJECT IDENTIFIER ::= { g8264T-mgmt 3 }
-- ----------------------------------------------------------------------------
-- { INSERT:  layer3
-- ----------------------------------------------------------------------------

layer3Configs     OBJECT IDENTIFIER ::= { layer3 1 }

layer3Stats       OBJECT IDENTIFIER ::= { layer3 2 }

layer3Info        OBJECT IDENTIFIER ::= { layer3 3 }


layer3Oper        OBJECT IDENTIFIER ::= { layer3 4 }

ipInterfaceCfg      OBJECT IDENTIFIER ::= { layer3Configs 1 }

ipInterfaceLoopbackCfg    OBJECT IDENTIFIER ::= { layer3Configs 24 }

ipGatewayCfg        OBJECT IDENTIFIER ::= { layer3Configs 2 }

ipStaticRouteCfg    OBJECT IDENTIFIER ::= { layer3Configs 3 }

ipForwardCfg        OBJECT IDENTIFIER ::= { layer3Configs 4 }


vrrpCfg         OBJECT IDENTIFIER ::= { layer3Configs 6 }
arpCfg          OBJECT IDENTIFIER ::= { layer3Configs 7 }

ipBootpCfg      OBJECT IDENTIFIER ::= { layer3Configs 8 }

dnsCfg          OBJECT IDENTIFIER ::= { layer3Configs 9 }


ipNwfCfg        OBJECT IDENTIFIER ::= { layer3Configs 10 }
ipRmapCfg       OBJECT IDENTIFIER ::= { layer3Configs 11 }

bgpCfg          OBJECT IDENTIFIER ::= { layer3Configs 12 }

ospfCfg         OBJECT IDENTIFIER ::= { layer3Configs 13 }

ipGeneralCfg        OBJECT IDENTIFIER ::= { layer3Configs 14 }

ipStaticArpCfg      OBJECT IDENTIFIER ::= { layer3Configs 15 }




rip2Cfg         OBJECT IDENTIFIER ::= { layer3Configs 18 }

igmpCfg             OBJECT IDENTIFIER ::= { layer3Configs 19 }

ipStaticNbrCfg      OBJECT IDENTIFIER ::= { layer3Configs 21 }

ipGatewayIpv6Cfg    OBJECT IDENTIFIER ::= { layer3Configs 22 }

ipStaticRoute6Cfg   OBJECT IDENTIFIER ::= { layer3Configs 23 }



ospf3Cfg              OBJECT IDENTIFIER ::= { layer3Configs 26 }

pptCfg      OBJECT IDENTIFIER ::= { layer3Configs 27 }
 
ipv6pmtuCfg          OBJECT IDENTIFIER ::= { layer3Configs 28 }

floodingCfg OBJECT IDENTIFIER ::= { layer3Configs 29 }

mldCfg             OBJECT IDENTIFIER ::= { layer3Configs 30 }

ndprefixCfg    OBJECT IDENTIFIER ::= { layer3Configs 31 }



dhcpsnpCfg  OBJECT IDENTIFIER ::= { layer3Configs 33 }

ipsecCfg       OBJECT IDENTIFIER ::= { layer3Configs 32 }



arpStats      OBJECT IDENTIFIER ::= { layer3Stats 2 }

routeStats        OBJECT IDENTIFIER ::= { layer3Stats 3 }

dnsStats      OBJECT IDENTIFIER ::= { layer3Stats 4 }

vrrpStats         OBJECT IDENTIFIER ::= { layer3Stats 5 }

ospfStats     OBJECT IDENTIFIER ::= { layer3Stats 6 }

clearStats    OBJECT IDENTIFIER ::= { layer3Stats 7 }

igmpStats         OBJECT IDENTIFIER ::= { layer3Stats 9 }

ipv6Stats          OBJECT IDENTIFIER ::= { layer3Stats 10}
rip2Stats     OBJECT IDENTIFIER ::= { layer3Stats 13 }



ipStats           OBJECT IDENTIFIER ::= { layer3Stats 16 }
icmpStats         OBJECT IDENTIFIER ::= { layer3Stats 17 }
tcpStats          OBJECT IDENTIFIER ::= { layer3Stats 18 }
udpStats          OBJECT IDENTIFIER ::= { layer3Stats 19 }
bootpStats        OBJECT IDENTIFIER ::= { layer3Stats 20 }


ospf3Stats        OBJECT IDENTIFIER ::= { layer3Stats 22 }

mldStats         OBJECT IDENTIFIER ::= { layer3Stats 23 }

ipsecStats     OBJECT IDENTIFIER ::= { layer3Stats 24 }

nbrStats         OBJECT IDENTIFIER ::= { layer3Stats 26 }

dhcpsnpStats     OBJECT IDENTIFIER ::= { layer3Stats 25}



ipRoutingInfo     OBJECT IDENTIFIER ::= { layer3Info 1 }

ipEcmpRoutingInfo     OBJECT IDENTIFIER ::= { layer3Info 19 }
ipEcmpHash            OBJECT IDENTIFIER ::= { layer3Info 20 }


ipv6PmtuInfo          OBJECT IDENTIFIER ::= { layer3Info 21}

arpInfo       OBJECT IDENTIFIER ::= { layer3Info 2 }

vrrpInfo      OBJECT IDENTIFIER ::= { layer3Info 3 }

ospfinfo      OBJECT IDENTIFIER ::= { layer3Info 4 }


gatewayInfo   OBJECT IDENTIFIER ::= { layer3Info 5 }

igmpInfo          OBJECT IDENTIFIER ::= { layer3Info 6 }

nbrInfo      OBJECT IDENTIFIER ::= { layer3Info 12 }
gatewayIPv6Info   OBJECT IDENTIFIER ::= { layer3Info 13 }

ipRoute6Info      OBJECT IDENTIFIER ::= { layer3Info 14 }


ipInfo            OBJECT IDENTIFIER ::= { layer3Info 8 }

ipIntfInfo        OBJECT IDENTIFIER ::= { layer3Info 9 }

ipIntfLoopbackInfo OBJECT IDENTIFIER ::= { layer3Info 16 }


rip2Info          OBJECT IDENTIFIER ::= { layer3Info 10 }
bgpInfo           OBJECT IDENTIFIER ::= { layer3Info 11 }

dhcpInfo   OBJECT IDENTIFIER ::= { layer3Info 15 }


ospf3Info         OBJECT IDENTIFIER ::= { layer3Info 18 }


mldInfo          OBJECT IDENTIFIER ::= { layer3Info 22 }

ipsecInfo      OBJECT IDENTIFIER ::= { layer3Info 23 }

dhcpsnpInfo      OBJECT IDENTIFIER ::= { layer3Info 24 }

-- ----------------------------------------------------------------------------
-- { INSERT:  DHCP Snooping Config
-- ----------------------------------------------------------------------------

dhcpSnoopingCurCfgOnState                  OBJECT-TYPE
    SYNTAX      INTEGER  {
                    on(1),
                    off(2)
                }
    MAX-ACCESS  read-only
    STATUS      current
    DESCRIPTION
        "DHCP Snooping ON/OFF settings."
    ::= { dhcpsnpCfg 1 }
    
dhcpSnoopingNewCfgOnState                  OBJECT-TYPE
    SYNTAX      INTEGER  {
                    on(1),
                    off(2)
                }
    MAX-ACCESS  read-write
    STATUS      current
    DESCRIPTION
        "DHCP Snooping ON/OFF setting."
    ::= { dhcpsnpCfg 2 }

dhcpSnoopingCurCfgOption82OnState           OBJECT-TYPE
    SYNTAX      INTEGER  {
                    on(1),
                    off(2)
                }
    MAX-ACCESS  read-only
    STATUS      current
    DESCRIPTION
        "on/off state of DHCP Snooping option82."
    ::= { dhcpsnpCfg 3 }

dhcpSnoopingNewCfgOption82OnState          OBJECT-TYPE
    SYNTAX      INTEGER  {
                    on(1),
                    off(2)
                }
    MAX-ACCESS  read-write
    STATUS      current
    DESCRIPTION
        "Enable/Disable DHCP Snooping option82"
    ::= { dhcpsnpCfg 4 }    

dhcpSnoopingCurCfgPortTable             OBJECT-TYPE
    SYNTAX      SEQUENCE OF DHCPSnoopingCurCfgPortTableEntry
    MAX-ACCESS  not-accessible
    STATUS      current
    DESCRIPTION
        "DHCP Snooping Port Configuration Table."
    ::= { dhcpsnpCfg 5 }

dhcpSnoopingCurCfgPortTableEntry        OBJECT-TYPE
    SYNTAX      DHCPSnoopingCurCfgPortTableEntry
    MAX-ACCESS  not-accessible
    STATUS      current
    DESCRIPTION
        "A row in DHCP Snooping Port Configuration Table"
    INDEX  { dhcpSnoopingCurCfgPortId }
    ::= { dhcpSnoopingCurCfgPortTable 1 }

DHCPSnoopingCurCfgPortTableEntry ::= SEQUENCE {
    dhcpSnoopingCurCfgPortId                   Integer32,
    dhcpSnoopingCurCfgPortTrusted                 INTEGER,
    dhcpSnoopingCurCfgPortRateLimit            Integer32
}

dhcpSnoopingCurCfgPortId           OBJECT-TYPE
    SYNTAX      Integer32 
    MAX-ACCESS  read-only
    STATUS      current
    DESCRIPTION
        "Port ID of this DHCP Snooping port configration."
    ::= { dhcpSnoopingCurCfgPortTableEntry 1 }

dhcpSnoopingCurCfgPortTrusted     OBJECT-TYPE
    SYNTAX      INTEGER  {
                    trusted(1),
                    untrusted(2)
                } 
    MAX-ACCESS  read-only
    STATUS      current
    DESCRIPTION
        "Set port as trusted or untrusted port."
    ::= { dhcpSnoopingCurCfgPortTableEntry 2 }

dhcpSnoopingCurCfgPortRateLimit    OBJECT-TYPE
    SYNTAX      Integer32 
    MAX-ACCESS  read-only
    STATUS      current
    DESCRIPTION
        "Set port DHCP packet rate limit(pps). 
         Its ranges is 0 ~ 2048, set 0 to disable rate limit."
    ::= { dhcpSnoopingCurCfgPortTableEntry 3 }


dhcpSnoopingNewCfgPortTable             OBJECT-TYPE
    SYNTAX      SEQUENCE OF DHCPSnoopingNewCfgPortTableEntry
    MAX-ACCESS  not-accessible
    STATUS      current
    DESCRIPTION
        "DHCP Snooping Port Configuration Table."
    ::= { dhcpsnpCfg 6 }

dhcpSnoopingNewCfgPortTableEntry        OBJECT-TYPE
    SYNTAX      DHCPSnoopingNewCfgPortTableEntry
    MAX-ACCESS  not-accessible
    STATUS      current
    DESCRIPTION
        "A row in the DHCP Snooping Port Configuration Table"
    INDEX  { dhcpSnoopingNewCfgportId }
    ::= { dhcpSnoopingNewCfgPortTable 1 }

DHCPSnoopingNewCfgPortTableEntry ::= SEQUENCE {
    dhcpSnoopingNewCfgportId          Integer32,
    dhcpSnoopingNewCfgportTrusted      INTEGER,
    dhcpSnoopingNewCfgportRateLimit  Integer32
}

dhcpSnoopingNewCfgportId           OBJECT-TYPE
    SYNTAX      Integer32 
    MAX-ACCESS  read-only
    STATUS      current
    DESCRIPTION
        "Port ID of this DHCP Snooping port configration."
    ::= { dhcpSnoopingNewCfgPortTableEntry 1 }

dhcpSnoopingNewCfgportTrusted     OBJECT-TYPE
    SYNTAX      INTEGER  {
                    trusted(1),
                    untrusted(2)
                }  
    MAX-ACCESS  read-write
    STATUS      current
    DESCRIPTION
        "Set port as trusted or untrusted port."
::= { dhcpSnoopingNewCfgPortTableEntry 2 }

dhcpSnoopingNewCfgportRateLimit    OBJECT-TYPE
    SYNTAX      Integer32 
    MAX-ACCESS  read-write
    STATUS      current
    DESCRIPTION
        "Set port DHCP packet rate limit(pps). Set 0 to disable rate limit."
    ::= { dhcpSnoopingNewCfgPortTableEntry 3 }

   
dhcpSnoopingCurCfgVlanTable             OBJECT-TYPE
    SYNTAX      SEQUENCE OF DHCPSnoopingCurCfgVlanTableEntry
    MAX-ACCESS  not-accessible
    STATUS      current
    DESCRIPTION
        "DHCP Snooping VLAN Table."
    ::= { dhcpsnpCfg 7 }

dhcpSnoopingCurCfgVlanTableEntry        OBJECT-TYPE
    SYNTAX      DHCPSnoopingCurCfgVlanTableEntry
    MAX-ACCESS  not-accessible
    STATUS      current
    DESCRIPTION
        "A row in the DHCP Snooping VLAN Table"
    INDEX  { dhcpSnoopingCurCfgVlanId }
    ::= { dhcpSnoopingCurCfgVlanTable 1 }

DHCPSnoopingCurCfgVlanTableEntry ::= SEQUENCE {
    dhcpSnoopingCurCfgVlanId                 Integer32,
    dhcpSnoopingCurCfgVlanOnState        INTEGER
}
    
dhcpSnoopingCurCfgVlanId           OBJECT-TYPE
    SYNTAX      Integer32 (1..4094)
    MAX-ACCESS  read-only
    STATUS      current
    DESCRIPTION
        "VLAN ID of this DHCP Snooping VLAN configration."
    ::= { dhcpSnoopingCurCfgVlanTableEntry 1 }
    
dhcpSnoopingCurCfgVlanOnState           OBJECT-TYPE
    SYNTAX      INTEGER  {
                    on(1),
                    off(2)
                }
    MAX-ACCESS  read-only
    STATUS      current
    DESCRIPTION
        "on/off state of DHCP Snooping on this VLAN."
    ::= { dhcpSnoopingCurCfgVlanTableEntry 2 }    
    
dhcpSnoopingNewCfgVlanTable             OBJECT-TYPE
    SYNTAX      SEQUENCE OF DHCPSnoopingNewCfgVLANTableEntry
    MAX-ACCESS  not-accessible
    STATUS      current
    DESCRIPTION
        "DHCP Snooping VLAN Table."
    ::= { dhcpsnpCfg 8 }

dhcpSnoopingNewCfgVlanTableEntry        OBJECT-TYPE
    SYNTAX      DHCPSnoopingNewCfgVLANTableEntry
    MAX-ACCESS  not-accessible
    STATUS      current
    DESCRIPTION
        "A row in the DHCP Snooping VLAN Table"
    INDEX  { dhcpSnoopingNewCfgVlanId }
    ::= { dhcpSnoopingNewCfgVlanTable 1 }

DHCPSnoopingNewCfgVLANTableEntry ::= SEQUENCE {
    dhcpSnoopingNewCfgVlanId             Integer32,
    dhcpSnoopingNewCfgVlanOnState         INTEGER
}

dhcpSnoopingNewCfgVlanId           OBJECT-TYPE
    SYNTAX      Integer32 (1..4094)
    MAX-ACCESS  read-only
    STATUS      current
    DESCRIPTION
        "VLAN ID of this DHCP Snooping VLAN configration."
    ::= { dhcpSnoopingNewCfgVlanTableEntry 1 }
    
dhcpSnoopingNewCfgVlanOnState           OBJECT-TYPE
    SYNTAX      INTEGER  {
                    on(1),
                    off(2)
                }
    MAX-ACCESS  read-write
    STATUS      current
    DESCRIPTION
        "Enable/Disable DHCP Snooping on this VLAN."
    ::= { dhcpSnoopingNewCfgVlanTableEntry 2 }    
    
dhcpSnoopingBindingInfoTable             OBJECT-TYPE
    SYNTAX      SEQUENCE OF  DHCPSnoopingBindingInfoEntry 
    MAX-ACCESS  not-accessible
    STATUS      current
    DESCRIPTION
        "DHCP Snooping binding Table."
    ::= { dhcpsnpInfo 1 }

dhcpSnoopingBindingInfoEntry        OBJECT-TYPE
    SYNTAX      DHCPSnoopingBindingInfoEntry
    MAX-ACCESS  not-accessible
    STATUS      current
    DESCRIPTION
        "A row in the DHCP Snooping binding Table"
    INDEX  { dhcpSnoopingBindingInfoIndex }
    ::= { dhcpSnoopingBindingInfoTable             1 }

DHCPSnoopingBindingInfoEntry ::= SEQUENCE {
	    dhcpSnoopingBindingInfoIndex        Integer32,
        dhcpSnoopingBindingInfoMac          OCTET STRING,
        dhcpSnoopingBindingInfoIp                IpAddress,
        dhcpSnoopingBindingInfoVLAN         Integer32,
        dhcpSnoopingBindingInfoPort         Integer32,
        dhcpSnoopingBindingInfoExpiry       Unsigned32,
        dhcpSnoopingBindingInfoType         INTEGER
    }

dhcpSnoopingBindingInfoIndex           OBJECT-TYPE
    SYNTAX      Integer32
    MAX-ACCESS  read-only
    STATUS      current
    DESCRIPTION
        "Index of this DHCP Snooping binding entry."
    ::= { dhcpSnoopingBindingInfoEntry 1 }
    
dhcpSnoopingBindingInfoMac           OBJECT-TYPE
    SYNTAX      OCTET STRING 
    MAX-ACCESS  read-create
    STATUS      current
    DESCRIPTION
        "Mac Address of this DHCP Snooping binding entry."
    ::= { dhcpSnoopingBindingInfoEntry 2 }

dhcpSnoopingBindingInfoIp           OBJECT-TYPE
    SYNTAX      IpAddress 
    MAX-ACCESS  read-write
    STATUS      current
    DESCRIPTION
        "Ip Address of this DHCP Snooping binding entry."
    ::= { dhcpSnoopingBindingInfoEntry 3 }
    
dhcpSnoopingBindingInfoVLAN           OBJECT-TYPE
    SYNTAX      Integer32 
    MAX-ACCESS  read-write
    STATUS      current
    DESCRIPTION
        "VLAN ID of this DHCP Snooping binding entry."
    ::= { dhcpSnoopingBindingInfoEntry 4 }    

dhcpSnoopingBindingInfoPort           OBJECT-TYPE
    SYNTAX      Integer32 
    MAX-ACCESS  read-write
    STATUS      current
    DESCRIPTION
        "Port Number of this DHCP Snooping binding entry."
    ::= { dhcpSnoopingBindingInfoEntry 5 }    

dhcpSnoopingBindingInfoExpiry           OBJECT-TYPE
    SYNTAX      Unsigned32   
    MAX-ACCESS  read-write
    STATUS      current
    DESCRIPTION
        "The lease time of this DHCP Snooping binding entry.
         Set 0 to remove this entry"
    ::= { dhcpSnoopingBindingInfoEntry 6 }
    
dhcpSnoopingBindingInfoType           OBJECT-TYPE
    SYNTAX      INTEGER  {
                    static(1),
                    dynamic(2)
                } 
    MAX-ACCESS  read-write
    STATUS      current
    DESCRIPTION
        "Show How this DHCP Snooping binding entry come from."
    ::= { dhcpSnoopingBindingInfoEntry 7 }
     

    
-- ----------------------------------------------------------------------------
-- { INSERT:  DHCP Snooping stat
-- ----------------------------------------------------------------------------

dhcpSnoopingStatInPacketRequest        OBJECT-TYPE
    SYNTAX      Integer32 
    MAX-ACCESS  read-only
    STATUS      current
    DESCRIPTION
        "Counter of DHCP REQUEST messages received."
    ::= { dhcpsnpStats 1 }
    
dhcpSnoopingStatInPacketReply           OBJECT-TYPE
    SYNTAX      Integer32 
    MAX-ACCESS  read-only
    STATUS      current
    DESCRIPTION
        "Counter of DHCP REPLY messages received."
    ::= { dhcpsnpStats 2 }

dhcpSnoopingStatDroppedPacketInvalid           OBJECT-TYPE
    SYNTAX      Integer32 
    MAX-ACCESS  read-only
    STATUS      current
    DESCRIPTION
        "Counter of dropped DHCP messages due to invalid packet."
    ::= { dhcpsnpStats 3 }

dhcpSnoopingStatDroppedPacketRateLimit           OBJECT-TYPE
    SYNTAX      Integer32 
    MAX-ACCESS  read-only
    STATUS      current
    DESCRIPTION
        "Counter of dropped DHCP messages due to Rate Limit in software."
    ::= { dhcpsnpStats 4 }
    
dhcpSnoopingStatDroppedPacketOther           OBJECT-TYPE
    SYNTAX      Integer32 
    MAX-ACCESS  read-only
    STATUS      current
    DESCRIPTION
        "Counter of dropped DHCP messages due to other reason."
    ::= { dhcpsnpStats 5 }
    

vrrpOper          OBJECT IDENTIFIER ::= { layer3Oper 1 }

dhcpInfoMacAddr OBJECT-TYPE
    SYNTAX  DisplayString
    MAX-ACCESS  read-only
    STATUS  current
    DESCRIPTION
        "The MAC address of the interface."
    ::= { dhcpInfo 1}

dhcpInfoAddr OBJECT-TYPE
    SYNTAX  IpAddress
    MAX-ACCESS  read-only
    STATUS  current
    DESCRIPTION
        "The IP address of the interface."
    ::= { dhcpInfo 2}

dhcpInfoSubnetMask OBJECT-TYPE
    SYNTAX  IpAddress
    MAX-ACCESS  read-only
    STATUS  current
    DESCRIPTION
        "The subnet mask of the interface."
    ::= { dhcpInfo 3}

dhcpInfoDefaultGateway OBJECT-TYPE
    SYNTAX  IpAddress
    MAX-ACCESS  read-only
    STATUS  current
    DESCRIPTION
        "The IP address of default gateway for the interface."
    ::= { dhcpInfo 4}

dhcpInfoServer OBJECT-TYPE
    SYNTAX  IpAddress
    MAX-ACCESS  read-only
    STATUS  current
    DESCRIPTION
        "The IP address of the DHCP server that leased the ip of the interface."
    ::= { dhcpInfo 5}

dhcpInfoLeaseObtained  OBJECT-TYPE
    SYNTAX  DisplayString (SIZE(0..32))
    MAX-ACCESS  read-only
    STATUS  current
    DESCRIPTION
        "The time and date when the lease was obtained ."
    ::= { dhcpInfo 6}

dhcpInfoLeaseExpires   OBJECT-TYPE
    SYNTAX  DisplayString (SIZE(0..32))
    MAX-ACCESS  read-only
    STATUS  current
    DESCRIPTION
        "The time and date when the lease was obtained ."
    ::= { dhcpInfo 7} 


-- IP Configuration
ipInterfaceTableMax OBJECT-TYPE
    SYNTAX  Integer32
    MAX-ACCESS  read-only
    STATUS  current
    DESCRIPTION
        "The maximum number of rows in the IP interface table."
    ::= { ipInterfaceCfg 1 }

ipCurCfgIntfTable OBJECT-TYPE
    SYNTAX  SEQUENCE OF IpCurCfgIntfEntry
    MAX-ACCESS  not-accessible
    STATUS  current
    DESCRIPTION
        "The table of IP interface configuration."
    ::= { ipInterfaceCfg 2 }

ipCurCfgIntfEntry OBJECT-TYPE
    SYNTAX  IpCurCfgIntfEntry
    MAX-ACCESS  not-accessible
    STATUS  current
    DESCRIPTION
        "A row in the Ip interface table"
    INDEX   { ipCurCfgIntfIndex }
    ::= { ipCurCfgIntfTable 1 }

IpCurCfgIntfEntry ::= SEQUENCE {
    ipCurCfgIntfIndex         Integer32,
    ipCurCfgIntfAddr          DisplayString,
    ipCurCfgIntfMask          DisplayString,
    ipCurCfgIntfBroadcast     IpAddress,
    ipCurCfgIntfState         INTEGER,
    ipCurCfgIntfBootpRelay    INTEGER,
    ipCurCfgIntfRouteAdv      INTEGER,
    ipCurCfgIntfManagedCfg    INTEGER,
    ipCurCfgIntfOtherCfg      INTEGER,
    ipCurCfgIntfAdvLifetime   INTEGER,
    ipCurCfgIntfDadAttempts   INTEGER,
    ipCurCfgIntfReachTime     Gauge32,
    ipCurCfgIntfAdvInterval   INTEGER,
    ipCurCfgIntfAdvIntervalMin    INTEGER,
    ipCurCfgIntfRetransmitTimer   Gauge32,
    ipCurCfgIntfHopLimit          INTEGER,
    ipCurCfgIntfAdvMtu          INTEGER,
    ipCurCfgIntfIp6Host       INTEGER,
    ipCurCfgIntfIp6Dstun      INTEGER,
    ipCurCfgSecIntfAddr          DisplayString,
    ipCurCfgSecIntfPrefix        Integer32,
    ipCurCfgSecIntfAnycast       INTEGER, 
    ipCurCfgIntfAnycast          INTEGER, 
    ipCurCfgIntfVlan          Integer32
    }

ipCurCfgIntfIndex OBJECT-TYPE
    SYNTAX  Integer32
    MAX-ACCESS  read-only
    STATUS  current
    DESCRIPTION
        "The interface number for which the IP information is related."
    ::= { ipCurCfgIntfEntry 1}

ipCurCfgIntfAddr OBJECT-TYPE
    SYNTAX  DisplayString  (SIZE(0..40))
    MAX-ACCESS read-only
    STATUS  current
    DESCRIPTION
        "This field configures the new IP/IPv6 addr of the interface.
         Address should be IPv4 dotted-quads or IPv6 16-byte hexadecimal 
         colon notation.
         Valid IPv6 address should be in any of the following forms
           xxxx:xxxx:xxxx:xxxx:xxxx:xxxx:xxxx:xxxx or
           xxxx::xxxx:xxxx:xxxx:xxxx"
    ::= { ipCurCfgIntfEntry 2 }

ipCurCfgIntfMask OBJECT-TYPE
    SYNTAX  DisplayString  (SIZE(0..15))
    MAX-ACCESS read-only
    STATUS  current
    DESCRIPTION
        "The subnet mask as IPv4 dotted-quads OR
         the IPv6 prefix length (integer in range 0..128)
         associated with this IP address ."
    ::= { ipCurCfgIntfEntry 3 }

ipCurCfgIntfBroadcast OBJECT-TYPE
    SYNTAX  IpAddress
    MAX-ACCESS  read-only
    STATUS  obsolete  
    DESCRIPTION
        "The broadcast address of the interface."
    ::= { ipCurCfgIntfEntry 4 }

ipCurCfgIntfVlan OBJECT-TYPE
    SYNTAX  Integer32
    MAX-ACCESS  read-only
    STATUS  current  
    DESCRIPTION
        "The VLAN associated with the interface."
    ::= { ipCurCfgIntfEntry 5 }

ipCurCfgIntfState OBJECT-TYPE
    SYNTAX  INTEGER { 
    enabled(2),
    disabled(3)
    }
    MAX-ACCESS  read-only
    STATUS  current  
    DESCRIPTION
        "The state of the interface."
    ::= { ipCurCfgIntfEntry 6 }

ipCurCfgIntfBootpRelay OBJECT-TYPE
    SYNTAX  INTEGER { 
    enabled(1),
    disabled(2)
    }
    MAX-ACCESS  read-only
    STATUS  current  
    DESCRIPTION
        "Enable/disable BOOTP relay."
    ::= { ipCurCfgIntfEntry 7 }


ipCurCfgIntfRouteAdv  OBJECT-TYPE
    SYNTAX  INTEGER {
        enabled(1),
        disabled(2)
        }
    MAX-ACCESS  read-only
    STATUS  current
    DESCRIPTION
        "Enable/disable route advertisement of the interface."
    ::= { ipCurCfgIntfEntry 12 }

ipCurCfgIntfManagedCfg  OBJECT-TYPE
    SYNTAX  INTEGER {
        enabled(1),
        disabled(2)
        }
    MAX-ACCESS  read-only
    STATUS  current
    DESCRIPTION
        "Enable/disable Managed config flag of the interface, which
         allows the host to use DHCP for address configuration."
    ::= { ipCurCfgIntfEntry 13 }

ipCurCfgIntfOtherCfg  OBJECT-TYPE
    SYNTAX  INTEGER {
        enabled(1),
        disabled(2)
        }
    MAX-ACCESS  read-only
    STATUS  current
    DESCRIPTION
        "Enable/disable Other config flag of the interface,
        which allows the host to use DHCP for other stateful configuration."
    ::= { ipCurCfgIntfEntry 14 }

ipCurCfgIntfAdvLifetime  OBJECT-TYPE
    SYNTAX  INTEGER (0..9000)
    MAX-ACCESS  read-only
    STATUS  current
    DESCRIPTION
        "Set Router Advertisement lifetime of the interface."
    ::= { ipCurCfgIntfEntry 15 }

ipCurCfgIntfDadAttempts  OBJECT-TYPE
    SYNTAX  INTEGER (1..10)
    MAX-ACCESS  read-only
    STATUS  current
    DESCRIPTION
        "Set the number of duplicate address detection (dad)
        attempts of the interface."
    ::= { ipCurCfgIntfEntry 16 }

ipCurCfgIntfReachTime  OBJECT-TYPE
    SYNTAX  Gauge32 (0..3600000)
    MAX-ACCESS  read-only
    STATUS  current
    DESCRIPTION
        "Set the advertised reachability time of the interface in ms."
    ::= { ipCurCfgIntfEntry 17 }

ipCurCfgIntfAdvInterval  OBJECT-TYPE
    SYNTAX  INTEGER (4..1800)
    MAX-ACCESS  read-only
    STATUS  current
    DESCRIPTION
        "Set the IPv6 Router Advertisement interval of the interface."
    ::= { ipCurCfgIntfEntry 18 }

ipCurCfgIntfAdvIntervalMin  OBJECT-TYPE
    SYNTAX  INTEGER (3..1350)
    MAX-ACCESS  read-only
    STATUS  current
    DESCRIPTION
        "Set the IPv6 Router Advertisement Minimum interval limit 
        of the interface."
    ::= { ipCurCfgIntfEntry 19 }

ipCurCfgIntfRetransmitTimer  OBJECT-TYPE
    SYNTAX  Gauge32 (0..4294967295)
    MAX-ACCESS  read-only
    STATUS  current
    DESCRIPTION
        "Set the IPv6 Router Advertisement Retransmit Timer in ms."
    ::= { ipCurCfgIntfEntry 20 }

ipCurCfgIntfHopLimit  OBJECT-TYPE
    SYNTAX  INTEGER (0..255)
    MAX-ACCESS  read-only
    STATUS  current
    DESCRIPTION
        "Set the IPv6 Router Advertisement Current Hop Limit"
    ::= { ipCurCfgIntfEntry 21 }

ipCurCfgIntfAdvMtu  OBJECT-TYPE
    SYNTAX  INTEGER {
        enabled(1),
        disabled(2)
        }
    MAX-ACCESS  read-only
    STATUS  current
    DESCRIPTION
        "Enable/disable Advertise MTU option."
    ::= { ipCurCfgIntfEntry 22 }

ipCurCfgIntfIp6Host  OBJECT-TYPE
    SYNTAX  INTEGER {
        enabled(1),
        disabled(2)
        }
    MAX-ACCESS  read-only
    STATUS  current
    DESCRIPTION
        "Enable/disable IPv6 host mode on the interface."
    ::= { ipCurCfgIntfEntry 23 }


ipCurCfgSecIntfAddr OBJECT-TYPE
    SYNTAX  DisplayString  (SIZE(0..40))
    MAX-ACCESS read-only
    STATUS  current
    DESCRIPTION
        "This field configures the new IP/IPv6 addr of the interface.
         Address should be in IPv6 4-byte haxadecimal 
         colon notation.
         Valid IPv6 address should be in any of the following forms
           xxxx:xxxx:xxxx:xxxx:xxxx:xxxx:xxxx:xxxx or
           xxxx::xxxx:xxxx:xxxx:xxxx"
    ::= { ipCurCfgIntfEntry 25 }

ipCurCfgSecIntfPrefix OBJECT-TYPE
    SYNTAX  Integer32 
    MAX-ACCESS read-only
    STATUS  current
    DESCRIPTION
        "The IPv6 prefix length (integer in range 0..128)
         associated with this IP address ."
    ::= { ipCurCfgIntfEntry 26 }

ipCurCfgIntfAnycast  OBJECT-TYPE
    SYNTAX  INTEGER {
        anycast(1),
        none(2)
        }
    MAX-ACCESS  read-only
    STATUS  current
    DESCRIPTION
        "This field has the value of anycast(1) if IPv6 interface address
         is anycast and none(2) if not."
    ::= { ipCurCfgIntfEntry 27 }

ipCurCfgSecIntfAnycast  OBJECT-TYPE
    SYNTAX  INTEGER {
        anycast(1),
        none(2)
        }
    MAX-ACCESS  read-only
    STATUS  current
    DESCRIPTION
        "This field has the value of anycast(1) if secondary IPv6 interface address
         is anycast and none(2) if not."
    ::= { ipCurCfgIntfEntry 28 }
ipCurCfgIntfIp6Dstun  OBJECT-TYPE
    SYNTAX  INTEGER {
        enabled(1),
        disabled(2)
        }
    MAX-ACCESS  read-only
    STATUS  current
    DESCRIPTION
        "Enable/disable sending of ICMP Unreachable messages."
    ::= { ipCurCfgIntfEntry 29 }

ipNewCfgIntfTable OBJECT-TYPE
    SYNTAX  SEQUENCE OF IpNewCfgIntfEntry
    MAX-ACCESS  not-accessible
    STATUS  current
    DESCRIPTION
        "The table of interface in the new configuration block."
    ::= { ipInterfaceCfg 3 }

ipNewCfgIntfEntry OBJECT-TYPE
    SYNTAX  IpNewCfgIntfEntry
    MAX-ACCESS  not-accessible
    STATUS  current
    DESCRIPTION
        "A row in the Ip interface table"
    INDEX   { ipNewCfgIntfIndex }
    ::= { ipNewCfgIntfTable 1 }
 
IpNewCfgIntfEntry ::= SEQUENCE {
    ipNewCfgIntfIndex         Integer32,
    ipNewCfgIntfAddr          DisplayString,
    ipNewCfgIntfMask          DisplayString,
    ipNewCfgIntfVlan          Integer32,
    ipNewCfgIntfState         INTEGER,
    ipNewCfgIntfBootpRelay    INTEGER,
    ipNewCfgIntfRouteAdv      INTEGER,
    ipNewCfgIntfIp6Host       INTEGER,
    ipNewCfgIntfIp6Dstun      INTEGER,
    ipNewCfgIntfManagedCfg    INTEGER,
    ipNewCfgIntfOtherCfg      INTEGER,
    ipNewCfgIntfAdvLifetime   INTEGER,
    ipNewCfgIntfDadAttempts   INTEGER,
    ipNewCfgIntfReachTime     Gauge32,
    ipNewCfgIntfAdvInterval   INTEGER,
    ipNewCfgIntfAdvIntervalMin    INTEGER,
    ipNewCfgIntfRetransmitTimer   Gauge32,
    ipNewCfgIntfHopLimit          INTEGER,
    ipNewCfgIntfAdvMtu            INTEGER,
    ipNewCfgSecIntfAddr          DisplayString,
    ipNewCfgSecIntfPrefix        Integer32,
    ipNewCfgSecIntfAnycast       INTEGER, 
    ipNewCfgIntfAnycast          INTEGER, 
    ipNewCfgIntfDelete        INTEGER
    }
 
ipNewCfgIntfIndex OBJECT-TYPE
    SYNTAX  Integer32
    MAX-ACCESS  read-only
    STATUS  current
    DESCRIPTION
    "The interface number for which the IP information is related."
    ::= { ipNewCfgIntfEntry 1 }


ipNewCfgIntfAddr OBJECT-TYPE
    SYNTAX  DisplayString  (SIZE(0..40))
    MAX-ACCESS read-create
    STATUS  current
    DESCRIPTION
        "This field configures the new IP/IPv6 addr of the interface.
         Address should be IPv4 dotted-quads or IPv6 16-byte hexadecimal 
         colon notation.
         Valid IPv6 address should be in any of the following forms
           xxxx:xxxx:xxxx:xxxx:xxxx:xxxx:xxxx:xxxx or
           xxxx::xxxx:xxxx:xxxx:xxxx"
    ::= { ipNewCfgIntfEntry 2 }

ipNewCfgIntfMask OBJECT-TYPE
    SYNTAX  DisplayString  (SIZE(0..15))
    MAX-ACCESS read-create
    STATUS  current
    DESCRIPTION
        "The subnet mask as IPv4 dotted-quads OR
         the IPv6 prefix length (integer in range 0..128)
         associated with this IP address ."
    ::= { ipNewCfgIntfEntry 3 }


ipNewCfgIntfVlan OBJECT-TYPE
    SYNTAX  Integer32
    MAX-ACCESS  read-create
    STATUS  current  
    DESCRIPTION
        "The VLAN associated with the interface."
    ::= { ipNewCfgIntfEntry 5 }

ipNewCfgIntfState OBJECT-TYPE
    SYNTAX  INTEGER { 
    enabled(2),
    disabled(3)
    }
    MAX-ACCESS  read-create
    STATUS  current  
    DESCRIPTION
        "The state of the interface."
    ::= { ipNewCfgIntfEntry 6 }

ipNewCfgIntfDelete OBJECT-TYPE
    SYNTAX  INTEGER { 
    other(1),
        delete(2)
    }
    MAX-ACCESS  read-create
    STATUS  current
    DESCRIPTION
        "When set to the value of 2 (delete), the entire row is deleted. 
         When read, other(1) is returned. Setting the value to anything 
         other than 2(delete) has no effect on the state of the row."
    ::= { ipNewCfgIntfEntry 7 }

ipNewCfgIntfBootpRelay OBJECT-TYPE
    SYNTAX  INTEGER { 
    enabled(1),
    disabled(2)
    }
    MAX-ACCESS  read-create
    STATUS  current  
    DESCRIPTION
        "Enable/disable BOOTP relay."
    ::= { ipNewCfgIntfEntry 8 }


ipNewCfgIntfRouteAdv  OBJECT-TYPE
    SYNTAX  INTEGER {
        enabled(1),
        disabled(2)
        }
    MAX-ACCESS  read-create
    STATUS  current
    DESCRIPTION
        "Enable/disable route advertisement of the interface."
    ::= { ipNewCfgIntfEntry 13 }

ipNewCfgIntfManagedCfg  OBJECT-TYPE
    SYNTAX  INTEGER {
        enabled(1),
        disabled(2)
        }
    MAX-ACCESS  read-create
    STATUS  current
    DESCRIPTION
        "Enable/disable Managed config flag of the interface, which 
         allows the host to use DHCP for address configuration."
    ::= { ipNewCfgIntfEntry 14 }

ipNewCfgIntfOtherCfg  OBJECT-TYPE
    SYNTAX  INTEGER {
        enabled(1),
        disabled(2)
        }
    MAX-ACCESS  read-create
    STATUS  current
    DESCRIPTION
        "Enable/disable Other config flag of the interface, 
        which allows the host to use DHCP for other stateful configuration."
    ::= { ipNewCfgIntfEntry 15 }

ipNewCfgIntfAdvLifetime  OBJECT-TYPE
    SYNTAX  INTEGER (0..9000)
    MAX-ACCESS  read-create
    STATUS  current
    DESCRIPTION
        "Set Router Advertisement lifetime of the interface."
    ::= { ipNewCfgIntfEntry 16 }

ipNewCfgIntfDadAttempts  OBJECT-TYPE
    SYNTAX  INTEGER (1..10)
    MAX-ACCESS  read-create
    STATUS  current
    DESCRIPTION
        "Set the number of duplicate address detection (dad) 
        attempts of the interface."
    ::= { ipNewCfgIntfEntry 17 }

ipNewCfgIntfReachTime  OBJECT-TYPE
    SYNTAX  Gauge32 (0..3600000)
    MAX-ACCESS  read-create
    STATUS  current
    DESCRIPTION
        "Set the advertised reachability time of the interface in ms."
    ::= { ipNewCfgIntfEntry 18 }

ipNewCfgIntfAdvInterval  OBJECT-TYPE
    SYNTAX  INTEGER (4..1800)
    MAX-ACCESS  read-create
    STATUS  current
    DESCRIPTION
        "Set the IPv6 Router Advertisement interval of the interface."
    ::= { ipNewCfgIntfEntry 19 }

ipNewCfgIntfAdvIntervalMin  OBJECT-TYPE
    SYNTAX  INTEGER (3..1350)
    MAX-ACCESS  read-create
    STATUS  current
    DESCRIPTION
        "Set the IPv6 Router Advertisement Minimum interval limit 
        of the interface."
    ::= { ipNewCfgIntfEntry 20 }

ipNewCfgIntfRetransmitTimer  OBJECT-TYPE
    SYNTAX  Gauge32 (0..4294967295)
    MAX-ACCESS  read-create
    STATUS  current
    DESCRIPTION
        "Set the IPv6 Router Advertisement Retransmit Timer in ms."
    ::= { ipNewCfgIntfEntry 21 }

ipNewCfgIntfHopLimit  OBJECT-TYPE
    SYNTAX  INTEGER (0..255)
    MAX-ACCESS  read-create
    STATUS  current
    DESCRIPTION
        "Set the IPv6 Router Advertisement Current Hop Limit"
    ::= { ipNewCfgIntfEntry 22 }

ipNewCfgIntfAdvMtu  OBJECT-TYPE
    SYNTAX  INTEGER {
        enabled(1),
        disabled(2)
        }
    MAX-ACCESS  read-create
    STATUS  current
    DESCRIPTION
        "Enable/disable Advertise MTU option."
    ::= { ipNewCfgIntfEntry 23 }

ipNewCfgIntfIp6Host  OBJECT-TYPE
    SYNTAX  INTEGER {
        enabled(1),
        disabled(2)
        }
    MAX-ACCESS  read-create
    STATUS  current
    DESCRIPTION
        "Enable/disable IPv6 host mode on the interface."
    ::= { ipNewCfgIntfEntry 24 }


ipNewCfgSecIntfAddr OBJECT-TYPE
    SYNTAX  DisplayString  (SIZE(0..40))
    MAX-ACCESS read-write
    STATUS  current
    DESCRIPTION
        "This field configures the new IPv6 addr of the interface.
         Address should be in IPv6 4-byte haxadecimal 
         colon notation.
         Valid IPv6 address should be in any of the following forms
           xxxx:xxxx:xxxx:xxxx:xxxx:xxxx:xxxx:xxxx or
           xxxx::xxxx:xxxx:xxxx:xxxx"
    ::= { ipNewCfgIntfEntry 26 }

ipNewCfgSecIntfPrefix OBJECT-TYPE
    SYNTAX  Integer32 
    MAX-ACCESS read-write
    STATUS  current
    DESCRIPTION
        "The IPv6 prefix length (integer in range 0..128)
         associated with this IP address ."
    ::= { ipNewCfgIntfEntry 27 }

ipNewCfgIntfAnycast  OBJECT-TYPE
    SYNTAX  INTEGER {
        anycast(1),
        none(2)
        }
    MAX-ACCESS  read-write
    STATUS  current
    DESCRIPTION
        "This field has the value of anycast(1) if IPv6 interface address
         is anycast and none(2) if not."
    ::= { ipNewCfgIntfEntry 28 }

ipNewCfgSecIntfAnycast  OBJECT-TYPE
    SYNTAX  INTEGER {
        anycast(1),
        none(2)
        }
    MAX-ACCESS  read-write
    STATUS  current
    DESCRIPTION
        "This field has the value of anycast(1) if secondary IPv6 interface address
         is anycast and none(2) if not."
    ::= { ipNewCfgIntfEntry 29 }

ipNewCfgIntfIp6Dstun  OBJECT-TYPE
    SYNTAX  INTEGER {
        enabled(1),
        disabled(2)
        }
    MAX-ACCESS  read-create
    STATUS  current
    DESCRIPTION
        "Enable/disable sending of ICMP Unreachable messages."
    ::= { ipNewCfgIntfEntry 30 }




-- IP Loopback Configuration

ipInterfaceLoopbackTableMax OBJECT-TYPE
    SYNTAX  Integer32
    MAX-ACCESS  read-only
    STATUS  current
    DESCRIPTION
        "The maximum number of rows in the IP Loopback interface table."
    ::= { ipInterfaceLoopbackCfg 1 }

ipCurCfgIntfLoopbackTable OBJECT-TYPE
    SYNTAX  SEQUENCE OF IpCurCfgIntfLoopbackEntry
    MAX-ACCESS  not-accessible
    STATUS  current
    DESCRIPTION
        "The table of IP Loopback interface configuration."
    ::= { ipInterfaceLoopbackCfg 2 }

ipCurCfgIntfLoopbackEntry OBJECT-TYPE
    SYNTAX  IpCurCfgIntfLoopbackEntry
    MAX-ACCESS  not-accessible
    STATUS  current
    DESCRIPTION
        "A row in the Ip Loopback interface table"
    INDEX   { ipCurCfgIntfLoopbackIndex }
    ::= { ipCurCfgIntfLoopbackTable 1 }

IpCurCfgIntfLoopbackEntry ::= SEQUENCE {
    ipCurCfgIntfLoopbackIndex         Integer32,
    ipCurCfgIntfLoopbackAddr          IpAddress,
    ipCurCfgIntfLoopbackMask          IpAddress,
    ipCurCfgIntfLoopbackBroadcast     IpAddress,
    ipCurCfgIntfLoopbackState         INTEGER 
    }
 
ipCurCfgIntfLoopbackIndex OBJECT-TYPE
    SYNTAX  Integer32
    MAX-ACCESS  read-only
    STATUS  current
    DESCRIPTION
        "The Loopback interface number for which the IP information is related."
    ::= { ipCurCfgIntfLoopbackEntry 1}

ipCurCfgIntfLoopbackAddr OBJECT-TYPE
    SYNTAX  IpAddress
    MAX-ACCESS  read-only
    STATUS  current
    DESCRIPTION
        "The IP address of the interface."
    ::= { ipCurCfgIntfLoopbackEntry 2 }

ipCurCfgIntfLoopbackMask OBJECT-TYPE
    SYNTAX  IpAddress
    MAX-ACCESS  read-only
    STATUS  current  
    DESCRIPTION
        "The subnet mask of the interface."
    ::= { ipCurCfgIntfLoopbackEntry 3 }

ipCurCfgIntfLoopbackBroadcast OBJECT-TYPE
    SYNTAX  IpAddress
    MAX-ACCESS  read-only
    STATUS  current  
    DESCRIPTION
        "The broadcast address of the interface."
    ::= { ipCurCfgIntfLoopbackEntry 4 }

ipCurCfgIntfLoopbackState OBJECT-TYPE
    SYNTAX  INTEGER { 
    enabled(2),
    disabled(3)
    }
    MAX-ACCESS  read-only
    STATUS  current  
    DESCRIPTION
        "The state of the interface."
    ::= { ipCurCfgIntfLoopbackEntry 6 }

ipNewCfgIntfLoopbackTable OBJECT-TYPE
    SYNTAX  SEQUENCE OF IpNewCfgIntfLoopbackEntry
    MAX-ACCESS  not-accessible
    STATUS  current
    DESCRIPTION
        "The table of loopback interface in the new configuration block."
    ::= { ipInterfaceLoopbackCfg 3 }

ipNewCfgIntfLoopbackEntry OBJECT-TYPE
    SYNTAX  IpNewCfgIntfLoopbackEntry
    MAX-ACCESS  not-accessible
    STATUS  current
    DESCRIPTION
        "A row in the Ip Loopback interface table"
    INDEX   { ipNewCfgIntfLoopbackIndex }
    ::= { ipNewCfgIntfLoopbackTable 1 }
 
IpNewCfgIntfLoopbackEntry ::= SEQUENCE {
    ipNewCfgIntfLoopbackIndex         Integer32,
    ipNewCfgIntfLoopbackAddr          IpAddress,
    ipNewCfgIntfLoopbackMask          IpAddress,
    ipNewCfgIntfLoopbackState         INTEGER,
    ipNewCfgIntfLoopbackDelete        INTEGER
    }
 
ipNewCfgIntfLoopbackIndex OBJECT-TYPE
    SYNTAX  Integer32
    MAX-ACCESS  read-only
    STATUS  current
    DESCRIPTION
    "The Loopback interface number for which the IP information is related."
    ::= { ipNewCfgIntfLoopbackEntry 1 }

ipNewCfgIntfLoopbackAddr OBJECT-TYPE
    SYNTAX  IpAddress
    MAX-ACCESS  read-create
    STATUS  current
    DESCRIPTION
        "The IP address of the interface."
    ::= { ipNewCfgIntfLoopbackEntry 2 }

ipNewCfgIntfLoopbackMask OBJECT-TYPE
    SYNTAX  IpAddress
    MAX-ACCESS  read-create
    STATUS  current  
    DESCRIPTION
        "The subnet mask of the interface."
    ::= { ipNewCfgIntfLoopbackEntry 3 }

ipNewCfgIntfLoopbackState OBJECT-TYPE
    SYNTAX  INTEGER { 
    enabled(2),
    disabled(3)
    }
    MAX-ACCESS  read-create
    STATUS  current  
    DESCRIPTION
        "The state of the interface."
    ::= { ipNewCfgIntfLoopbackEntry 6 }

ipNewCfgIntfLoopbackDelete OBJECT-TYPE
    SYNTAX  INTEGER { 
    other(1),
        delete(2)
    }
    MAX-ACCESS  read-create
    STATUS  current
    DESCRIPTION
        "When set to the value of 2 (delete), the entire row is deleted. 
         When read, other(1) is returned. Setting the value to anything 
         other than 2(delete) has no effect on the state of the row."
    ::= { ipNewCfgIntfLoopbackEntry 7 }


-- IP Gateway Table Configuration


ipGatewayTableMax OBJECT-TYPE
    SYNTAX  Integer32
    MAX-ACCESS  read-only
    STATUS  current
    DESCRIPTION
        "The maximum number of rows in the IP gateway table."
    ::= { ipGatewayCfg 3 }

ipCurCfgGwTable OBJECT-TYPE
    SYNTAX  SEQUENCE OF IpCurCfgGwEntry
    MAX-ACCESS  not-accessible
    STATUS  current
    DESCRIPTION
        "The table of gateways in the current configuration block."
    ::= { ipGatewayCfg 4 }

ipCurCfgGwEntry OBJECT-TYPE
    SYNTAX  IpCurCfgGwEntry
    MAX-ACCESS  not-accessible
    STATUS  current
    DESCRIPTION
        "A row in the Ip gateway table"
    INDEX   { ipCurCfgGwIndex }
    ::= { ipCurCfgGwTable 1 }

IpCurCfgGwEntry ::= SEQUENCE {
    ipCurCfgGwIndex         Integer32,
    ipCurCfgGwAddr          IpAddress,
    ipCurCfgGwInterval      INTEGER,
    ipCurCfgGwRetry         INTEGER,
    ipCurCfgGwArp           INTEGER,
    ipCurCfgGwState         INTEGER
    }

ipCurCfgGwIndex OBJECT-TYPE
    SYNTAX  Integer32
    MAX-ACCESS  read-only
    STATUS  current
    DESCRIPTION
        "The gateway number for which the information is related."
    ::= { ipCurCfgGwEntry 1}

ipCurCfgGwAddr OBJECT-TYPE
    SYNTAX  IpAddress
    MAX-ACCESS  read-only
    STATUS  current
    DESCRIPTION
        "The IP address of the default gateway."
    ::= { ipCurCfgGwEntry 2 }

ipCurCfgGwInterval OBJECT-TYPE 
    SYNTAX  INTEGER (0..60)
    MAX-ACCESS  read-only 
    STATUS  current 
    DESCRIPTION 
        "The interval between ping attempts." 
    ::= { ipCurCfgGwEntry 3 }

ipCurCfgGwRetry OBJECT-TYPE
    SYNTAX  INTEGER (1..120)   
    MAX-ACCESS  read-only
    STATUS  current
    DESCRIPTION
        "The number of failed attempts to declare the default gateway DOWN."
    ::= { ipCurCfgGwEntry 4 }

ipCurCfgGwState OBJECT-TYPE
    SYNTAX  INTEGER {
        enabled(2),
        disabled(3)
    }  
    MAX-ACCESS  read-only
    STATUS  current
    DESCRIPTION
        "The state of the default gateway."
    ::= { ipCurCfgGwEntry 5 }

ipCurCfgGwArp OBJECT-TYPE
    SYNTAX  INTEGER {
        enabled(2),
        disabled(3)
        } 
    MAX-ACCESS  read-only
    STATUS  current
    DESCRIPTION
        "The state of ARP only health checks."
    ::= { ipCurCfgGwEntry 6 }



ipNewCfgGwTable OBJECT-TYPE
    SYNTAX  SEQUENCE OF IpNewCfgGwEntry
    MAX-ACCESS  not-accessible
    STATUS  current
    DESCRIPTION
        "The table of gateway in the new configuration block."
    ::= { ipGatewayCfg 5 }

ipNewCfgGwEntry OBJECT-TYPE
    SYNTAX  IpNewCfgGwEntry
    MAX-ACCESS  not-accessible
    STATUS  current
    DESCRIPTION
        "A row in the Ip default gateway table"
    INDEX   { ipNewCfgGwIndex }
    ::= { ipNewCfgGwTable 1 }

IpNewCfgGwEntry ::= SEQUENCE {
    ipNewCfgGwIndex         Integer32,
    ipNewCfgGwAddr          IpAddress,
    ipNewCfgGwInterval      INTEGER,
    ipNewCfgGwRetry         INTEGER,
    ipNewCfgGwState         INTEGER,
    ipNewCfgGwArp           INTEGER,
    ipNewCfgGwDelete        INTEGER
    }

ipNewCfgGwIndex OBJECT-TYPE
    SYNTAX  Integer32
    MAX-ACCESS  read-only
    STATUS  current
    DESCRIPTION
        "The gateway number for which the information is related."
    ::= { ipNewCfgGwEntry 1}

ipNewCfgGwAddr OBJECT-TYPE
    SYNTAX  IpAddress
    MAX-ACCESS  read-create
    STATUS  current
    DESCRIPTION
        "The IP address of the default gateway."
    ::= { ipNewCfgGwEntry 2 }

ipNewCfgGwInterval OBJECT-TYPE 
    SYNTAX  INTEGER (0..60)
    MAX-ACCESS  read-create 
    STATUS  current 
    DESCRIPTION 
        "The interval in seconds between ping attempts." 
    ::= { ipNewCfgGwEntry 3 }

ipNewCfgGwRetry OBJECT-TYPE
    SYNTAX  INTEGER (1..120)   
    MAX-ACCESS  read-create
    STATUS  current
    DESCRIPTION
        "The number of failed attempts to declare the default gateway DOWN."
    ::= { ipNewCfgGwEntry 4 }

ipNewCfgGwState OBJECT-TYPE
    SYNTAX  INTEGER {
        enabled(2),
        disabled(3)
    }
    MAX-ACCESS  read-create
    STATUS  current
    DESCRIPTION
        "The state of the default gateway."
    ::= { ipNewCfgGwEntry 5 }

ipNewCfgGwDelete OBJECT-TYPE
    SYNTAX  INTEGER {
    other(1),
        delete(2)
        }
    MAX-ACCESS  read-create
    STATUS  current
    DESCRIPTION
        "When set to the value of 2 (delete), the entire row is deleted. 
         When read, other is returned. Setting the value to anything other 
         than 2(delete) has no effect on the state of the row."
    ::= { ipNewCfgGwEntry 6 }

ipNewCfgGwArp OBJECT-TYPE
    SYNTAX  INTEGER {
        enabled(2),
        disabled(3)
        }
    MAX-ACCESS  read-create
    STATUS  current
    DESCRIPTION
        "The state of the ARP only health checks."
    ::= { ipNewCfgGwEntry 7 }





--
-- IP Static Route Configuration
--
ipStaticRouteTableMaxSize OBJECT-TYPE
    SYNTAX  Integer32
    MAX-ACCESS  read-only
    STATUS  current
    DESCRIPTION
        "The maximum number of rows in the Static Route table."
    ::= { ipStaticRouteCfg 1 }


ipCurCfgStaticRouteTable OBJECT-TYPE
    SYNTAX  SEQUENCE OF IpCurCfgStaticRouteEntry
    MAX-ACCESS  not-accessible
    STATUS  current
    DESCRIPTION
        "The table of static routes in the current configuration block."
    ::= { ipStaticRouteCfg 2 }

ipCurCfgStaticRouteEntry OBJECT-TYPE
    SYNTAX  IpCurCfgStaticRouteEntry
    MAX-ACCESS  not-accessible
    STATUS  current
    DESCRIPTION
        "A row in the static IP route table"
    INDEX   { ipCurCfgStaticRouteIndx }
    ::= { ipCurCfgStaticRouteTable 1 }

IpCurCfgStaticRouteEntry ::= SEQUENCE {
    ipCurCfgStaticRouteIndx         Integer32,
    ipCurCfgStaticRouteDestIp       IpAddress,
    ipCurCfgStaticRouteMask         IpAddress,
    ipCurCfgStaticRouteGateway      IpAddress,
    ipCurCfgStaticRouteInterface    Integer32
    }

ipCurCfgStaticRouteIndx OBJECT-TYPE
    SYNTAX  Integer32
    MAX-ACCESS  read-only
    STATUS  current
    DESCRIPTION
        "The index of the static routing table."
    ::= { ipCurCfgStaticRouteEntry 1}

ipCurCfgStaticRouteDestIp OBJECT-TYPE
    SYNTAX  IpAddress
    MAX-ACCESS  read-only
    STATUS  current
    DESCRIPTION
        "The destination IP address of this route."
    ::= { ipCurCfgStaticRouteEntry 2}

ipCurCfgStaticRouteMask OBJECT-TYPE 
    SYNTAX  IpAddress
    MAX-ACCESS  read-only 
    STATUS  current 
    DESCRIPTION 
        "The current subnet mask of this route."
    ::= { ipCurCfgStaticRouteEntry 3}

ipCurCfgStaticRouteGateway OBJECT-TYPE 
    SYNTAX  IpAddress
    MAX-ACCESS  read-only 
    STATUS  current 
    DESCRIPTION 
        "The current gateway of this route."
    ::= { ipCurCfgStaticRouteEntry 4}

ipCurCfgStaticRouteInterface OBJECT-TYPE 
    SYNTAX  Integer32
    MAX-ACCESS  read-only 
    STATUS  current 
    DESCRIPTION 
        "The IP interface of this route.  The IP address of the specified 
         interface shall be use as source IP when performs routing."
    ::= { ipCurCfgStaticRouteEntry 5}

ipNewCfgStaticRouteTable OBJECT-TYPE
    SYNTAX  SEQUENCE OF IpNewCfgStaticRouteEntry
    MAX-ACCESS  not-accessible
    STATUS  current
    DESCRIPTION
        "The table of static routes in the new configuration block."
    ::= { ipStaticRouteCfg 3 }

ipStaticRouteClearAllByDestIp OBJECT-TYPE
    SYNTAX  IpAddress
    MAX-ACCESS  read-write
    STATUS  current
    DESCRIPTION
        "Clears all static routes with the specified destination IP address."
    ::= { ipStaticRouteCfg 4}

ipStaticRouteClearAllByGatewayIp OBJECT-TYPE
    SYNTAX  IpAddress
    MAX-ACCESS  read-write
    STATUS  current
    DESCRIPTION
        "Clears all static routes with the specified gateway IP address."
    ::= { ipStaticRouteCfg 5}

ipStaticRouteClearAllByInterface OBJECT-TYPE
    SYNTAX  INTEGER
    MAX-ACCESS  read-write
    STATUS  current
    DESCRIPTION
        "Clears all routes on the specified inteface number."
    ::= { ipStaticRouteCfg 6}

ipStaticRouteClearAll OBJECT-TYPE
    SYNTAX INTEGER { 
    ok(1),
    clear(2)
    }
    MAX-ACCESS  read-write
    STATUS  current
    DESCRIPTION
        "When set to clear(2),clears all static routes. Otherwhise nothing is done."
    ::= { ipStaticRouteCfg 7}
ipStaticRouteCurPingInterval OBJECT-TYPE
    SYNTAX INTEGER
    MAX-ACCESS read-only
    STATUS current
    DESCRIPTION
        "The time between ping retries."
    ::= { ipStaticRouteCfg 8}
ipStaticRouteNewPingInterval OBJECT-TYPE
    SYNTAX INTEGER
    MAX-ACCESS read-write
    STATUS current
    DESCRIPTION
        "The time between ping retries."
    ::= { ipStaticRouteCfg 9}
ipStaticRouteCurPingRetries OBJECT-TYPE
    SYNTAX INTEGER
    MAX-ACCESS read-only
    STATUS current
    DESCRIPTION
        "The number of ping retries."
    ::= { ipStaticRouteCfg 10}
ipStaticRouteNewPingRetries OBJECT-TYPE
    SYNTAX INTEGER
    MAX-ACCESS read-write
    STATUS current
    DESCRIPTION
        "The number of ping retries."
    ::= { ipStaticRouteCfg 11}
ipStaticRouteCurEcmpHash OBJECT-TYPE
    SYNTAX  INTEGER {
        dipsip(0),      
        sip(1) 
    }
    MAX-ACCESS read-only
    STATUS current
    DESCRIPTION
        "Ecmp Hash based on dipsip/sip."
    ::= { ipStaticRouteCfg 12}
ipStaticRouteNewEcmpHash OBJECT-TYPE
    SYNTAX  INTEGER {
        dipsip(0),      
        sip(1) 
    }
    MAX-ACCESS read-write
    STATUS current
    DESCRIPTION
        "Ecmp Hash based on dipsip/sip."
    ::= { ipStaticRouteCfg 13}



ipStaticRouteCurHealthcheck OBJECT-TYPE
    SYNTAX  INTEGER {
        disable(0),
        enable(1)
    }
    MAX-ACCESS read-only
    STATUS current
    DESCRIPTION
        "Gateway healthcheck functionality"
    ::= { ipStaticRouteCfg 16}

ipStaticRouteNewHealthcheck OBJECT-TYPE
    SYNTAX  INTEGER {
        disable(0),
        enable(1)
    }
    MAX-ACCESS read-write
    STATUS current
    DESCRIPTION
        "Gateway healthcheck functionality"
    ::= { ipStaticRouteCfg 17}


ipNewCfgStaticRouteEntry OBJECT-TYPE
    SYNTAX  IpNewCfgStaticRouteEntry
    MAX-ACCESS  not-accessible
    STATUS  current
    DESCRIPTION
        "A row in the static IP route table"
    INDEX   { ipNewCfgStaticRouteIndx }
    ::= { ipNewCfgStaticRouteTable 1 }

IpNewCfgStaticRouteEntry ::= SEQUENCE {
    ipNewCfgStaticRouteIndx         Integer32,
    ipNewCfgStaticRouteDestIp       IpAddress,
    ipNewCfgStaticRouteMask         IpAddress,
    ipNewCfgStaticRouteGateway      IpAddress,
    ipNewCfgStaticRouteAction       INTEGER,
    ipNewCfgStaticRouteInterface    Integer32
    }

ipNewCfgStaticRouteIndx OBJECT-TYPE
    SYNTAX  Integer32
    MAX-ACCESS  read-only
    STATUS  current
    DESCRIPTION
        "The index of the static routing table."
    ::= { ipNewCfgStaticRouteEntry 1}

ipNewCfgStaticRouteDestIp OBJECT-TYPE
    SYNTAX  IpAddress
    MAX-ACCESS  read-create
    STATUS  current
    DESCRIPTION
        "The destination IP address of this route."
    ::= { ipNewCfgStaticRouteEntry 2}

ipNewCfgStaticRouteMask OBJECT-TYPE 
    SYNTAX  IpAddress
    MAX-ACCESS  read-create 
    STATUS  current 
    DESCRIPTION 
        "The subnet mask of this route."
    ::= { ipNewCfgStaticRouteEntry 3}

ipNewCfgStaticRouteGateway OBJECT-TYPE 
    SYNTAX  IpAddress
    MAX-ACCESS  read-create 
    STATUS  current 
    DESCRIPTION 
        "The IP address of the gateway for this route."
    ::= { ipNewCfgStaticRouteEntry 4}

ipNewCfgStaticRouteAction OBJECT-TYPE
    SYNTAX  INTEGER {
        other(1),
        delete(2)
       }  
    MAX-ACCESS  read-create
    STATUS  current
    DESCRIPTION
        "When set to the value of 2 (delete), the entire row is deleted. 
         When read, other is returned. Setting the value to anything other 
         than 2(delete) has no effect on the state of the row."
    ::= { ipNewCfgStaticRouteEntry 5 }

ipNewCfgStaticRouteInterface OBJECT-TYPE 
    SYNTAX  Integer32
    MAX-ACCESS  read-create 
    STATUS  current 
    DESCRIPTION 
        "The IP interface of this route.  The IP address of the specified 
         interface shall be use as source IP when performs routing."
    ::= { ipNewCfgStaticRouteEntry 6 }



-- RIP version 2 Configuration 

ripCurCfgIntfTable OBJECT-TYPE
    SYNTAX SEQUENCE OF RipCurCfgIntfEntry
    MAX-ACCESS not-accessible
    STATUS current
    DESCRIPTION
      "The table of RIP on IP interface in the current configuration block."
    ::= { rip2Cfg 1 }

ripCurCfgIntfEntry OBJECT-TYPE
    SYNTAX RipCurCfgIntfEntry
    MAX-ACCESS not-accessible
    STATUS current
    DESCRIPTION
      "Information about  RIP on IP interface."
    INDEX { ripCurCfgIntfIndex }
    ::= { ripCurCfgIntfTable 1 }
 
RipCurCfgIntfEntry ::= SEQUENCE {
    ripCurCfgIntfIndex      Integer32,
    ripCurCfgIntfVersion    INTEGER,
    ripCurCfgIntfSupply     INTEGER,
    ripCurCfgIntfListen     INTEGER,
    ripCurCfgIntfTrigUpdate INTEGER,
    ripCurCfgIntfMcastUpdate    INTEGER,
    ripCurCfgIntfPoisonReverse  INTEGER,
    ripCurCfgIntfState      INTEGER,
    ripCurCfgIntfMetric         INTEGER, 
    ripCurCfgIntfAuth           INTEGER, 
    ripCurCfgIntfKey            DisplayString,
    ripCurCfgIntfDefault    INTEGER,
    ripCurCfgIntfSplitHorizon   INTEGER
    }
 
ripCurCfgIntfIndex OBJECT-TYPE
    SYNTAX Integer32
    MAX-ACCESS read-only
    STATUS current
    DESCRIPTION
    "The interface number for which the RIP information is related."
    ::= { ripCurCfgIntfEntry 1}

ripCurCfgIntfVersion OBJECT-TYPE
    SYNTAX INTEGER {
        ripVersion1(1),
        ripVersion2(2),
        ripVersionBoth(3)
        }
    MAX-ACCESS read-only
    STATUS current
    DESCRIPTION
        "RIP version."
    ::= { ripCurCfgIntfEntry 2 }

ripCurCfgIntfState OBJECT-TYPE
    SYNTAX INTEGER {
        enabled(1),
        disabled(2)
        }
    MAX-ACCESS read-only
    STATUS current
    DESCRIPTION
        "Enable or disable RIP protocol."
    ::= { ripCurCfgIntfEntry 3 }


ripCurCfgIntfListen OBJECT-TYPE
    SYNTAX INTEGER {
        enabled(1),
        disabled(2)
        }
    MAX-ACCESS read-only
    STATUS current
    DESCRIPTION
        "Enable or disable listening to route updates."
    ::= { ripCurCfgIntfEntry 4 }
 

ripCurCfgIntfTrigUpdate OBJECT-TYPE
    SYNTAX INTEGER {
        enabled(1),
        disabled(2)
        }
    MAX-ACCESS read-only
    STATUS current
    DESCRIPTION
    "Enable or disable triggered updates."
    ::= { ripCurCfgIntfEntry 6 }

ripCurCfgIntfMcastUpdate OBJECT-TYPE
    SYNTAX INTEGER {
        enabled(1),
        disabled(2)
        }
    MAX-ACCESS read-only
    STATUS current
    DESCRIPTION
    "Enable or disable multicast updates."
    ::= { ripCurCfgIntfEntry 7 }

ripCurCfgIntfPoisonReverse OBJECT-TYPE
    SYNTAX  INTEGER {
        enabled(1),
        disabled(2)
        }
    MAX-ACCESS read-only
    STATUS current
    DESCRIPTION
    "RIP poison reverse."
    ::= { ripCurCfgIntfEntry 8 }

ripCurCfgIntfSupply OBJECT-TYPE
    SYNTAX INTEGER {
        enabled(1),
        disabled(2)
        }
    MAX-ACCESS read-only
    STATUS current
    DESCRIPTION
        "Enable or disable supplying route updates."
    ::= { ripCurCfgIntfEntry 9 }

ripCurCfgIntfMetric OBJECT-TYPE
    SYNTAX  INTEGER (1..15)
    MAX-ACCESS read-only
    STATUS current
    DESCRIPTION
        "RIP route metric for this interface."
    ::= { ripCurCfgIntfEntry 10 }

ripCurCfgIntfAuth OBJECT-TYPE
    SYNTAX INTEGER {
        none(1),
        password(2)
        }
    MAX-ACCESS read-only
    STATUS current
    DESCRIPTION
        "The type of Authentication used on this interface."
    ::= { ripCurCfgIntfEntry 11 }

ripCurCfgIntfKey OBJECT-TYPE
    SYNTAX  DisplayString (SIZE(0..16))
    MAX-ACCESS  read-only
    STATUS  current
    DESCRIPTION
        "RIP update authentication password."
    ::= { ripCurCfgIntfEntry 12 }

ripCurCfgIntfDefault OBJECT-TYPE
    SYNTAX  INTEGER {
        both(1),
        listen(2),
        supply(3),
        none(4)
        }
    MAX-ACCESS read-only
    STATUS current
    DESCRIPTION
    "Specifies what RIP does with default routes."
    ::= { ripCurCfgIntfEntry 13 }

ripCurCfgIntfSplitHorizon OBJECT-TYPE
    SYNTAX  INTEGER {
        enabled(2),
        disabled(3)
        }
    MAX-ACCESS  read-only
    STATUS  current
    DESCRIPTION
         "RIP split horizon."
    ::= {ripCurCfgIntfEntry 14 }

ripNewCfgIntfTable OBJECT-TYPE
    SYNTAX SEQUENCE OF RipNewCfgIntfEntry
    MAX-ACCESS not-accessible
    STATUS current
    DESCRIPTION
      "The table of RIP on IP interface in the new configuration block."
    ::= { rip2Cfg 2 }

ripNewCfgIntfEntry OBJECT-TYPE
    SYNTAX RipNewCfgIntfEntry
    MAX-ACCESS not-accessible
    STATUS current
    DESCRIPTION
      "Information about  RIP on IP interface."
    INDEX { ripNewCfgIntfIndex }
    ::= { ripNewCfgIntfTable 1 }
 
RipNewCfgIntfEntry ::= SEQUENCE {
    ripNewCfgIntfIndex      Integer32,
    ripNewCfgIntfVersion    INTEGER,
    ripNewCfgIntfSupply     INTEGER,
    ripNewCfgIntfListen     INTEGER,
    ripNewCfgIntfTrigUpdate INTEGER,
    ripNewCfgIntfMcastUpdate    INTEGER,
    ripNewCfgIntfPoisonReverse  INTEGER,
    ripNewCfgIntfState      INTEGER,
    ripNewCfgIntfMetric         INTEGER, 
    ripNewCfgIntfAuth           INTEGER, 
    ripNewCfgIntfKey            DisplayString,
    ripNewCfgIntfDefault    INTEGER,
    ripNewCfgIntfSplitHorizon   INTEGER
    }
 
ripNewCfgIntfIndex OBJECT-TYPE
    SYNTAX Integer32
    MAX-ACCESS read-only
    STATUS current
    DESCRIPTION
    "The interface number for which the RIP information is related."
    ::= { ripNewCfgIntfEntry 1}

ripNewCfgIntfVersion OBJECT-TYPE
    SYNTAX INTEGER {
        ripVersion1(1),
        ripVersion2(2),
        ripVersionBoth(3) 
        }
    MAX-ACCESS read-create
    STATUS current
    DESCRIPTION
        "RIP version."
    ::= { ripNewCfgIntfEntry 2 }

ripNewCfgIntfSupply OBJECT-TYPE
    SYNTAX INTEGER {
        enabled(1),
        disabled(2)
        }
    MAX-ACCESS read-create
    STATUS current
    DESCRIPTION
        "Enable or disable supplying route updates."
    ::= { ripNewCfgIntfEntry 3 }

ripNewCfgIntfListen OBJECT-TYPE
    SYNTAX INTEGER {
        enabled(1),
        disabled(2)
        }
    MAX-ACCESS read-create
    STATUS current
    DESCRIPTION
        "Enable or disable listening to route updates."
    ::= { ripNewCfgIntfEntry 4 }
 

ripNewCfgIntfTrigUpdate OBJECT-TYPE
    SYNTAX INTEGER {
        enabled(1),
        disabled(2)
        }
    MAX-ACCESS read-create
    STATUS current
    DESCRIPTION
    "Enable or disable triggered updates."
    ::= { ripNewCfgIntfEntry 6 }

ripNewCfgIntfMcastUpdate OBJECT-TYPE
    SYNTAX INTEGER {
        enabled(1),
        disabled(2)
        }
    MAX-ACCESS read-create
    STATUS current
    DESCRIPTION
    "Enable or disable multicast updates."
    ::= { ripNewCfgIntfEntry 7 }

ripNewCfgIntfPoisonReverse OBJECT-TYPE
    SYNTAX INTEGER {
        enabled(1),
        disabled(2)
        }
    MAX-ACCESS read-create
    STATUS current
    DESCRIPTION
    "RIP poison reverse."
    ::= { ripNewCfgIntfEntry 8 }

ripNewCfgIntfState OBJECT-TYPE
    SYNTAX INTEGER {
        enabled(1),
        disabled(2)
        }
    MAX-ACCESS read-create
    STATUS current
    DESCRIPTION
        "Enable or disable RIP protocol."
    ::= { ripNewCfgIntfEntry 9 }

ripNewCfgIntfMetric OBJECT-TYPE
    SYNTAX  INTEGER (1..15)
    MAX-ACCESS read-write
    STATUS current
    DESCRIPTION
        "RIP route metric for this interface."
    ::= { ripNewCfgIntfEntry 10 }

ripNewCfgIntfAuth OBJECT-TYPE
    SYNTAX INTEGER {
        none(1),
        password(2)
        }
    MAX-ACCESS read-write
    STATUS current
    DESCRIPTION
        "The type of Authentication used on this interface."
    ::= { ripNewCfgIntfEntry 11 }

ripNewCfgIntfKey OBJECT-TYPE
    SYNTAX  DisplayString (SIZE(0..16))
    MAX-ACCESS  read-create
    STATUS  current
    DESCRIPTION
        "RIP update authentication password."
    ::= { ripNewCfgIntfEntry 12 }

ripNewCfgIntfDefault OBJECT-TYPE
    SYNTAX INTEGER {
        both(1),
        listen(2),
        supply(3),
        none(4)
        }
    MAX-ACCESS read-create
    STATUS current
    DESCRIPTION
    "Specifies what RIP does with default routes. The default routes 
         action could be set to listen/supply/both/none."
    ::= { ripNewCfgIntfEntry 13 }

ripNewCfgIntfSplitHorizon OBJECT-TYPE
    SYNTAX  INTEGER {
        enabled(2),
        disabled(3)
        }
    MAX-ACCESS  read-write
    STATUS  current
    DESCRIPTION
        "RIP split horizon."
    ::= { ripNewCfgIntfEntry 14 }

ripGeneral  OBJECT IDENTIFIER ::= { rip2Cfg 3 }

rip2CurCfgState OBJECT-TYPE
    SYNTAX INTEGER {
        on(1),
        off(2)
        }
    MAX-ACCESS read-only
    STATUS current
    DESCRIPTION
    "RIP global state."
    ::= { ripGeneral 1 }

rip2NewCfgState OBJECT-TYPE
    SYNTAX INTEGER {
        on(1),
        off(2)
        }
    MAX-ACCESS read-write
    STATUS current
    DESCRIPTION
    "Globally turn RIP on or off."
    ::= { ripGeneral 2 }

rip2CurCfgUpdatePeriod OBJECT-TYPE
      SYNTAX  INTEGER  (1..120)
      MAX-ACCESS  read-only
      STATUS  current
      DESCRIPTION
          "Update Period in seconds."
      ::= { ripGeneral 3 }

rip2NewCfgUpdatePeriod OBJECT-TYPE
      SYNTAX  INTEGER  (1..120)
      MAX-ACCESS  read-write
      STATUS  current
      DESCRIPTION
          "Update Period in seconds."
      ::= { ripGeneral 4 }

ripRouteRedistribution   OBJECT IDENTIFIER ::= { rip2Cfg 4 }

ripRedistributeStatic    OBJECT IDENTIFIER ::= { ripRouteRedistribution 1 }

ripCurCfgStaticMetric OBJECT-TYPE
    SYNTAX INTEGER (0..15)
    MAX-ACCESS read-only
    STATUS current
    DESCRIPTION
    "The metric to be assigned to static routes. 
         A value of 0 indicates none."
    ::= { ripRedistributeStatic 1 }

ripNewCfgStaticMetric OBJECT-TYPE
    SYNTAX INTEGER (0..15)
    MAX-ACCESS read-write
    STATUS current
    DESCRIPTION
    "The metric to be assigned to static routes. 
         A value of 0 indicates none."
    ::= { ripRedistributeStatic 2 }

ripCurCfgStaticOutRmapList OBJECT-TYPE
    SYNTAX OCTET STRING
    MAX-ACCESS read-only
    STATUS current
    DESCRIPTION
        "The route maps present in the out route map list. 
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected"
    ::= { ripRedistributeStatic 5 }

ripNewCfgStaticOutRmapList OBJECT-TYPE
    SYNTAX OCTET STRING
    MAX-ACCESS read-only
    STATUS current
    DESCRIPTION
        "The route maps present in the out route map list. 
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected"
    ::= { ripRedistributeStatic 6 }

ripNewCfgStaticAddOutRmap OBJECT-TYPE
    SYNTAX Integer32 
    MAX-ACCESS read-write
    STATUS current  
    DESCRIPTION
    "The route map to be add into out-rmap list. When read, 0 is returned."
    ::= { ripRedistributeStatic 7 }

ripNewCfgStaticRemoveOutRmap OBJECT-TYPE
    SYNTAX Integer32 
    MAX-ACCESS read-write
    STATUS current  
    DESCRIPTION
    "The route map to be removed from out-rmap list. When read, 
         0 is returned."
    ::= { ripRedistributeStatic 8 }

ripRedistributeEbgp    OBJECT IDENTIFIER ::= { ripRouteRedistribution 2 }

ripCurCfgEbgpMetric OBJECT-TYPE
    SYNTAX INTEGER (0..15)
    MAX-ACCESS read-only
    STATUS current
    DESCRIPTION
    "The export metric to be assigned to External BGP routes.
         A value of 0 indicates none."
    ::= { ripRedistributeEbgp 1 }

ripNewCfgEbgpMetric OBJECT-TYPE
    SYNTAX INTEGER (0..15)
    MAX-ACCESS read-write
    STATUS current
    DESCRIPTION
    "The export metric to be assigned to External BGP routes.
         A value of 0 indicates none."
    ::= { ripRedistributeEbgp 2 }

ripCurCfgEbgpOutRmapList OBJECT-TYPE
    SYNTAX OCTET STRING
    MAX-ACCESS read-only
    STATUS current
    DESCRIPTION
        "The route maps present in the out route map list. 
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected"
    ::= { ripRedistributeEbgp 5 }

ripNewCfgEbgpOutRmapList OBJECT-TYPE
    SYNTAX OCTET STRING
    MAX-ACCESS read-only
    STATUS current
    DESCRIPTION
        "The route maps present in the out route map list. 
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected"
    ::= { ripRedistributeEbgp 6 }

ripNewCfgEbgpAddOutRmap OBJECT-TYPE
    SYNTAX Integer32 
    MAX-ACCESS read-write
    STATUS current  
    DESCRIPTION
    "The route map to be add into out-rmap list. When read, 0 is returned."
    ::= { ripRedistributeEbgp 7 }

ripNewCfgEbgpRemoveOutRmap OBJECT-TYPE
    SYNTAX Integer32 
    MAX-ACCESS read-write
    STATUS current  
    DESCRIPTION
    "The route map to be removed from out-rmap list. When read, 
         0 is returned."
    ::= { ripRedistributeEbgp 8 }

ripRedistributeIbgp    OBJECT IDENTIFIER ::= { ripRouteRedistribution 3 }

ripCurCfgIbgpMetric OBJECT-TYPE
    SYNTAX INTEGER (0..15)
    MAX-ACCESS read-only
    STATUS current
    DESCRIPTION
    "The export metric for Internal BGP routes.
         A value of 0 indicates none."
    ::= { ripRedistributeIbgp 1 }

ripNewCfgIbgpMetric OBJECT-TYPE
    SYNTAX INTEGER (0..15)
    MAX-ACCESS read-write
    STATUS current
    DESCRIPTION
    "The export metric for Internal BGP routes.
         A value of 0 indicates none."
    ::= { ripRedistributeIbgp 2 }

ripCurCfgIbgpOutRmapList OBJECT-TYPE
    SYNTAX OCTET STRING
    MAX-ACCESS read-only
    STATUS current
    DESCRIPTION
        "The route maps present in the out route map list. 
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected"
    ::= { ripRedistributeIbgp 5 }

ripNewCfgIbgpOutRmapList OBJECT-TYPE
    SYNTAX OCTET STRING
    MAX-ACCESS read-only
    STATUS current
    DESCRIPTION
        "The route maps present in the out route map list. 
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected"
    ::= { ripRedistributeIbgp 6 }

ripNewCfgIbgpAddOutRmap OBJECT-TYPE
    SYNTAX Integer32 
    MAX-ACCESS read-write
    STATUS current  
    DESCRIPTION
    "The route map to be add into out-rmap list. When read, 0 is returned."
    ::= { ripRedistributeIbgp 7 }

ripNewCfgIbgpRemoveOutRmap OBJECT-TYPE
    SYNTAX Integer32 
    MAX-ACCESS read-write
    STATUS current  
    DESCRIPTION
    "The route map to be removed from out-rmap list. When read, 
         0 is returned."
    ::= { ripRedistributeIbgp 8 }

ripRedistributeFixed    OBJECT IDENTIFIER ::= { ripRouteRedistribution 4 }

ripCurCfgFixedMetric OBJECT-TYPE
    SYNTAX INTEGER (0..15)
    MAX-ACCESS read-only
    STATUS current
    DESCRIPTION
    "The export metric for fixed routes. A value of 0 indicates none"
    ::= { ripRedistributeFixed 1 }

ripNewCfgFixedMetric OBJECT-TYPE
    SYNTAX INTEGER (0..15)
    MAX-ACCESS read-write
    STATUS current
    DESCRIPTION
    "The export metric for fixed routes. A value of 0 indicates none"
    ::= { ripRedistributeFixed 2 }

ripCurCfgFixedOutRmapList OBJECT-TYPE
    SYNTAX OCTET STRING
    MAX-ACCESS read-only
    STATUS current
    DESCRIPTION
        "The route maps present in the out route map list. 
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected"
    ::= { ripRedistributeFixed 5 }

ripNewCfgFixedOutRmapList OBJECT-TYPE
    SYNTAX OCTET STRING
    MAX-ACCESS read-only
    STATUS current
    DESCRIPTION
        "The route maps present in the out route map list. 
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected"
    ::= { ripRedistributeFixed 6 }

ripNewCfgFixedAddOutRmap OBJECT-TYPE
    SYNTAX Integer32 
    MAX-ACCESS read-write
    STATUS current  
    DESCRIPTION
    "The route map to be add into out-rmap list. When read, 0 is returned."
    ::= { ripRedistributeFixed 7 }

ripNewCfgFixedRemoveOutRmap OBJECT-TYPE
    SYNTAX Integer32 
    MAX-ACCESS read-write
    STATUS current  
    DESCRIPTION
    "The route map to be removed from out-rmap list. When read, 
         0 is returned."
    ::= { ripRedistributeFixed 8 }

ripRedistributeOspf    OBJECT IDENTIFIER ::= { ripRouteRedistribution 5 }

ripCurCfgOspfMetric OBJECT-TYPE
    SYNTAX INTEGER (0..15)
    MAX-ACCESS read-only
    STATUS current
    DESCRIPTION
    "The export metric for RIP routes. A value of 0 indicates none"
    ::= { ripRedistributeOspf 1 }

ripNewCfgOspfMetric OBJECT-TYPE
    SYNTAX INTEGER (0..15)
    MAX-ACCESS read-write
    STATUS current
    DESCRIPTION
    "The export metric for RIP routes. A value of 0 indicates none"
    ::= { ripRedistributeOspf 2 }

ripCurCfgOspfOutRmapList OBJECT-TYPE
    SYNTAX OCTET STRING
    MAX-ACCESS read-only
    STATUS current
    DESCRIPTION
        "The route maps present in the out route map list. 
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected"
    ::= { ripRedistributeOspf 5 }

ripNewCfgOspfOutRmapList OBJECT-TYPE
    SYNTAX OCTET STRING
    MAX-ACCESS read-only
    STATUS current
    DESCRIPTION
        "The route maps present in the out route map list. 
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected"
    ::= { ripRedistributeOspf 6 }

ripNewCfgOspfAddOutRmap OBJECT-TYPE
    SYNTAX Integer32 
    MAX-ACCESS read-write
    STATUS current  
    DESCRIPTION
    "The route map to be add into out-rmap list. When read, 0 is returned."
    ::= { ripRedistributeOspf 7 }

ripNewCfgOspfRemoveOutRmap OBJECT-TYPE
    SYNTAX Integer32 
    MAX-ACCESS read-write
    STATUS current  
    DESCRIPTION
    "The route map to be removed from out-rmap list. When read, 
         0 is returned."
    ::= { ripRedistributeOspf 8 }

ripRedistributeEospf    OBJECT IDENTIFIER ::= { ripRouteRedistribution 6 }

ripCurCfgEospfMetric OBJECT-TYPE
    SYNTAX INTEGER (0..15)
    MAX-ACCESS read-only
    STATUS current
    DESCRIPTION
    "The export metric for RIP routes. A value of 0 indicates none"
    ::= { ripRedistributeEospf 1 }

ripNewCfgEospfMetric OBJECT-TYPE
    SYNTAX INTEGER (0..15)
    MAX-ACCESS read-write
    STATUS current
    DESCRIPTION
    "The export metric for RIP routes. A value of 0 indicates none"
    ::= { ripRedistributeEospf 2 }

ripCurCfgEospfOutRmapList OBJECT-TYPE
    SYNTAX OCTET STRING
    MAX-ACCESS read-only
    STATUS current
    DESCRIPTION
        "The route maps present in the out route map list. 
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected"
    ::= { ripRedistributeEospf 5 }

ripNewCfgEospfOutRmapList OBJECT-TYPE
    SYNTAX OCTET STRING
    MAX-ACCESS read-only
    STATUS current
    DESCRIPTION
        "The route maps present in the out route map list. 
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected"
    ::= { ripRedistributeEospf 6 }

ripNewCfgEospfAddOutRmap OBJECT-TYPE
    SYNTAX Integer32 
    MAX-ACCESS read-write
    STATUS current  
    DESCRIPTION
    "The route map to be add into out-rmap list. When read, 0 is returned."
    ::= { ripRedistributeEospf 7 }

ripNewCfgEospfRemoveOutRmap OBJECT-TYPE
    SYNTAX Integer32 
    MAX-ACCESS read-write
    STATUS current  
    DESCRIPTION
    "The route map to be removed from out-rmap list. When read, 
         0 is returned."
    ::= { ripRedistributeEospf 8 }


-- IP Forwarding Configuration 

ipFwdGeneralCfg   OBJECT IDENTIFIER ::=  {ipForwardCfg 1 }

ipFwdCurCfgState OBJECT-TYPE
    SYNTAX  INTEGER {
        on(2),
        off(3)
    }
    MAX-ACCESS  read-only
    STATUS  current
    DESCRIPTION
        "IP forwarding global state."
    ::= { ipFwdGeneralCfg 1 }

ipFwdNewCfgState OBJECT-TYPE
    SYNTAX  INTEGER { 
        on(2),
        off(3) 
    }
    MAX-ACCESS  read-write
    STATUS  current  
    DESCRIPTION 
        "IP forwarding global state." 
    ::= { ipFwdGeneralCfg 2 }

ipFwdCurCfgDirectedBcast OBJECT-TYPE
    SYNTAX INTEGER {
        enabled(2),
        disabled(3)
    }
    MAX-ACCESS read-only
    STATUS current
    DESCRIPTION
        "Enable or disable forwarding directed broadcasts."
    ::= { ipFwdGeneralCfg 3 }

ipFwdNewCfgDirectedBcast OBJECT-TYPE
    SYNTAX INTEGER {
        enabled(2),
        disabled(3)
    }
    MAX-ACCESS read-write
    STATUS current
    DESCRIPTION
        "Enable or disable forwarding directed broadcasts."
    ::= { ipFwdGeneralCfg 4 }

ipFwdCurCfgNoICMPRedirect OBJECT-TYPE
    SYNTAX INTEGER {
        enabled(2),
        disabled(3)
        }
    MAX-ACCESS read-only
    STATUS current
    DESCRIPTION
        "Enable or disable no icmp redirects."
    ::= { ipFwdGeneralCfg 5 }

ipFwdNewCfgNoICMPRedirect OBJECT-TYPE
    SYNTAX INTEGER {
        enabled(2),
        disabled(3)
        }
    MAX-ACCESS read-write
    STATUS current
    DESCRIPTION
        "Enable or disable no icmp redirects."
    ::= { ipFwdGeneralCfg 6 }

ipFwdCurCfgICMP6Redirect OBJECT-TYPE
    SYNTAX INTEGER {
        enabled(2),
        disabled(3)
        }
    MAX-ACCESS read-only
    STATUS current
    DESCRIPTION
        "Enable or disable ICMPv6 redirects."
    ::= { ipFwdGeneralCfg 7 }

ipFwdNewCfgICMP6Redirect OBJECT-TYPE
    SYNTAX INTEGER {
        enabled(2),
        disabled(3)
        }
    MAX-ACCESS read-write
    STATUS current
    DESCRIPTION
        "Enable or disable ICMPv6 redirects."
    ::= { ipFwdGeneralCfg 8 }



--
-- ARP configuration
--
arpCurCfgReARPPeriod OBJECT-TYPE
    SYNTAX INTEGER (2..120)
    MAX-ACCESS read-only
    STATUS current
    DESCRIPTION
        "Re-ARP Period in seconds."
    ::= { arpCfg 1 }

arpNewCfgReARPPeriod OBJECT-TYPE 
    SYNTAX  INTEGER (2..120)
    MAX-ACCESS  read-write
    STATUS  current 
    DESCRIPTION 
        "Re-ARP Period in seconds." 
    ::= { arpCfg 2 }

--
-- IP Bootp Configration
--

ipCurCfgBootpAddr OBJECT-TYPE
    SYNTAX  IpAddress
    MAX-ACCESS  read-only
    STATUS  current
    DESCRIPTION
        "The IP address of BOOTP server."
    ::= { ipBootpCfg 1 }

ipNewCfgBootpAddr OBJECT-TYPE
    SYNTAX  IpAddress
    MAX-ACCESS  read-write
    STATUS  current
    DESCRIPTION
        "The IP address of BOOTP server."
    ::= { ipBootpCfg 2 }

ipCurCfgBootpAddr2 OBJECT-TYPE
    SYNTAX  IpAddress
    MAX-ACCESS  read-only
    STATUS  current
    DESCRIPTION
        "The IP address of second BOOTP server."
    ::= { ipBootpCfg 3 }

ipNewCfgBootpAddr2 OBJECT-TYPE
    SYNTAX  IpAddress
    MAX-ACCESS  read-write
    STATUS  current
    DESCRIPTION
        "The IP address of second BOOTP server."
    ::= { ipBootpCfg 4 }

ipCurCfgBootpState OBJECT-TYPE
    SYNTAX  INTEGER {
        enabled(2),
        disabled(3)
        }
    MAX-ACCESS  read-only
    STATUS  current
    DESCRIPTION
        "The state of BOOTP relay."
    ::= { ipBootpCfg 5 }

ipNewCfgBootpState OBJECT-TYPE
    SYNTAX  INTEGER {
        enabled(2),
        disabled(3)
        }
    MAX-ACCESS  read-write  
    STATUS  current
    DESCRIPTION
        "The state of BOOTP relay."
    ::= { ipBootpCfg 6 }


ipCurCfgBootpGlobalServerTable OBJECT-TYPE
    SYNTAX  SEQUENCE OF IpCurCfgBootpGlobalServerEntry
    MAX-ACCESS  not-accessible
    STATUS  current
    DESCRIPTION
        "The table of global BOOTP server addresses"
    ::= { ipBootpCfg 20 }

ipCurCfgBootpGlobalServerEntry OBJECT-TYPE
    SYNTAX  IpCurCfgBootpGlobalServerEntry
    MAX-ACCESS  not-accessible
    STATUS  current
    DESCRIPTION
        "A row in the ipCurCfgBootpGlobalServerAddrTable"
    INDEX   { ipCurCfgBootpGlobalServerIndex }
    ::= { ipCurCfgBootpGlobalServerTable 1 }

IpCurCfgBootpGlobalServerEntry ::= SEQUENCE {
    ipCurCfgBootpGlobalServerIndex Integer32,
    ipCurCfgBootpGlobalServerAddress    IpAddress
    }

ipCurCfgBootpGlobalServerIndex OBJECT-TYPE
    SYNTAX  Integer32 
    MAX-ACCESS  read-only
    STATUS  current
    DESCRIPTION
        "The index of ipCurCfgBootpGlobalServerTable"
    ::= { ipCurCfgBootpGlobalServerEntry  1 }

ipCurCfgBootpGlobalServerAddress OBJECT-TYPE
    SYNTAX  IpAddress
    MAX-ACCESS  read-only
    STATUS  current
    DESCRIPTION
        "The current global server IP."
    ::= { ipCurCfgBootpGlobalServerEntry 2 }

ipNewCfgBootpGlobalServerTable OBJECT-TYPE
    SYNTAX  SEQUENCE OF IpNewCfgBootpGlobalServerEntry
    MAX-ACCESS  not-accessible
    STATUS  current
    DESCRIPTION
        "The table of global BOOTP server addresses"
    ::= { ipBootpCfg 21 }

ipNewCfgBootpGlobalServerEntry OBJECT-TYPE
    SYNTAX  IpNewCfgBootpGlobalServerEntry
    MAX-ACCESS  not-accessible
    STATUS  current
    DESCRIPTION
        "A row in the ipNewCfgBootpGlobalServerAddrTable"
    INDEX   { ipNewCfgBootpGlobalServerIndex }
    ::= { ipNewCfgBootpGlobalServerTable 1 }

IpNewCfgBootpGlobalServerEntry ::= SEQUENCE {
    ipNewCfgBootpGlobalServerIndex Integer32,
    ipNewCfgBootpGlobalServerAddress    IpAddress
    }

ipNewCfgBootpGlobalServerIndex OBJECT-TYPE
    SYNTAX  Integer32 
    MAX-ACCESS  read-only
    STATUS  current
    DESCRIPTION
        "The index of ipCurCfgBootpGlobalServerTable"
    ::= { ipNewCfgBootpGlobalServerEntry  1 }

ipNewCfgBootpGlobalServerAddress OBJECT-TYPE
    SYNTAX  IpAddress
    MAX-ACCESS  read-write
    STATUS  current
    DESCRIPTION
        "The current global server IP."
    ::= { ipNewCfgBootpGlobalServerEntry 2 }

ipCurCfgBootpBcastDomainTable OBJECT-TYPE
     SYNTAX  SEQUENCE OF IpCurCfgBootpBcastDomainEntry
     MAX-ACCESS  not-accessible
     STATUS  current
     DESCRIPTION
        "The table of broadcast domain settings"
     ::= { ipBootpCfg 22 }

ipCurCfgBootpBcastDomainEntry OBJECT-TYPE
    SYNTAX  IpCurCfgBootpBcastDomainEntry
    MAX-ACCESS  not-accessible
    STATUS  current
    DESCRIPTION
        "A row in the broadcast domain table"
    INDEX   { ipCurCfgBootpBcastDomainIndex }
    ::= { ipCurCfgBootpBcastDomainTable 1 }

IpCurCfgBootpBcastDomainEntry ::= SEQUENCE {
    ipCurCfgBootpBcastDomainIndex Integer32,
    ipCurCfgBootpBcastDomainVlan        Integer32,
    ipCurCfgBootpBcastDomainEnable      INTEGER 
    }

ipCurCfgBootpBcastDomainIndex OBJECT-TYPE
    SYNTAX  Integer32
    MAX-ACCESS  read-only
    STATUS  current
    DESCRIPTION
        "The index of the broadcast domain entry"
    ::= { ipCurCfgBootpBcastDomainEntry 1 }

ipCurCfgBootpBcastDomainVlan OBJECT-TYPE
    SYNTAX  Integer32
    MAX-ACCESS  read-only
    STATUS  current
    DESCRIPTION
        "The VLAN of the broadcast domain entry"
    ::= { ipCurCfgBootpBcastDomainEntry 2 }

ipCurCfgBootpBcastDomainEnable OBJECT-TYPE
    SYNTAX  INTEGER {
    enabled(2),
    disabled(3)
        }
    MAX-ACCESS  read-only
    STATUS  current
    DESCRIPTION
        "The state of the broadcast domain entry"
    ::= { ipCurCfgBootpBcastDomainEntry 3 }

ipNewCfgBootpBcastDomainTable OBJECT-TYPE
     SYNTAX  SEQUENCE OF IpNewCfgBootpBcastDomainEntry
     MAX-ACCESS  not-accessible
     STATUS  current
     DESCRIPTION
        "The table of broadcast domain settings"
     ::= { ipBootpCfg 23 }

ipNewCfgBootpBcastDomainEntry OBJECT-TYPE
    SYNTAX  IpNewCfgBootpBcastDomainEntry
    MAX-ACCESS  not-accessible
    STATUS  current
    DESCRIPTION
        "A row in the broadcast domain table"
    INDEX   { ipNewCfgBootpBcastDomainIndex }
    ::= { ipNewCfgBootpBcastDomainTable 1 }

IpNewCfgBootpBcastDomainEntry ::= SEQUENCE {
    ipNewCfgBootpBcastDomainIndex Integer32,
    ipNewCfgBootpBcastDomainVlan        Integer32,
    ipNewCfgBootpBcastDomainEnable      INTEGER, 
    ipNewCfgBootpBcastDomainAction      INTEGER
    }

ipNewCfgBootpBcastDomainIndex OBJECT-TYPE
    SYNTAX  Integer32
    MAX-ACCESS  read-only
    STATUS  current
    DESCRIPTION
        "The index of the broadcast domain entry"
    ::= { ipNewCfgBootpBcastDomainEntry 1 }

ipNewCfgBootpBcastDomainVlan OBJECT-TYPE
    SYNTAX  Integer32
    MAX-ACCESS  read-write
    STATUS  current
    DESCRIPTION
        "The VLAN of the broadcast domain entry"
    ::= { ipNewCfgBootpBcastDomainEntry 2 }

ipNewCfgBootpBcastDomainEnable OBJECT-TYPE
    SYNTAX  INTEGER {
    enabled(2),
    disabled(3)
        }
    MAX-ACCESS  read-write
    STATUS  current
    DESCRIPTION
        "The state of the broadcast domain entry"
    ::= { ipNewCfgBootpBcastDomainEntry 3 }

ipNewCfgBootpBcastDomainAction OBJECT-TYPE
    SYNTAX  INTEGER {
    other(1),
    delete(2)
        }
    MAX-ACCESS  read-create
    STATUS  current
    DESCRIPTION
        "When set to the value of 2 (delete), the broadcast domain is deleted. 
     When read, other is returned. Setting the value to anything other 
     than 2(delete) has no effect on the state of broadcast domain."
    ::= { ipNewCfgBootpBcastDomainEntry 4 }

ipCurCfgBootpBcastDomainServerTable OBJECT-TYPE
     SYNTAX  SEQUENCE OF IpCurCfgBootpBcastDomainServerEntry
     MAX-ACCESS  not-accessible
     STATUS  current
     DESCRIPTION
        "The table of broadcast domain servers"
     ::= { ipBootpCfg 24 }

ipCurCfgBootpBcastDomainServerEntry OBJECT-TYPE
    SYNTAX  IpCurCfgBootpBcastDomainServerEntry
    MAX-ACCESS  not-accessible
    STATUS  current
    DESCRIPTION
        "A row in the broadcast domain server table"
    INDEX   { ipCurCfgBootpBcastDomainBDIndex,
              ipCurCfgBootpBcastDomainServIndex  }
    ::= { ipCurCfgBootpBcastDomainServerTable 1 }

IpCurCfgBootpBcastDomainServerEntry ::= SEQUENCE {
    ipCurCfgBootpBcastDomainBDIndex    Integer32,
    ipCurCfgBootpBcastDomainServIndex        Integer32,
    ipCurCfgBootpBcastDomainServerIP      IpAddress 
    }

ipCurCfgBootpBcastDomainBDIndex OBJECT-TYPE
    SYNTAX  Integer32
    MAX-ACCESS  read-only
    STATUS  current
    DESCRIPTION
        "The index of the broadcast domain entry in the server table"
    ::= { ipCurCfgBootpBcastDomainServerEntry 1 }

ipCurCfgBootpBcastDomainServIndex OBJECT-TYPE
    SYNTAX  Integer32
    MAX-ACCESS  read-only
    STATUS  current
    DESCRIPTION
        "The index of the server in the server table"
    ::= { ipCurCfgBootpBcastDomainServerEntry 2 }

ipCurCfgBootpBcastDomainServerIP OBJECT-TYPE
    SYNTAX  IpAddress
    MAX-ACCESS  read-only
    STATUS  current
    DESCRIPTION
        "The current broadcast domain server IP."
    ::= { ipCurCfgBootpBcastDomainServerEntry 3 }

ipNewCfgBootpBcastDomainServerTable OBJECT-TYPE
     SYNTAX  SEQUENCE OF IpNewCfgBootpBcastDomainServerEntry
     MAX-ACCESS  not-accessible
     STATUS  current
     DESCRIPTION
        "The table of broadcast domain servers"
     ::= { ipBootpCfg 25 }

ipNewCfgBootpBcastDomainServerEntry OBJECT-TYPE
    SYNTAX  IpNewCfgBootpBcastDomainServerEntry
    MAX-ACCESS  not-accessible
    STATUS  current
    DESCRIPTION
        "A row in the broadcast domain server table"
    INDEX   { ipNewCfgBootpBcastDomainBDIndex,
              ipNewCfgBootpBcastDomainServIndex  }
    ::= { ipNewCfgBootpBcastDomainServerTable 1 }

IpNewCfgBootpBcastDomainServerEntry ::= SEQUENCE {
    ipNewCfgBootpBcastDomainBDIndex    Integer32,
    ipNewCfgBootpBcastDomainServIndex        Integer32,
    ipNewCfgBootpBcastDomainServerIP      IpAddress 
    }

ipNewCfgBootpBcastDomainBDIndex OBJECT-TYPE
    SYNTAX  Integer32
    MAX-ACCESS  read-only
    STATUS  current
    DESCRIPTION
        "The index of the broadcast domain entry in the server table"
    ::= { ipNewCfgBootpBcastDomainServerEntry 1 }

ipNewCfgBootpBcastDomainServIndex OBJECT-TYPE
    SYNTAX  Integer32
    MAX-ACCESS  read-only
    STATUS  current
    DESCRIPTION
        "The index of the server in the server table"
    ::= { ipNewCfgBootpBcastDomainServerEntry 2 }

ipNewCfgBootpBcastDomainServerIP OBJECT-TYPE
    SYNTAX  IpAddress
    MAX-ACCESS  read-write
    STATUS  current
    DESCRIPTION
        "The current broadcast domain server IP."
    ::= { ipNewCfgBootpBcastDomainServerEntry 3 }


ipCurCfgBootpOpt82State OBJECT-TYPE
     SYNTAX  INTEGER {
        enabled(2),
        disabled(3)
     }
     MAX-ACCESS  read-only
     STATUS  current
     DESCRIPTION
        "The state of Bootp relay option 82"
     ::= { ipBootpCfg 26 }
     
ipNewCfgBootpOpt82State OBJECT-TYPE
     SYNTAX  INTEGER {
        enabled(2),
        disabled(3)
     }
     MAX-ACCESS  read-write
     STATUS  current
     DESCRIPTION
        "Set the stare of Bootp relay option 82"
     ::= { ipBootpCfg 27 }
     
ipCurCfgBootpOpt82Policy OBJECT-TYPE
    SYNTAX  INTEGER {
        replace(0),
        drop(1),
        keep(2)
     }
     MAX-ACCESS  read-only
     STATUS  current
     DESCRIPTION
        "The policy of Bootp relay option 82"
     ::= { ipBootpCfg 28 }

ipNewCfgBootpOpt82Policy OBJECT-TYPE
    SYNTAX  INTEGER {
        replace(0),
        drop(1),
        keep(2)
     }
     MAX-ACCESS  read-write
     STATUS  current
     DESCRIPTION
        "Set the policy of Bootp relay option 82"
     ::= { ipBootpCfg 29 }
    

-- VRRP (Virtual Router Redundantcy Protocol) Group

vrrpGeneral       OBJECT IDENTIFIER ::= { vrrpCfg 1 }

vrrpCurCfgGenState OBJECT-TYPE
    SYNTAX  INTEGER {
        enabled(1),
        disabled(2)
        }
    MAX-ACCESS  read-only
    STATUS  current
    DESCRIPTION
        "Enable or disable VRRP operation globally."
    ::= { vrrpGeneral 1 }

vrrpNewCfgGenState OBJECT-TYPE
    SYNTAX  INTEGER {
        enabled(1),
        disabled(2)
        }
    MAX-ACCESS  read-write
    STATUS  current
    DESCRIPTION
        "Enable or disable VRRP operation globally."
    ::= { vrrpGeneral 2 }

vrrpCurCfgGenTckVirtRtrInc OBJECT-TYPE
    SYNTAX  INTEGER (0..254)
    MAX-ACCESS  read-only
    STATUS  current
    DESCRIPTION
        "The increment of VRRP virtual router priority. The priority is 
         adjusted by tracking the state of other virtual routers."
    ::= { vrrpGeneral 3 }

vrrpNewCfgGenTckVirtRtrInc OBJECT-TYPE
    SYNTAX  INTEGER (0..254)
    MAX-ACCESS  read-write
    STATUS  current
    DESCRIPTION
        "The increment of VRRP virtual router priority. The priority is 
         adjusted by tracking the state of other virtual routers."
    ::= { vrrpGeneral 4 }

vrrpCurCfgGenTckIpIntfInc OBJECT-TYPE
    SYNTAX  INTEGER (0..254)
    MAX-ACCESS  read-only
    STATUS  current
    DESCRIPTION
        "The increment of VRRP virtual router priority. The priority is 
         adjusted by tracking the state of other router interfaces."
    ::= { vrrpGeneral 5 }

vrrpNewCfgGenTckIpIntfInc OBJECT-TYPE
    SYNTAX  INTEGER (0..254)
    MAX-ACCESS  read-write
    STATUS  current
    DESCRIPTION
        "The increment of VRRP virtual router priority. The priority is 
         adjusted by tracking the state of other router interfaces."
    ::= { vrrpGeneral 6 }

vrrpCurCfgGenTckVlanPortInc OBJECT-TYPE
    SYNTAX  INTEGER (0..254)
    MAX-ACCESS  read-only
    STATUS  current
    DESCRIPTION
        "The increment of VRRP virtual router priority. The priority is 
         adjusted by tracking the port state of ports that belongs to the 
         same virtual LAN as the virtual router."
    ::= { vrrpGeneral 7 }

vrrpNewCfgGenTckVlanPortInc OBJECT-TYPE
    SYNTAX  INTEGER (0..254)
    MAX-ACCESS  read-write
    STATUS  current
    DESCRIPTION
        "The increment of VRRP virtual router priority. The priority is 
         adjusted by tracking the port state of ports that belongs to the 
         same virtual LAN as the virtual router."
    ::= { vrrpGeneral 8 }




vrrpCurCfgGenHoldoff OBJECT-TYPE
        SYNTAX  INTEGER (0..255)
        MAX-ACCESS  read-only
        STATUS  current
        DESCRIPTION
                "The time for VRRP virtual router to hold before it 
                 begins to change state to backup or master state."
        ::= { vrrpGeneral 19 }

vrrpNewCfgGenHoldoff OBJECT-TYPE
        SYNTAX  INTEGER (0..255)
        MAX-ACCESS  read-write
        STATUS  current
        DESCRIPTION
                "The time for VRRP virtual router to hold before it 
                 begins to change state to backup or master state."
        ::= { vrrpGeneral 20 }


vrrpVirtRtrTableMaxSize OBJECT-TYPE
    SYNTAX Integer32
    MAX-ACCESS read-only
    STATUS current
    DESCRIPTION
        "The maximum number of entries in VRRP virtual router table."
    ::= { vrrpCfg 2 }

vrrpCurCfgVirtRtrTable OBJECT-TYPE
    SYNTAX  SEQUENCE OF VrrpCurCfgVirtRtrTableEntry
    MAX-ACCESS  not-accessible
    STATUS  current
    DESCRIPTION
        "The table of VRRP virtual routers in the current configuration block."
    ::= { vrrpCfg 3 }
 
vrrpCurCfgVirtRtrTableEntry OBJECT-TYPE
    SYNTAX  VrrpCurCfgVirtRtrTableEntry
    MAX-ACCESS  not-accessible
    STATUS  current
    DESCRIPTION
        "Information about a VRRP virtual router."
    INDEX   { vrrpCurCfgVirtRtrIndx }
    ::= { vrrpCurCfgVirtRtrTable 1 }
 
VrrpCurCfgVirtRtrTableEntry ::= SEQUENCE {
    vrrpCurCfgVirtRtrIndx         Integer32,
    vrrpCurCfgVirtRtrID           INTEGER,
    vrrpCurCfgVirtRtrAddr         IpAddress,
    vrrpCurCfgVirtRtrIfIndex      Integer32,
    vrrpCurCfgVirtRtrInterval     INTEGER,
    vrrpCurCfgVirtRtrPreDelay     INTEGER,
    vrrpCurCfgVirtRtrPriority     INTEGER,
    vrrpCurCfgVirtRtrPreempt      INTEGER,
    vrrpCurCfgVirtRtrTckVirtRtr   INTEGER,
    vrrpCurCfgVirtRtrTckIpIntf    INTEGER,
    vrrpCurCfgVirtRtrTckVlanPort  INTEGER,
    vrrpCurCfgVirtRtrState        INTEGER
    , vrrpCurCfgVirtRtrFastAdvertisement INTEGER
    }

vrrpCurCfgVirtRtrIndx OBJECT-TYPE
    SYNTAX  Integer32
    MAX-ACCESS  read-only
    STATUS  current
    DESCRIPTION
        "The VRRP virtual router table index."
    ::= { vrrpCurCfgVirtRtrTableEntry 1 }

vrrpCurCfgVirtRtrID OBJECT-TYPE
    SYNTAX  INTEGER (1..255)
    MAX-ACCESS  read-only
    STATUS  current 
    DESCRIPTION
        "The VRRP virtual router identifier."
    ::= { vrrpCurCfgVirtRtrTableEntry 2 }

vrrpCurCfgVirtRtrAddr OBJECT-TYPE
    SYNTAX  IpAddress
    MAX-ACCESS  read-only
    STATUS  current
    DESCRIPTION
        "The VRRP virtual router IP address."
    ::= { vrrpCurCfgVirtRtrTableEntry 3 }

vrrpCurCfgVirtRtrIfIndex OBJECT-TYPE
    SYNTAX  Integer32
    MAX-ACCESS  read-only
    STATUS  current
    DESCRIPTION
        "The IfIndex that the VRRP virtual router is representing."
    ::= { vrrpCurCfgVirtRtrTableEntry 4 }

vrrpCurCfgVirtRtrInterval OBJECT-TYPE
    SYNTAX  INTEGER (1..255)
    MAX-ACCESS  read-only
    STATUS  current
    DESCRIPTION
        "The time interval between VRRP advertisements in seconds.
    When FAST_ADVERTISEMENT is enabled, this object indicates advertisement
    interval in centi-seconds"
    ::= { vrrpCurCfgVirtRtrTableEntry 5 }

vrrpCurCfgVirtRtrPriority OBJECT-TYPE
    SYNTAX  INTEGER (1..254)
    MAX-ACCESS  read-only
    STATUS  current
    DESCRIPTION
        "The priority value to be used by the specified VRRP virtual routers."
    ::= { vrrpCurCfgVirtRtrTableEntry 6 }

vrrpCurCfgVirtRtrPreempt OBJECT-TYPE
    SYNTAX  INTEGER {
        enabled(1),
        disabled(2)
        }
    MAX-ACCESS  read-only
    STATUS  current
    DESCRIPTION
        "This is for controlling whether a higher priority Backup
          VRRP virtual router preempts a low priority Master.

          enabled(1)  - allow preemption
          disabled(2) - prohibit preemption"
    ::= { vrrpCurCfgVirtRtrTableEntry 7 }


vrrpCurCfgVirtRtrTckVirtRtr OBJECT-TYPE
    SYNTAX  INTEGER {
        enabled(1),
        disabled(2)
        }
    MAX-ACCESS  read-only
    STATUS  current
    DESCRIPTION
        "Enable or disable tracking other virtual routers for priority 
         adjustment. The priority increment is defined 
         in vrrpCurCfgGenTckVirtRtrInc."
    ::= { vrrpCurCfgVirtRtrTableEntry 9 }

vrrpCurCfgVirtRtrTckIpIntf OBJECT-TYPE
    SYNTAX  INTEGER {
        enabled(1),
        disabled(2)
        }
    MAX-ACCESS  read-only
    STATUS  current
    DESCRIPTION
        "Enable or disable tracking other router interfaces for 
     priority adjustment. The priority increment is defined 
     in vrrpCurCfgGenTckIpIntfInc."
    ::= { vrrpCurCfgVirtRtrTableEntry 10 }



vrrpCurCfgVirtRtrTckVlanPort OBJECT-TYPE
    SYNTAX  INTEGER {
        enabled(1),
        disabled(2)
        }
    MAX-ACCESS  read-only
    STATUS  current
    DESCRIPTION
        "Enable or disable tracking port state of VLAN ports 
     for priority adjustment. The priority increment is 
     defined in vrrpCurCfgGenTckVlanPortInc."
    ::= { vrrpCurCfgVirtRtrTableEntry 15 }


vrrpCurCfgVirtRtrState OBJECT-TYPE
    SYNTAX  INTEGER {
        enabled(1),
        disabled(2)
        }
    MAX-ACCESS  read-only
    STATUS  current
    DESCRIPTION
        "Enable or disable the VRRP virtual router."
    ::= { vrrpCurCfgVirtRtrTableEntry 16 }

vrrpCurCfgVirtRtrFastAdvertisement OBJECT-TYPE
    SYNTAX  INTEGER {
        enabled(1),
        disabled(2)
        }
    MAX-ACCESS read-only 
    STATUS  current
    DESCRIPTION
        "This object provides the status of FAST_ADVERTISEMENT.
         When FAST_ADVERTISEMENT is enabled, 
           - New message type FAST_ADVERTISEMENT(2) will be used in the
         VRRP advertisements
           - Can interop only with another FAST_ADVERTISEMENT enabled router
           - VRRP advertisement interval will be sent in units of centi-seconds
           - Timers will be running with centi-second granularity"
    ::= { vrrpCurCfgVirtRtrTableEntry 17 }

vrrpCurCfgVirtRtrPreDelay OBJECT-TYPE
    SYNTAX  INTEGER (0..255)
    MAX-ACCESS  read-only
    STATUS  current
    DESCRIPTION
        "The pre-emptive delay interval in seconds."
    ::= { vrrpCurCfgVirtRtrTableEntry 18 }

vrrpNewCfgVirtRtrTable OBJECT-TYPE
    SYNTAX  SEQUENCE OF VrrpNewCfgVirtRtrTableEntry
    MAX-ACCESS  not-accessible
    STATUS  current
    DESCRIPTION
        "The table of VRRP virtual routers in the current configuration block."
    ::= { vrrpCfg 4 }

vrrpNewCfgVirtRtrTableEntry OBJECT-TYPE
    SYNTAX  VrrpNewCfgVirtRtrTableEntry
    MAX-ACCESS  not-accessible
    STATUS  current
    DESCRIPTION
        "Information about a VRRP virtual router."
    INDEX   { vrrpNewCfgVirtRtrIndx }
    ::= { vrrpNewCfgVirtRtrTable 1 }

VrrpNewCfgVirtRtrTableEntry ::= SEQUENCE {
    vrrpNewCfgVirtRtrIndx         Integer32,
    vrrpNewCfgVirtRtrID           INTEGER,
    vrrpNewCfgVirtRtrAddr         IpAddress,
    vrrpNewCfgVirtRtrIfIndex      Integer32,
    vrrpNewCfgVirtRtrInterval     INTEGER,
    vrrpNewCfgVirtRtrPreDelay     INTEGER,
    vrrpNewCfgVirtRtrPriority     INTEGER,
    vrrpNewCfgVirtRtrPreempt      INTEGER,
    vrrpNewCfgVirtRtrDelete       INTEGER,
    vrrpNewCfgVirtRtrTckVirtRtr   INTEGER,
    vrrpNewCfgVirtRtrTckIpIntf    INTEGER,
    vrrpNewCfgVirtRtrTckVlanPort  INTEGER,
    vrrpNewCfgVirtRtrState        INTEGER
    , vrrpNewCfgVirtRtrFastAdvertisement INTEGER
    }

vrrpNewCfgVirtRtrIndx OBJECT-TYPE
    SYNTAX  Integer32
    MAX-ACCESS  read-only
    STATUS  current
    DESCRIPTION
        "The VRRP virtual router table index."
    ::= { vrrpNewCfgVirtRtrTableEntry 1 }

vrrpNewCfgVirtRtrID OBJECT-TYPE
    SYNTAX  INTEGER (1..255)
    MAX-ACCESS  read-create
    STATUS  current 
    DESCRIPTION
        "The VRRP virtual router identifier."
    ::= { vrrpNewCfgVirtRtrTableEntry 2 }

vrrpNewCfgVirtRtrAddr OBJECT-TYPE
    SYNTAX  IpAddress
    MAX-ACCESS  read-create
    STATUS  current
    DESCRIPTION
        "The VRRP virtual router IP address."
    ::= { vrrpNewCfgVirtRtrTableEntry 3 }

vrrpNewCfgVirtRtrIfIndex OBJECT-TYPE
    SYNTAX  Integer32
    MAX-ACCESS  read-create
    STATUS  current
    DESCRIPTION
        "The IfIndex that the VRRP virtual router is representing."
   ::= { vrrpNewCfgVirtRtrTableEntry 4 }

vrrpNewCfgVirtRtrInterval OBJECT-TYPE
    SYNTAX  INTEGER (1..255)
    MAX-ACCESS  read-create
    STATUS  current
    DESCRIPTION
        "The time interval between VRRP advertisements in seconds.
    When FAST_ADVERTISEMENT is enabled, this object indicates advertisement
    interval in centi-seconds"
    ::= { vrrpNewCfgVirtRtrTableEntry 5 }

vrrpNewCfgVirtRtrPriority OBJECT-TYPE
    SYNTAX  INTEGER (1..254)
    MAX-ACCESS  read-create
    STATUS  current
    DESCRIPTION
        "The priority value to be used by the specified VRRP virtual router."
    ::= { vrrpNewCfgVirtRtrTableEntry 6 }

vrrpNewCfgVirtRtrPreempt OBJECT-TYPE
    SYNTAX  INTEGER {
        enabled(1),
        disabled(2)
        }
    MAX-ACCESS  read-create
    STATUS  current
    DESCRIPTION
        "This is for controlling whether a higher priority Backup
         VRRP virtual router preempts a low priority Master.

         enabled(1)  - allow preemption
         disabled(2) - prohibit preemption"
    ::= { vrrpNewCfgVirtRtrTableEntry 7 }


vrrpNewCfgVirtRtrDelete OBJECT-TYPE
    SYNTAX  INTEGER { 
    other(1),
        delete(2)
    }
    MAX-ACCESS  read-create
    STATUS  current
    DESCRIPTION
        "When set to the value of 2 (delete), the entire row is deleted. 
         When read, other(1) is returned. Setting the value to anything 
         other than delete(2) has no effect on the state of the row."
    ::= { vrrpNewCfgVirtRtrTableEntry 8 }


vrrpNewCfgVirtRtrTckVirtRtr OBJECT-TYPE
    SYNTAX  INTEGER {
        enabled(1),
        disabled(2)
        }
    MAX-ACCESS  read-create
    STATUS  current
    DESCRIPTION
        "Enable or disable tracking other virtual routers for 
     priority adjustment.  the priority increment is defined 
     in vrrpNewCfgGenTckVirtRtrInc."
    ::= { vrrpNewCfgVirtRtrTableEntry 10 }

vrrpNewCfgVirtRtrTckIpIntf OBJECT-TYPE
    SYNTAX  INTEGER {
        enabled(1),
        disabled(2)
        }
     MAX-ACCESS  read-create
     STATUS  current
     DESCRIPTION
         "Enable or disable tracking other router interfaces for 
      priority adjustment.  the priority increment is defined 
      in vrrpNewCfgGenTckIpIntfInc."
    ::= { vrrpNewCfgVirtRtrTableEntry 11 }

vrrpNewCfgVirtRtrTckVlanPort OBJECT-TYPE
    SYNTAX  INTEGER {
        enabled(1),
        disabled(2)
        }
    MAX-ACCESS  read-create
    STATUS  current
    DESCRIPTION
        "Enable or disable tracking port state of VLAN ports 
     for priority adjustment.  the priority increment is 
     defined in vrrpNewCfgGenTckVlanPortInc."
    ::= { vrrpNewCfgVirtRtrTableEntry 12 }


vrrpNewCfgVirtRtrState OBJECT-TYPE
    SYNTAX  INTEGER {
        enabled(1),
        disabled(2)
        }
    MAX-ACCESS  read-create
    STATUS  current
    DESCRIPTION
        "Enable or disable the VRRP virtual router."
    ::= { vrrpNewCfgVirtRtrTableEntry 17 }
    
vrrpNewCfgVirtRtrFastAdvertisement OBJECT-TYPE
    SYNTAX  INTEGER {
        enabled(1),
        disabled(2)
        }
    MAX-ACCESS  read-create
    STATUS  current
    DESCRIPTION
        "This object can be enabled if sub-second advertisement interval is required.
         When FAST_ADVERTISEMENT is enabled, 
           - New message type FAST_ADVERTISEMENT(2) will be used in the
         VRRP advertisements
           - Can interop only with another FAST_ADVERTISEMENT enabled router
           - VRRP advertisement interval will be sent in units of centi-seconds
           - Timers will be running with centi-second granularity"
         
    DEFVAL    { disabled }
    ::= { vrrpNewCfgVirtRtrTableEntry 18 }

vrrpNewCfgVirtRtrPreDelay OBJECT-TYPE
    SYNTAX  INTEGER (0..255)
    MAX-ACCESS  read-create
    STATUS  current
    DESCRIPTION
        "The pre-emptive delay interval in seconds."
    ::= { vrrpNewCfgVirtRtrTableEntry 19 }
-- VRRP Interface Table

vrrpIfTableMaxSize OBJECT-TYPE
    SYNTAX Integer32
    MAX-ACCESS read-only
    STATUS current
    DESCRIPTION
        "The maximum number of entries in VRRP interface table."
    ::= { vrrpCfg 5 }

vrrpCurCfgIfTable OBJECT-TYPE
    SYNTAX  SEQUENCE OF VrrpCurCfgIfTableEntry
    MAX-ACCESS  not-accessible
    STATUS  current
    DESCRIPTION
        "The table of VRRP interface in the current configuration block."
    ::= { vrrpCfg 6 }
 
vrrpCurCfgIfTableEntry OBJECT-TYPE
    SYNTAX  VrrpCurCfgIfTableEntry
    MAX-ACCESS  not-accessible
    STATUS  current
    DESCRIPTION
        "Information about a VRRP interface."
    INDEX   { vrrpCurCfgIfIndx }
    ::= { vrrpCurCfgIfTable 1 }
 
VrrpCurCfgIfTableEntry ::= SEQUENCE {
    vrrpCurCfgIfIndx         Integer32,
    vrrpCurCfgIfAuthType     INTEGER,
    vrrpCurCfgIfPasswd       DisplayString
    }

vrrpCurCfgIfIndx OBJECT-TYPE
    SYNTAX  Integer32
    MAX-ACCESS  read-only
    STATUS  current
    DESCRIPTION
        "The VRRP interface index.  This is eqivalent to IfIndex."
    ::= { vrrpCurCfgIfTableEntry 1 }

vrrpCurCfgIfAuthType OBJECT-TYPE
    SYNTAX  INTEGER {
        none(1),
        simple-text-password(2)
        }
    MAX-ACCESS  read-only
    STATUS  current
    DESCRIPTION
        "Type of authentication being used.
     none(1) - no authentication
     simple-text-password(2) - use password specified in 
         vrrpCurCfgIfPasswd for authentication."
    ::= { vrrpCurCfgIfTableEntry 2 }

vrrpCurCfgIfPasswd OBJECT-TYPE
    SYNTAX  DisplayString (SIZE(0..7))
    MAX-ACCESS  read-only
    STATUS  current
    DESCRIPTION
        "The password for authentication."
    ::= { vrrpCurCfgIfTableEntry 3 }

vrrpNewCfgIfTable OBJECT-TYPE
    SYNTAX  SEQUENCE OF VrrpNewCfgIfTableEntry
    MAX-ACCESS  not-accessible
    STATUS  current
    DESCRIPTION
        "The table of VRRP interface in the current configuration block."
    ::= { vrrpCfg 7 }
 
vrrpNewCfgIfTableEntry OBJECT-TYPE
    SYNTAX  VrrpNewCfgIfTableEntry
    MAX-ACCESS  not-accessible
    STATUS  current
    DESCRIPTION
        "Information about a VRRP interface."
    INDEX   { vrrpNewCfgIfIndx }
    ::= { vrrpNewCfgIfTable 1 }
 
VrrpNewCfgIfTableEntry ::= SEQUENCE {
    vrrpNewCfgIfIndx         Integer32,
    vrrpNewCfgIfAuthType     INTEGER,
    vrrpNewCfgIfPasswd       DisplayString,
    vrrpNewCfgIfDelete       INTEGER
    }

vrrpNewCfgIfIndx OBJECT-TYPE
    SYNTAX  Integer32
    MAX-ACCESS  read-only
    STATUS  current
    DESCRIPTION
        "The VRRP interface index.  This is eqivalent to IfIndex."
    ::= { vrrpNewCfgIfTableEntry 1 }

vrrpNewCfgIfAuthType OBJECT-TYPE
    SYNTAX  INTEGER {
        none(1),
        simple-text-password(2)
        }
    MAX-ACCESS  read-create
    STATUS  current
    DESCRIPTION
        "Type of authentication being used.
     none(1) - no authentication
     simple-text-password(2) - use password specified in 
         vrrpNewCfgIfPasswd for authentication."
    ::= { vrrpNewCfgIfTableEntry 2 }

vrrpNewCfgIfPasswd OBJECT-TYPE
    SYNTAX  DisplayString (SIZE(0..8))
    MAX-ACCESS  read-create
    STATUS  current
    DESCRIPTION
        "The password for authentication."
    ::= { vrrpNewCfgIfTableEntry 3 }

vrrpNewCfgIfDelete OBJECT-TYPE
    SYNTAX  INTEGER {
        other(1),
        delete(2)
        }
    MAX-ACCESS  read-create
    STATUS  current
    DESCRIPTION
        "When set to the value of 2 (delete), the entire row is deleted. 
         When read, other(1) is returned. Setting the value to anything 
         other than delete(2) has no effect on the state of the row."
    ::= { vrrpNewCfgIfTableEntry 4 }

-- Failover Virtual Router Groups
vrrpVirtRtrGrpTableMaxSize OBJECT-TYPE
    SYNTAX Integer32
    MAX-ACCESS read-only
    STATUS current
    DESCRIPTION
        "The maximum number of entries in VRRP Group table."
    ::= { vrrpCfg 8 }

vrrpCurCfgVirtRtrGrpTable OBJECT-TYPE
    SYNTAX  SEQUENCE OF VrrpCurCfgVirtRtrGrpTableEntry
    MAX-ACCESS  not-accessible
    STATUS  current
    DESCRIPTION
        "The table of VRRP virtual router group in the current configuration block."
    ::= { vrrpCfg 9 }

vrrpCurCfgVirtRtrGrpTableEntry OBJECT-TYPE
    SYNTAX  VrrpCurCfgVirtRtrGrpTableEntry
    MAX-ACCESS  not-accessible
    STATUS  current
    DESCRIPTION
        "Information about a VRRP failover virtual router."
    INDEX   { vrrpCurCfgVirtRtrGrpIndx }
    ::= { vrrpCurCfgVirtRtrGrpTable 1 }

VrrpCurCfgVirtRtrGrpTableEntry ::= SEQUENCE {
    vrrpCurCfgVirtRtrGrpIndx                Integer32,
    vrrpCurCfgVirtRtrGrpID                  INTEGER,
    vrrpCurCfgVirtRtrGrpIfIndex             Integer32,
    vrrpCurCfgVirtRtrGrpInterval            INTEGER,
    vrrpCurCfgVirtRtrGrpPriority            INTEGER,
    vrrpCurCfgVirtRtrGrpPreempt             INTEGER,
    vrrpCurCfgVirtRtrGrpState               INTEGER,
    vrrpCurCfgVirtRtrGrpTckIpIntf           INTEGER,
    vrrpCurCfgVirtRtrGrpTckVlanPort         INTEGER
   ,vrrpCurCfgVirtRtrGrpFastAdvertisement   INTEGER
    ,vrrpCurCfgVirtRtrGrpPredelay           INTEGER
    }
 
vrrpCurCfgVirtRtrGrpIndx OBJECT-TYPE
    SYNTAX  Integer32
    MAX-ACCESS  read-only
    STATUS  current
    DESCRIPTION
        "The VRRP virtual router table index."
    ::= { vrrpCurCfgVirtRtrGrpTableEntry 1 }
 
vrrpCurCfgVirtRtrGrpID OBJECT-TYPE
    SYNTAX  INTEGER (1..255)
    MAX-ACCESS  read-only
    STATUS  current 
    DESCRIPTION
        "The VRRP virtual router identifier."
    ::= { vrrpCurCfgVirtRtrGrpTableEntry 2 }
 
vrrpCurCfgVirtRtrGrpIfIndex OBJECT-TYPE
    SYNTAX  Integer32
    MAX-ACCESS  read-only
    STATUS  current
    DESCRIPTION
        "The IfIndex that the VRRP virtual router is representing."
    ::= { vrrpCurCfgVirtRtrGrpTableEntry 3 }

vrrpCurCfgVirtRtrGrpInterval OBJECT-TYPE
    SYNTAX  INTEGER (1..255)
    MAX-ACCESS  read-only
    STATUS  current
    DESCRIPTION
        "The time interval between VRRP advertisements in seconds."
    ::= { vrrpCurCfgVirtRtrGrpTableEntry 4 }

vrrpCurCfgVirtRtrGrpPriority OBJECT-TYPE
    SYNTAX  INTEGER (1..254)
    MAX-ACCESS  read-only
    STATUS  current
    DESCRIPTION
        "The priority value to be used by the specified VRRP virtual routers."
    ::= { vrrpCurCfgVirtRtrGrpTableEntry 5 }

vrrpCurCfgVirtRtrGrpPreempt OBJECT-TYPE
    SYNTAX  INTEGER {
        enabled(1),
        disabled(2)
        }
    MAX-ACCESS  read-only
    STATUS  current
    DESCRIPTION
        "This is for controlling whether a higher priority Backup
         VRRP virtual router preempts a low priority Master.

         enabled(1)  - allow preemption
         disabled(2) - prohibit preemption"
   ::= { vrrpCurCfgVirtRtrGrpTableEntry 6 }

vrrpCurCfgVirtRtrGrpState OBJECT-TYPE
    SYNTAX  INTEGER {
        enabled(1),
        disabled(2)
        }
    MAX-ACCESS  read-only
    STATUS  current
    DESCRIPTION
        "Enable or disable the VRRP virtual router."
    ::= { vrrpCurCfgVirtRtrGrpTableEntry 7 }



vrrpCurCfgVirtRtrGrpTckIpIntf OBJECT-TYPE
    SYNTAX  INTEGER {
        enabled(1),
        disabled(2)
        }
    MAX-ACCESS  read-only
    STATUS  current
    DESCRIPTION
        "Enable or disable tracking other router interfaces for
         priority adjustment.  the priority increment is defined
         in vrrpCurCfgGenTckIpIntfInc."
    ::= { vrrpCurCfgVirtRtrGrpTableEntry 10 }

vrrpCurCfgVirtRtrGrpTckVlanPort OBJECT-TYPE
    SYNTAX  INTEGER {
        enabled(1),
        disabled(2)
        }
    MAX-ACCESS  read-only
    STATUS  current
    DESCRIPTION
        "Enable or disable tracking port state of VLAN ports
         for priority adjustment.  the priority increment is
         defined in vrrpCurCfgGenTckVlanPortInc."
    ::= { vrrpCurCfgVirtRtrGrpTableEntry 11 }


vrrpCurCfgVirtRtrGrpFastAdvertisement OBJECT-TYPE
    SYNTAX  INTEGER {
        enabled(1),
        disabled(2)
        }
    MAX-ACCESS read-only 
    STATUS  current
    DESCRIPTION
        "This object provides the status of FAST_ADVERTISEMENT.
         When FAST_ADVERTISEMENT is enabled, 
           - New message type FAST_ADVERTISEMENT(2) will be used in the
         VRRP advertisements
           - Can interop only with another FAST_ADVERTISEMENT enabled router
           - VRRP advertisement interval will be sent in units of centi-seconds
           - Timers will be running with centi-second granularity"
    ::= { vrrpCurCfgVirtRtrGrpTableEntry 16 }




vrrpCurCfgVirtRtrGrpPredelay OBJECT-TYPE
    SYNTAX  INTEGER (1..255)
    MAX-ACCESS  read-only
    STATUS  current
    DESCRIPTION
        "The pre-emptive delay interval in seconds for specified VRRP virtual routers."
    ::= { vrrpCurCfgVirtRtrGrpTableEntry 21 }


vrrpNewCfgVirtRtrGrpTable OBJECT-TYPE
    SYNTAX  SEQUENCE OF VrrpNewCfgVirtRtrGrpTableEntry
    MAX-ACCESS  not-accessible
    STATUS  current
    DESCRIPTION
        "The table of VRRP virtual router group in the new configuration block."
    ::= { vrrpCfg 10 }

vrrpNewCfgVirtRtrGrpTableEntry OBJECT-TYPE
    SYNTAX  VrrpNewCfgVirtRtrGrpTableEntry
    MAX-ACCESS  not-accessible
    STATUS  current
    DESCRIPTION
        "Information about a VRRP failover virtual router."
    INDEX   { vrrpNewCfgVirtRtrGrpIndx }
    ::= { vrrpNewCfgVirtRtrGrpTable 1 }
 
VrrpNewCfgVirtRtrGrpTableEntry ::= SEQUENCE {
    vrrpNewCfgVirtRtrGrpIndx                Integer32,
    vrrpNewCfgVirtRtrGrpID                  INTEGER,
    vrrpNewCfgVirtRtrGrpIfIndex             Integer32,
    vrrpNewCfgVirtRtrGrpInterval            INTEGER,
    vrrpNewCfgVirtRtrGrpPriority            INTEGER,
    vrrpNewCfgVirtRtrGrpPreempt             INTEGER,
    vrrpNewCfgVirtRtrGrpState               INTEGER,
    vrrpNewCfgVirtRtrGrpDelete              INTEGER,
    vrrpNewCfgVirtRtrGrpTckIpIntf           INTEGER,
    vrrpNewCfgVirtRtrGrpTckVlanPort         INTEGER
   ,vrrpNewCfgVirtRtrGrpFastAdvertisement   INTEGER
    ,vrrpNewCfgVirtRtrGrpPredelay            INTEGER
    }
 
vrrpNewCfgVirtRtrGrpIndx OBJECT-TYPE
    SYNTAX  Integer32
    MAX-ACCESS  read-only
    STATUS  current
    DESCRIPTION
        "The VRRP virtual router table index."
    ::= { vrrpNewCfgVirtRtrGrpTableEntry 1 }

vrrpNewCfgVirtRtrGrpID OBJECT-TYPE
    SYNTAX  INTEGER (1..255)
    MAX-ACCESS  read-create
    STATUS  current 
    DESCRIPTION
        "The VRRP virtual router identifier."
    ::= { vrrpNewCfgVirtRtrGrpTableEntry 2 }

vrrpNewCfgVirtRtrGrpIfIndex OBJECT-TYPE
    SYNTAX  Integer32
    MAX-ACCESS  read-create
    STATUS  current
    DESCRIPTION
        "The IfIndex that the VRRP virtual router is representing."
    ::= { vrrpNewCfgVirtRtrGrpTableEntry 3 }

vrrpNewCfgVirtRtrGrpInterval OBJECT-TYPE
    SYNTAX  INTEGER (1..255)
    MAX-ACCESS  read-create
    STATUS  current
    DESCRIPTION
        "The time interval between VRRP advertisements in seconds."
    ::= { vrrpNewCfgVirtRtrGrpTableEntry 4 }

vrrpNewCfgVirtRtrGrpPriority OBJECT-TYPE
    SYNTAX  INTEGER (1..254)
    MAX-ACCESS  read-create
    STATUS  current
    DESCRIPTION
        "The priority value to be used by the specified VRRP virtual router."
    ::= { vrrpNewCfgVirtRtrGrpTableEntry 5 }

vrrpNewCfgVirtRtrGrpPreempt OBJECT-TYPE
    SYNTAX  INTEGER {
        enabled(1),
        disabled(2)
        }
    MAX-ACCESS  read-create
    STATUS  current
    DESCRIPTION
        "This is for controlling whether a higher priority Backup
         VRRP virtual router preempts a low priority Master.

         enabled(1)  - allow preemption
         disabled(2) - prohibit preemption"
    ::= { vrrpNewCfgVirtRtrGrpTableEntry 6 }

vrrpNewCfgVirtRtrGrpState OBJECT-TYPE
    SYNTAX  INTEGER {
        enabled(1),
        disabled(2)
        }
    MAX-ACCESS  read-create
    STATUS  current
    DESCRIPTION
        "Enable or disable the VRRP virtual router."
    ::= { vrrpNewCfgVirtRtrGrpTableEntry 7 }

vrrpNewCfgVirtRtrGrpDelete OBJECT-TYPE
    SYNTAX  INTEGER {
        other(1),
        delete(2)
        }
    MAX-ACCESS  read-create
    STATUS  current
    DESCRIPTION
        "When set to the value of 2 (delete), the entire row is deleted. 
         When read, other(1) is returned. Setting the value to anything 
         other than delete(2) has no effect on the state of the row."
    ::= { vrrpNewCfgVirtRtrGrpTableEntry 8 }



vrrpNewCfgVirtRtrGrpTckIpIntf OBJECT-TYPE
    SYNTAX  INTEGER {
        enabled(1),
        disabled(2)
        }
    MAX-ACCESS  read-create
    STATUS  current
    DESCRIPTION
        "Enable or disable tracking other router interfaces for
         priority adjustment.  the priority increment is defined
         in vrrpNewCfgGenTckIpIntfInc."
    ::= { vrrpNewCfgVirtRtrGrpTableEntry 11 }

vrrpNewCfgVirtRtrGrpTckVlanPort OBJECT-TYPE
    SYNTAX  INTEGER {
        enabled(1),
        disabled(2)
        }
    MAX-ACCESS  read-create
    STATUS  current
    DESCRIPTION
        "Enable or disable tracking port state of VLAN ports
         for priority adjustment.  the priority increment is
         defined in vrrpNewCfgGenTckVlanPortInc."
    ::= { vrrpNewCfgVirtRtrGrpTableEntry 12 }


vrrpNewCfgVirtRtrGrpFastAdvertisement OBJECT-TYPE
    SYNTAX  INTEGER {
        enabled(1),
        disabled(2)
        }
    MAX-ACCESS  read-create
    STATUS  current
    DESCRIPTION
        "This object can be enabled if sub-second advertisement interval is required.
         When FAST_ADVERTISEMENT is enabled, 
           - New message type FAST_ADVERTISEMENT(2) will be used in the
         VRRP advertisements
           - Can interop only with another FAST_ADVERTISEMENT enabled router
           - VRRP advertisement interval will be sent in units of centi-seconds
           - Timers will be running with centi-second granularity"
         
    DEFVAL    { disabled }
    ::= {vrrpNewCfgVirtRtrGrpTableEntry 17 }




vrrpNewCfgVirtRtrGrpPredelay OBJECT-TYPE
    SYNTAX  INTEGER (0..255)
    MAX-ACCESS  read-create
    STATUS  current
    DESCRIPTION
         "The pre-emptive delay interval in seconds."
    ::= { vrrpNewCfgVirtRtrGrpTableEntry 21 }




-- Domain Name Server Configuration

dnsCurCfgPrimaryIpAddr OBJECT-TYPE
    SYNTAX DisplayString
    MAX-ACCESS  read-only
    STATUS  current
    DESCRIPTION
        "The DNS primary IP address in the current configuration block."
    ::= { dnsCfg 1 }

dnsNewCfgPrimaryIpAddr OBJECT-TYPE
    SYNTAX DisplayString
    MAX-ACCESS  read-write
    STATUS  current
    DESCRIPTION
        "The DNS primary IP address in the new configuration block."
    ::= { dnsCfg 2 }

dnsCurCfgSecondaryIpAddr OBJECT-TYPE
    SYNTAX DisplayString
    MAX-ACCESS  read-only
    STATUS  current
    DESCRIPTION
        "The DNS primary IP address in the current configuration block."
    ::= { dnsCfg 3 }

dnsNewCfgSecondaryIpAddr OBJECT-TYPE
    SYNTAX DisplayString
    MAX-ACCESS  read-write
    STATUS  current
    DESCRIPTION
        "The DNS primary IP address in the new configuration block."
    ::= { dnsCfg 4 }

dnsCurCfgDomainName OBJECT-TYPE
    SYNTAX  DisplayString (SIZE(0..191))
    MAX-ACCESS  read-only
    STATUS  current
    DESCRIPTION
        "The DNS doamin name in the current configuration block."
    ::= { dnsCfg 5 }

dnsNewCfgDomainName OBJECT-TYPE
    SYNTAX  DisplayString (SIZE(0..191))
    MAX-ACCESS  read-write
    STATUS  current
    DESCRIPTION
        "The DNS doamin name in the new configuration block."
    ::= { dnsCfg 6 }

dnsNewCfgFirstRequestAddr OBJECT-TYPE
   SYNTAX  INTEGER{
        ipv4(1),
        ipv6(2)
        }
   MAX-ACCESS read-write
   STATUS current
   DESCRIPTION
    "Type of the first request to dns"
   ::= { dnsCfg 9 }

dnsCurCfgFirstRequestAddr OBJECT-TYPE
   SYNTAX  INTEGER{
        ipv4(1),
        ipv6(2)
        }
   MAX-ACCESS read-only
   STATUS current
   DESCRIPTION
    "Type of the first request to dns"
   ::= { dnsCfg 10}

dnsCurCfgPriServerPort OBJECT-TYPE
    SYNTAX  INTEGER {
        data(1),
        mgt(2)
        }
    MAX-ACCESS  read-only
    STATUS  current
    DESCRIPTION
        "Choose the port that the primary server is connected to."
    ::= { dnsCfg 11 }

dnsNewCfgPriServerPort OBJECT-TYPE
    SYNTAX  INTEGER {
        data(1),
        mgt(2)
        }
    MAX-ACCESS  read-write
    STATUS  current
    DESCRIPTION
        "Choose the port that the primary server is connected to."
    ::= { dnsCfg 12 }

dnsCurCfgSecServerPort OBJECT-TYPE
    SYNTAX  INTEGER {
        data(1),
        mgt(2)
        }
    MAX-ACCESS  read-only
    STATUS  current
    DESCRIPTION
        "Choose the port that the secondary server is connected to."
    ::= { dnsCfg 13 }

dnsNewCfgSecServerPort OBJECT-TYPE
    SYNTAX  INTEGER {
        data(1),
        mgt(2)
        }
    MAX-ACCESS  read-write
    STATUS  current
    DESCRIPTION
        "Choose the port that the secondary server is connected to."
    ::= { dnsCfg 14 }

--
-- IP network filter configuration
--
ipNwfTableMax OBJECT-TYPE
    SYNTAX Integer32
    MAX-ACCESS read-only
    STATUS current
    DESCRIPTION
    "The maximum number of rows in the IP network filter table."
    ::= { ipNwfCfg 1 }

ipCurCfgNwfTable OBJECT-TYPE
    SYNTAX SEQUENCE OF IpCurCfgNwfEntry
    MAX-ACCESS not-accessible
    STATUS current
    DESCRIPTION
      "The table of IP network filter in the current configuration block."
    ::= { ipNwfCfg 2 }

ipCurCfgNwfEntry OBJECT-TYPE
    SYNTAX IpCurCfgNwfEntry
    MAX-ACCESS not-accessible
    STATUS current
    DESCRIPTION
      "Information about an IP network filter."
    INDEX { ipCurCfgNwfIndex }
    ::= { ipCurCfgNwfTable 1 }
 
IpCurCfgNwfEntry ::= SEQUENCE {
    ipCurCfgNwfIndex     Integer32,
    ipCurCfgNwfAddr      IpAddress,
    ipCurCfgNwfMask      IpAddress,
    ipCurCfgNwfState     INTEGER
    }
 
ipCurCfgNwfIndex OBJECT-TYPE
    SYNTAX Integer32
    MAX-ACCESS read-only
    STATUS current
    DESCRIPTION
    "The netowrk filter number for which the NWF is related."
    ::= { ipCurCfgNwfEntry 1}

ipCurCfgNwfAddr OBJECT-TYPE
    SYNTAX IpAddress
    MAX-ACCESS read-only
    STATUS current
    DESCRIPTION
    "The IP address of the network filter."
    ::= { ipCurCfgNwfEntry 2 }

ipCurCfgNwfMask OBJECT-TYPE
    SYNTAX IpAddress
    MAX-ACCESS read-only
    STATUS current  
    DESCRIPTION
    "The IP network filter mask."
    ::= { ipCurCfgNwfEntry 3 }

ipCurCfgNwfState OBJECT-TYPE
    SYNTAX INTEGER { 
        enabled(1),
        disabled(2)
    }
    MAX-ACCESS  read-only
    STATUS  current  
    DESCRIPTION
    "Enable or disable the network filter."
    ::= { ipCurCfgNwfEntry 4 }

ipNewCfgNwfTable OBJECT-TYPE
    SYNTAX SEQUENCE OF IpNewCfgNwfEntry
    MAX-ACCESS not-accessible
    STATUS current
    DESCRIPTION
      "The table of IP network filter in the current configuration block."
    ::= { ipNwfCfg 3 }

ipNewCfgNwfEntry OBJECT-TYPE
    SYNTAX IpNewCfgNwfEntry
    MAX-ACCESS not-accessible
    STATUS current
    DESCRIPTION
      "Information about an IP network filter."
    INDEX { ipNewCfgNwfIndex }
    ::= { ipNewCfgNwfTable 1 }
 
IpNewCfgNwfEntry ::= SEQUENCE {
    ipNewCfgNwfIndex     Integer32,
    ipNewCfgNwfAddr      IpAddress,
    ipNewCfgNwfMask      IpAddress,
    ipNewCfgNwfState     INTEGER,
    ipNewCfgNwfDelete    INTEGER
    }
 
ipNewCfgNwfIndex OBJECT-TYPE
    SYNTAX Integer32
    MAX-ACCESS read-only
    STATUS current
    DESCRIPTION
    "The netowrk filter number for which the NWF is related."
    ::= { ipNewCfgNwfEntry 1}

ipNewCfgNwfAddr OBJECT-TYPE
    SYNTAX IpAddress
    MAX-ACCESS read-create
    STATUS current
    DESCRIPTION
    "The IP address of the network filter."
    ::= { ipNewCfgNwfEntry 2 }

ipNewCfgNwfMask OBJECT-TYPE
    SYNTAX IpAddress
    MAX-ACCESS read-create
    STATUS current  
    DESCRIPTION
    "The IP network filter mask."
    ::= { ipNewCfgNwfEntry 3 }

ipNewCfgNwfState OBJECT-TYPE
    SYNTAX INTEGER { 
        enabled(1),
        disabled(2)
    }
    MAX-ACCESS  read-create
    STATUS  current  
    DESCRIPTION
    "Enable or disable the network filter."
    ::= { ipNewCfgNwfEntry 4 }

ipNewCfgNwfDelete OBJECT-TYPE
    SYNTAX INTEGER { 
        other(1),
        delete(2)
        }
    MAX-ACCESS read-create
    STATUS current
    DESCRIPTION
    "When set to the value of 2 (delete), the entire row is deleted. 
     When read, other(1) is returned. Setting the value to anything 
     other than 2(delete) has no effect on the state of the row."
    ::= { ipNewCfgNwfEntry 5 }

--
-- IP route map configuration
--
ipRmapTableMax OBJECT-TYPE
    SYNTAX Integer32
    MAX-ACCESS read-only
    STATUS current
    DESCRIPTION
    "The maximum number of rows in the IP route map table."
    ::= { ipRmapCfg 1 }

ipCurCfgRmapTable OBJECT-TYPE
    SYNTAX SEQUENCE OF IpCurCfgRmapEntry
    MAX-ACCESS not-accessible
    STATUS current
    DESCRIPTION
      "The table of IP route map in the current configuration block."
    ::= { ipRmapCfg 2 }

ipCurCfgRmapEntry OBJECT-TYPE
    SYNTAX IpCurCfgRmapEntry
    MAX-ACCESS not-accessible
    STATUS current
    DESCRIPTION
      "Information about an IP route map."
    INDEX { ipCurCfgRmapIndex }
    ::= { ipCurCfgRmapTable 1 }
 
IpCurCfgRmapEntry ::= SEQUENCE {
    ipCurCfgRmapIndex       Integer32,
    ipCurCfgRmapLp      Unsigned32,
    ipCurCfgRmapMetric      Unsigned32,
    ipCurCfgRmapPrec        INTEGER,
    ipCurCfgRmapWeight      INTEGER,
    ipCurCfgRmapAp              DisplayString, 
    ipCurCfgRmapMetricType      INTEGER,
    ipCurCfgRmapNexthop   INTEGER,
    ipCurCfgRmapState       INTEGER
    }
 
ipCurCfgRmapIndex OBJECT-TYPE
    SYNTAX Integer32
    MAX-ACCESS read-only
    STATUS current
    DESCRIPTION
    "The route map number for which the RMAP is related."
    ::= { ipCurCfgRmapEntry 1}

ipCurCfgRmapLp OBJECT-TYPE
    SYNTAX Unsigned32 (0..4294967295) 
    MAX-ACCESS read-only
    STATUS current
    DESCRIPTION
    "The local-preference of the route map. 4294967295 means none"
    ::= { ipCurCfgRmapEntry 2 }

ipCurCfgRmapMetric OBJECT-TYPE
    SYNTAX Unsigned32 (1..4294967295) 
    MAX-ACCESS read-only
    STATUS current
    DESCRIPTION
    "The metric of the route map. 4294967295 means none.
     Range is [1-16777214] if OSPF metric-type is used."
    ::= { ipCurCfgRmapEntry 3 }

ipCurCfgRmapPrec OBJECT-TYPE
    SYNTAX INTEGER (1..255) 
    MAX-ACCESS read-only
    STATUS current
    DESCRIPTION
    "The precedence of the route map."
    ::= { ipCurCfgRmapEntry 4 }

ipCurCfgRmapWeight OBJECT-TYPE
    SYNTAX INTEGER (0..65535) 
    MAX-ACCESS read-only
    STATUS current
    DESCRIPTION
    "The weight of the route map. 65535 means none"
    ::= { ipCurCfgRmapEntry 5 }

ipCurCfgRmapState OBJECT-TYPE
    SYNTAX INTEGER { 
        enabled(1),
        disabled(2)
    }
    MAX-ACCESS  read-only
    STATUS  current  
    DESCRIPTION
    "Enable or disable the route map."
    ::= { ipCurCfgRmapEntry 6 }

ipCurCfgRmapAp OBJECT-TYPE
    SYNTAX DisplayString (SIZE(0..17)) 
    MAX-ACCESS read-only
    STATUS current
    DESCRIPTION
    "The as-path prepend of the matched route. Up to 3 AS number can be 
     displayed for the string. 
     The usuage is:<AS number> [<AS number>][ <AS number>]"
    ::= { ipCurCfgRmapEntry 7 }

ipCurCfgRmapMetricType OBJECT-TYPE
    SYNTAX INTEGER {
        none(1),
        type1(2),
        type2(3)
        }
    MAX-ACCESS  read-only
    STATUS  current  
    DESCRIPTION
    "The OSPF metric-type of the matched route."
    ::= { ipCurCfgRmapEntry 8 }
ipCurCfgRmapNexthop OBJECT-TYPE
    SYNTAX INTEGER { 
        enabled(1),
        disabled(2)
    }
    MAX-ACCESS  read-only
    STATUS  current  
    DESCRIPTION
    "Peer address as nexthop of the matched route(only for BGP)."
    ::= { ipCurCfgRmapEntry 9 }

ipNewCfgRmapTable OBJECT-TYPE
    SYNTAX SEQUENCE OF IpNewCfgRmapEntry
    MAX-ACCESS not-accessible
    STATUS current
    DESCRIPTION
      "The table of IP route map in the new configuration block."
    ::= { ipRmapCfg 3 }

ipNewCfgRmapEntry OBJECT-TYPE
    SYNTAX IpNewCfgRmapEntry
    MAX-ACCESS not-accessible
    STATUS current
    DESCRIPTION
      "Information about an IP route map."
    INDEX { ipNewCfgRmapIndex }
    ::= { ipNewCfgRmapTable 1 }
 
IpNewCfgRmapEntry ::= SEQUENCE {
    ipNewCfgRmapIndex       Integer32,
    ipNewCfgRmapLp      Unsigned32,
    ipNewCfgRmapMetric      Unsigned32,
    ipNewCfgRmapPrec        INTEGER,
    ipNewCfgRmapWeight      INTEGER,
    ipNewCfgRmapAp              DisplayString, 
    ipNewCfgRmapState       INTEGER,
    ipNewCfgRmapMetricType  INTEGER,
    ipNewCfgRmapNexthop     INTEGER,
    ipNewCfgRmapDelete      INTEGER
    }
 
ipNewCfgRmapIndex OBJECT-TYPE
    SYNTAX Integer32
    MAX-ACCESS read-only
    STATUS current
    DESCRIPTION
    "The route map number for which the RMAP is related."
    ::= { ipNewCfgRmapEntry 1}

ipNewCfgRmapLp OBJECT-TYPE
    SYNTAX Unsigned32 (0..4294967295) 
    MAX-ACCESS read-create
    STATUS current
    DESCRIPTION
    "The local-preference of the route map. 4294967295 means none"
    ::= { ipNewCfgRmapEntry 2 }

ipNewCfgRmapMetric OBJECT-TYPE
    SYNTAX Unsigned32 (1..4294967295) 
    MAX-ACCESS read-create
    STATUS current
    DESCRIPTION
    "The metric of the route map. 4294967295 means none.
     Range is [1-16777214] if OSPF metric-type is used."
    ::= { ipNewCfgRmapEntry 3 }

ipNewCfgRmapPrec OBJECT-TYPE
    SYNTAX INTEGER (1..255) 
    MAX-ACCESS read-create
    STATUS current
    DESCRIPTION
    "The precedence of the route map."
    ::= { ipNewCfgRmapEntry 4 }

ipNewCfgRmapWeight OBJECT-TYPE
    SYNTAX INTEGER (0..65535) 
    MAX-ACCESS read-create
    STATUS current
    DESCRIPTION
    "The weight of the route map. 65535 means none"
    ::= { ipNewCfgRmapEntry 5 }

ipNewCfgRmapState OBJECT-TYPE
    SYNTAX INTEGER { 
        enabled(1),
        disabled(2)
    }
    MAX-ACCESS  read-create
    STATUS  current  
    DESCRIPTION
    "Enable or disable the route map."
    ::= { ipNewCfgRmapEntry 6 }

ipNewCfgRmapAp OBJECT-TYPE
    SYNTAX DisplayString (SIZE(0..17)) 
    MAX-ACCESS read-create
    STATUS current
    DESCRIPTION
    "The as-path prepend of the matched route. Up to 3 AS number can be 
     displayed for the string. 
     The usuage is:<AS number> [<AS number>][ <AS number>]"
    ::= { ipNewCfgRmapEntry 7 }

ipNewCfgRmapMetricType OBJECT-TYPE
    SYNTAX INTEGER {
        none(1),
        type1(2),
        type2(3)
        }
    MAX-ACCESS  read-create
    STATUS  current  
    DESCRIPTION
    "The OSPF metric-type of the matched route."
    ::= { ipNewCfgRmapEntry 8 }

ipNewCfgRmapDelete OBJECT-TYPE
    SYNTAX  INTEGER {
    other(1),
    delete(2)
    }
    MAX-ACCESS  read-create
    STATUS  current
    DESCRIPTION
    "When set to the value of 2 (delete), the entire row is deleted. 
     When read, other(1) is returned. Setting the value to anything 
     other than 2(delete) has no effect on the state of the row."
    ::= { ipNewCfgRmapEntry 9 }

ipNewCfgRmapNexthop OBJECT-TYPE
    SYNTAX INTEGER { 
        enabled(1),
        disabled(2)
    }
    MAX-ACCESS  read-create
    STATUS  current  
    DESCRIPTION
    "Peer address as nexthop of the matched route(only for BGP)."
    ::= { ipNewCfgRmapEntry 10 }

ipAlistTableMax OBJECT-TYPE
    SYNTAX Integer32
    MAX-ACCESS read-only
    STATUS current
    DESCRIPTION
    "The maximum number of rows in the IP route map table."
    ::= { ipRmapCfg 4 }

ipCurCfgAlistTable OBJECT-TYPE
    SYNTAX SEQUENCE OF IpCurCfgAlistEntry
    MAX-ACCESS not-accessible
    STATUS current
    DESCRIPTION
      "The table of IP route map access list in the current configuration 
       block."
    ::= { ipRmapCfg 5 }

ipCurCfgAlistEntry OBJECT-TYPE
    SYNTAX IpCurCfgAlistEntry
    MAX-ACCESS not-accessible
    STATUS current
    DESCRIPTION
      "Information about an IP route map."
    INDEX { ipCurCfgAlistRmapIndex, ipCurCfgAlistIndex }
    ::= { ipCurCfgAlistTable 1 }
 
IpCurCfgAlistEntry ::= SEQUENCE {
    ipCurCfgAlistRmapIndex  Integer32,
    ipCurCfgAlistIndex      Integer32,
    ipCurCfgAlistNwf        INTEGER,
    ipCurCfgAlistMetric     Unsigned32,
    ipCurCfgAlistAction     INTEGER,
    ipCurCfgAlistState      INTEGER
    }
 
ipCurCfgAlistRmapIndex OBJECT-TYPE
    SYNTAX Integer32
    MAX-ACCESS read-only
    STATUS current
    DESCRIPTION
    "The route map number for which the RMAP is related."
    ::= { ipCurCfgAlistEntry 1 }

ipCurCfgAlistIndex OBJECT-TYPE
    SYNTAX Integer32
    MAX-ACCESS read-only
    STATUS current
    DESCRIPTION
    "The access list number for which the access list is related."
    ::= { ipCurCfgAlistEntry 2 }

ipCurCfgAlistNwf OBJECT-TYPE
    SYNTAX INTEGER (0..256) 
    MAX-ACCESS read-only
    STATUS current
    DESCRIPTION
    "The network filter number of the route map access list. 
     0 means none"
    ::= { ipCurCfgAlistEntry 3 }

ipCurCfgAlistMetric OBJECT-TYPE
    SYNTAX Unsigned32 (1..4294967295) 
    MAX-ACCESS read-only
    STATUS current
    DESCRIPTION
    "The metric of the route map access list. 4294967295 means none"
    ::= { ipCurCfgAlistEntry 4 }

ipCurCfgAlistAction OBJECT-TYPE
    SYNTAX INTEGER {
    permit(1),
    deny(2)
    }
    MAX-ACCESS read-only
    STATUS current
    DESCRIPTION
    "Action of the route map access list."
    ::= { ipCurCfgAlistEntry 5 }

ipCurCfgAlistState OBJECT-TYPE
    SYNTAX INTEGER { 
        enabled(1),
        disabled(2)
    }
    MAX-ACCESS  read-only
    STATUS  current  
    DESCRIPTION
    "Enable or disable the route map access list."
    ::= { ipCurCfgAlistEntry 6 }

ipNewCfgAlistTable OBJECT-TYPE
    SYNTAX SEQUENCE OF IpNewCfgAlistEntry
    MAX-ACCESS not-accessible
    STATUS current
    DESCRIPTION
      "The table of IP route map access list in the current configuration
       block."
    ::= { ipRmapCfg 6 }

ipNewCfgAlistEntry OBJECT-TYPE
    SYNTAX IpNewCfgAlistEntry
    MAX-ACCESS not-accessible
    STATUS current
    DESCRIPTION
      "Information about an IP route map."
    INDEX { ipNewCfgAlistRmapIndex, ipNewCfgAlistIndex }
    ::= { ipNewCfgAlistTable 1 }
 
IpNewCfgAlistEntry ::= SEQUENCE {
    ipNewCfgAlistRmapIndex  Integer32,
    ipNewCfgAlistIndex      Integer32,
    ipNewCfgAlistNwf        INTEGER,
    ipNewCfgAlistMetric     Unsigned32,
    ipNewCfgAlistAction     INTEGER,
    ipNewCfgAlistState      INTEGER,
    ipNewCfgAlistDelete     INTEGER
    }
 
ipNewCfgAlistRmapIndex OBJECT-TYPE
    SYNTAX Integer32
    MAX-ACCESS read-only
    STATUS current
    DESCRIPTION
    "The route map number for which the RMAP is related."
    ::= { ipNewCfgAlistEntry 1 }

ipNewCfgAlistIndex OBJECT-TYPE
    SYNTAX Integer32
    MAX-ACCESS read-only
    STATUS current
    DESCRIPTION
    "The access list number for which the access list is related."
    ::= { ipNewCfgAlistEntry 2 }

ipNewCfgAlistNwf OBJECT-TYPE
    SYNTAX INTEGER (1..256) 
    MAX-ACCESS read-create
    STATUS current
    DESCRIPTION
    "The network filter number of the route map access list. 
     0 means none"
    ::= { ipNewCfgAlistEntry 3 }

ipNewCfgAlistMetric OBJECT-TYPE
    SYNTAX Unsigned32 (1..4294967295) 
    MAX-ACCESS read-create
    STATUS current
    DESCRIPTION
    "The metric of the route map access list. 4294967295 means none"
    ::= { ipNewCfgAlistEntry 4 }

ipNewCfgAlistAction OBJECT-TYPE
    SYNTAX INTEGER {
    permit(1),
    deny(2)
    }
    MAX-ACCESS read-create
    STATUS current
    DESCRIPTION
    "Action of the route map access list."
    ::= { ipNewCfgAlistEntry 5 }

ipNewCfgAlistState OBJECT-TYPE
    SYNTAX INTEGER { 
        enabled(1),
        disabled(2)
    }
    MAX-ACCESS  read-create
    STATUS  current  
    DESCRIPTION
    "Enable or disable the route map access list."
    ::= { ipNewCfgAlistEntry 6 }

ipNewCfgAlistDelete OBJECT-TYPE
    SYNTAX  INTEGER {
    other(1),
    delete(2)
    }
    MAX-ACCESS  read-create
    STATUS  current
    DESCRIPTION
    "When set to the value of 2 (delete), the entire row is deleted. 
     When read, other(1) is returned. Setting the value to anything 
     other than 2(delete) has no effect on the state of the row."
    ::= { ipNewCfgAlistEntry 7 }

ipAspathTableMax OBJECT-TYPE
    SYNTAX Integer32
    MAX-ACCESS read-only
    STATUS current
    DESCRIPTION
    "The maximum number of rows in the IP route map table."
    ::= { ipRmapCfg 7 }

ipCurCfgAspathTable OBJECT-TYPE
    SYNTAX SEQUENCE OF IpCurCfgAspathEntry
    MAX-ACCESS not-accessible
    STATUS current
    DESCRIPTION
      "The table of IP route map access path configuration."
    ::= { ipRmapCfg 8 }

ipCurCfgAspathEntry OBJECT-TYPE
    SYNTAX IpCurCfgAspathEntry
    MAX-ACCESS not-accessible
    STATUS current
    DESCRIPTION
      "Information about an IP route map."
    INDEX { ipCurCfgAspathRmapIndex, ipCurCfgAlistIndex }
    ::= { ipCurCfgAspathTable 1 }
 
IpCurCfgAspathEntry ::= SEQUENCE {
    ipCurCfgAspathRmapIndex Integer32,
    ipCurCfgAspathIndex     Integer32,
    ipCurCfgAspathAS        INTEGER,
    ipCurCfgAspathAction    INTEGER,
    ipCurCfgAspathState         INTEGER
    }
 
ipCurCfgAspathRmapIndex OBJECT-TYPE
    SYNTAX Integer32
    MAX-ACCESS read-only
    STATUS current
    DESCRIPTION
    "The route map number for which the RMAP is related."
    ::= { ipCurCfgAspathEntry 1 }

ipCurCfgAspathIndex OBJECT-TYPE
    SYNTAX Integer32
    MAX-ACCESS read-only
    STATUS current
    DESCRIPTION
    "The access path number for which the access list is related."
    ::= { ipCurCfgAspathEntry 2 }

ipCurCfgAspathAS OBJECT-TYPE
    SYNTAX INTEGER (1..65535) 
    MAX-ACCESS read-only
    STATUS current
    DESCRIPTION
    "The AS number of the route map access path. 
     0 means none"
    ::= { ipCurCfgAspathEntry 3 }

ipCurCfgAspathAction OBJECT-TYPE
    SYNTAX INTEGER {
    permit(1),
    deny(2)
    }
    MAX-ACCESS read-only
    STATUS current
    DESCRIPTION
    "Action of the route map access path."
    ::= { ipCurCfgAspathEntry 4 }

ipCurCfgAspathState OBJECT-TYPE
    SYNTAX INTEGER { 
        enabled(1),
        disabled(2)
    }
    MAX-ACCESS  read-only
    STATUS  current  
    DESCRIPTION
    "Enable or disable the route map access path."
    ::= { ipCurCfgAspathEntry 5 }

ipNewCfgAspathTable OBJECT-TYPE
    SYNTAX SEQUENCE OF IpNewCfgAspathEntry
    MAX-ACCESS not-accessible
    STATUS current
    DESCRIPTION
      "The table of IP route map access path configuration"
    ::= { ipRmapCfg 9 }

ipNewCfgAspathEntry OBJECT-TYPE
    SYNTAX IpNewCfgAspathEntry
    MAX-ACCESS not-accessible
    STATUS current
    DESCRIPTION
      "Information about an IP route map."
    INDEX { ipNewCfgAspathRmapIndex, ipNewCfgAspathIndex }
    ::= { ipNewCfgAspathTable 1 }
 
IpNewCfgAspathEntry ::= SEQUENCE {
    ipNewCfgAspathRmapIndex Integer32,
    ipNewCfgAspathIndex     Integer32,
    ipNewCfgAspathAS        INTEGER,
    ipNewCfgAspathAction    INTEGER,
    ipNewCfgAspathState         INTEGER,
    ipNewCfgAspathDelete    INTEGER
    }
 
ipNewCfgAspathRmapIndex OBJECT-TYPE
    SYNTAX Integer32
    MAX-ACCESS read-only
    STATUS current
    DESCRIPTION
    "The route map number for which the RMAP is related."
    ::= { ipNewCfgAspathEntry 1 }

ipNewCfgAspathIndex OBJECT-TYPE
    SYNTAX Integer32
    MAX-ACCESS read-only
    STATUS current
    DESCRIPTION
    "The access path number for which the access list is related."
    ::= { ipNewCfgAspathEntry 2 }

ipNewCfgAspathAS OBJECT-TYPE
    SYNTAX INTEGER (1..65535) 
    MAX-ACCESS read-create
    STATUS current
    DESCRIPTION
    "The AS number of the route map access path. 
     0 means none"
    ::= { ipNewCfgAspathEntry 3 }

ipNewCfgAspathAction OBJECT-TYPE
    SYNTAX INTEGER {
    permit(1),
    deny(2)
    }
    MAX-ACCESS read-create
    STATUS current
    DESCRIPTION
    "Action of the route map access path."
    ::= { ipNewCfgAspathEntry 4 }

ipNewCfgAspathState OBJECT-TYPE
    SYNTAX INTEGER { 
        enabled(1),
        disabled(2)
    }
    MAX-ACCESS  read-create
    STATUS  current  
    DESCRIPTION
    "Enable or disable the route map access path."
    ::= { ipNewCfgAspathEntry 5 }

ipNewCfgAspathDelete OBJECT-TYPE
    SYNTAX  INTEGER {
    other(1),
    delete(2)
    }
    MAX-ACCESS  read-create
    STATUS  current
    DESCRIPTION
    "When set to the value of 2 (delete), the entire row is deleted. 
     When read, other(1) is returned. Setting the value to anything 
     other than 2(delete) has no effect on the state of the row."
    ::= { ipNewCfgAspathEntry 6 }

--
-- IP BGP configuration
--
bgpGeneral  OBJECT IDENTIFIER ::= { bgpCfg 1 }

bgpCurCfgState OBJECT-TYPE
    SYNTAX INTEGER {
        on(1),
        off(2)
        }
    MAX-ACCESS read-only
    STATUS current
    DESCRIPTION
    "BGP global state."
    ::= { bgpGeneral 1 }

bgpNewCfgState OBJECT-TYPE
    SYNTAX INTEGER {
        on(1),
        off(2)
        }
    MAX-ACCESS read-write
    STATUS current
    DESCRIPTION
    "Globally turn BGP on or off."
    ::= { bgpGeneral 2 }

bgpCurCfgLocalPref OBJECT-TYPE
    SYNTAX Unsigned32 (0..4294967294) 
    MAX-ACCESS  read-only
    STATUS  current
    DESCRIPTION
        "Local preference value."
      ::= { bgpGeneral 3 }

bgpNewCfgLocalPref OBJECT-TYPE
    SYNTAX Unsigned32 (0..4294967294) 
    MAX-ACCESS  read-write
    STATUS  current
    DESCRIPTION
        "Local Preference value."
      ::= { bgpGeneral 4 }

bgpCurCfgASNumber OBJECT-TYPE
    SYNTAX INTEGER (0..65535)
    MAX-ACCESS read-only
    STATUS current
    DESCRIPTION
    "The autonomous system (AS) number."
    ::= { bgpGeneral 5 }

bgpNewCfgASNumber OBJECT-TYPE
    SYNTAX INTEGER (0..65535)
    MAX-ACCESS read-write
    STATUS current
    DESCRIPTION
    "The autonomous system (AS) number."
    ::= { bgpGeneral 6 }

bgpCurCfgEbgpMaxPaths OBJECT-TYPE
    SYNTAX Unsigned32 (0..4294967294) 
    MAX-ACCESS  read-only
    STATUS  current
    DESCRIPTION
        "Maximum eBGP Paths."
      ::= { bgpGeneral 7 }

bgpNewCfgEbgpMaxPaths OBJECT-TYPE
    SYNTAX Unsigned32 (0..4294967294) 
    MAX-ACCESS  read-write
    STATUS  current
    DESCRIPTION
        "Maximum eBGP Paths."
      ::= { bgpGeneral 8 }

bgpCurCfgIbgpMaxPaths OBJECT-TYPE
    SYNTAX Unsigned32 (0..4294967294)
    MAX-ACCESS  read-only
    STATUS  current
    DESCRIPTION
        "Maximum iBGP Paths."
      ::= { bgpGeneral 9 }

bgpNewCfgIbgpMaxPaths OBJECT-TYPE
    SYNTAX Unsigned32 (0..4294967294)  
    MAX-ACCESS  read-write
    STATUS  current
    DESCRIPTION
        "Maximum iBGP Paths."
      ::= { bgpGeneral 10 }

bgpCurCfgAsn4Comp OBJECT-TYPE
    SYNTAX INTEGER {
        enabled(1),
        disabled(2)
    }
    MAX-ACCESS read-only
    STATUS current
    DESCRIPTION
    "ASN4 to ASN2 compatibility."
    ::= { bgpGeneral 11 }

bgpNewCfgAsn4Comp OBJECT-TYPE
    SYNTAX INTEGER {
        enabled(1),
        disabled(2)
    }
    MAX-ACCESS read-write
    STATUS current
    DESCRIPTION
    "ASN4 to ASN2 compatibility."
    ::= { bgpGeneral 12 }

bgpCurCfgDscp OBJECT-TYPE
    SYNTAX INTEGER (0..63)
    MAX-ACCESS  read-only
    STATUS  current
    DESCRIPTION
        "BGP dscp marking value."
      ::= { bgpGeneral 13 }

bgpNewCfgDscp OBJECT-TYPE
    SYNTAX INTEGER (0..63)
    MAX-ACCESS  read-write
    STATUS  current
    DESCRIPTION
        "BGP dscp marking value."
      ::= { bgpGeneral 14 }

bgpNewCfgClusterId OBJECT-TYPE 

    SYNTAX IpAddress
    MAX-ACCESS read-write
    STATUS current
    DESCRIPTION
	"Cluster ID."
    ::= { bgpGeneral 15 }

bgpCurCfgClusterId OBJECT-TYPE
    SYNTAX IpAddress
    MAX-ACCESS read-only
    STATUS current
    DESCRIPTION
	"Cluster ID."
    ::= { bgpGeneral 16 }

bgpNewCfgClientToClientReflection OBJECT-TYPE
    SYNTAX INTEGER { 
        enabled(1),
        disabled(2)
    }
    MAX-ACCESS read-write
    STATUS current
    DESCRIPTION
	"Enable/disable client to client route reflection"
    ::= { bgpGeneral 17 }

bgpCurCfgClientToClientReflection OBJECT-TYPE
    SYNTAX INTEGER { 
        enabled(1),
        disabled(2)
    }
    MAX-ACCESS read-only
    STATUS current
    DESCRIPTION
	"Enable/disable client to client route reflection"
    ::= { bgpGeneral 18 }
      
bgpPeerTableMax OBJECT-TYPE
    SYNTAX Integer32
    MAX-ACCESS read-only
    STATUS current
    DESCRIPTION
    "The maximum number of rows in the BGP peer table."
    ::= { bgpCfg 2 }

bgpCurCfgPeerTable OBJECT-TYPE
    SYNTAX SEQUENCE OF BgpCurCfgPeerEntry
    MAX-ACCESS not-accessible
    STATUS current
    DESCRIPTION
      "The table of BGP peer in the current configuration block."
    ::= { bgpCfg 3 }

bgpCurCfgPeerEntry OBJECT-TYPE
    SYNTAX BgpCurCfgPeerEntry
    MAX-ACCESS not-accessible
    STATUS current
    DESCRIPTION
      "Information about a BGP peer."
    INDEX { bgpCurCfgPeerIndex }
    ::= { bgpCurCfgPeerTable 1 }

BgpCurCfgPeerEntry ::= SEQUENCE {
    bgpCurCfgPeerIndex      Integer32,
    bgpCurCfgPeerRemoteAddr IpAddress,
    bgpCurCfgPeerRemoteAs   INTEGER,
    bgpCurCfgPeerPassive      INTEGER,  
    bgpCurCfgPeerHold       INTEGER,
    bgpCurCfgPeerAlive      INTEGER,
    bgpCurCfgPeerAdvert     INTEGER,
    bgpCurCfgPeerRetry      INTEGER,
    bgpCurCfgPeerOrig       INTEGER,
    bgpCurCfgPeerRipState       INTEGER,
    bgpCurCfgPeerTtl        INTEGER,
    bgpCurCfgPeerPassword   DisplayString,
    bgpCurCfgPeerState      INTEGER,
    bgpCurCfgPeerMetric     Unsigned32,
    bgpCurCfgPeerDefaultAction  INTEGER,
    bgpCurCfgPeerOspfState  INTEGER,
    bgpCurCfgPeerFixedState     INTEGER,
    bgpCurCfgPeerStaticState    INTEGER,
    bgpCurCfgPeerInRmapList     OCTET STRING,
    bgpCurCfgPeerOutRmapList    OCTET STRING
    , bgpCurCfgPeerUpdateSrcIf        INTEGER
    , bgpCurCfgPeerUpdateSrcLoopIf    INTEGER
    , bgpCurCfgPeerTtlSecHops   INTEGER
    ,bgpCurCfgPeerNexthopSelf  INTEGER
    , bgpCurCfgPeerClient             INTEGER
    }

bgpCurCfgPeerIndex OBJECT-TYPE
    SYNTAX Integer32
    MAX-ACCESS read-only
    STATUS current
    DESCRIPTION
    "The BGP peer number for which the BGP peer table is related."
    ::= { bgpCurCfgPeerEntry 1 }

bgpCurCfgPeerRemoteAddr OBJECT-TYPE
    SYNTAX IpAddress
    MAX-ACCESS read-only
    STATUS current
    DESCRIPTION
    "The remote IP address of the BGP peer."
    ::= { bgpCurCfgPeerEntry 2 }

bgpCurCfgPeerRemoteAs OBJECT-TYPE
    SYNTAX INTEGER (1..65535)
    MAX-ACCESS read-only
    STATUS current
    DESCRIPTION
    "The remote AS number of the BGP peer.  0 means none" 
    ::= { bgpCurCfgPeerEntry 3 }

bgpCurCfgPeerTtl OBJECT-TYPE
    SYNTAX INTEGER (0..255)
    MAX-ACCESS read-only
    STATUS current
    DESCRIPTION
        "The time-to-live value of the BGP peer IP datagram. 0 means none."
    ::= { bgpCurCfgPeerEntry 4 }

bgpCurCfgPeerState OBJECT-TYPE
    SYNTAX INTEGER { 
        enabled(1),
        disabled(2)
    }
    MAX-ACCESS  read-only
    STATUS  current  
    DESCRIPTION
    "Enable or disable the peer."
    ::= { bgpCurCfgPeerEntry 5 }

bgpCurCfgPeerMetric OBJECT-TYPE
    SYNTAX Unsigned32 (0..4294967294) 
    MAX-ACCESS read-only
    STATUS current
    DESCRIPTION
    "The metric value of the BGP peer.  A value of '0' means none" 
    ::= { bgpCurCfgPeerEntry 10 }

bgpCurCfgPeerDefaultAction OBJECT-TYPE
    SYNTAX INTEGER { 
        none(1),
        import(2),
    originate(3),
    redistribute(4)
    }
    MAX-ACCESS  read-only
    STATUS  current  
    DESCRIPTION
    "The value of default route action."
    ::= { bgpCurCfgPeerEntry 11 }

bgpCurCfgPeerOspfState OBJECT-TYPE
    SYNTAX INTEGER { 
        enabled(1),
        disabled(2)
    }
    MAX-ACCESS  read-only
    STATUS  current  
    DESCRIPTION
    "Enable or disable advertising OSPF routes."
    ::= { bgpCurCfgPeerEntry 12 }

bgpCurCfgPeerFixedState OBJECT-TYPE
    SYNTAX INTEGER { 
        enabled(1),
        disabled(2)
    }
    MAX-ACCESS  read-only
    STATUS  current  
    DESCRIPTION
    "Enable or disable advertising fixed routes."
    ::= { bgpCurCfgPeerEntry 13 }

bgpCurCfgPeerStaticState OBJECT-TYPE
    SYNTAX INTEGER { 
        enabled(1),
        disabled(2)
    }
    MAX-ACCESS  read-only
    STATUS  current  
    DESCRIPTION
    "Enable or disable advertising static routes."
    ::= { bgpCurCfgPeerEntry 14 }


bgpCurCfgPeerInRmapList OBJECT-TYPE
    SYNTAX OCTET STRING
    MAX-ACCESS read-only
    STATUS current
    DESCRIPTION
        "The route maps present in the in route map list. 
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected"
    ::= { bgpCurCfgPeerEntry 16 }

bgpCurCfgPeerOutRmapList OBJECT-TYPE
    SYNTAX OCTET STRING
    MAX-ACCESS read-only
    STATUS current
    DESCRIPTION
        "The route maps present in the out route map list. 
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected"
    ::= { bgpCurCfgPeerEntry 17 }

bgpCurCfgPeerHold OBJECT-TYPE
    SYNTAX INTEGER (0..65535) 
    MAX-ACCESS  read-only
    STATUS  current
    DESCRIPTION
    "The hold time"    
    ::= { bgpCurCfgPeerEntry 18 }

bgpCurCfgPeerAlive OBJECT-TYPE
    SYNTAX INTEGER (0..21845)
    MAX-ACCESS  read-only
    STATUS  current
    DESCRIPTION
        "The keep alive time"
    ::= { bgpCurCfgPeerEntry 19 }

bgpCurCfgPeerAdvert OBJECT-TYPE
    SYNTAX INTEGER (1..65535)
    MAX-ACCESS read-only
    STATUS current
    DESCRIPTION
        "The min time between advertisements"
    ::= { bgpCurCfgPeerEntry 20 }

bgpCurCfgPeerRetry OBJECT-TYPE
    SYNTAX INTEGER (1..65535)
    MAX-ACCESS read-only
    STATUS current
    DESCRIPTION
    "The connect retry interval"
    ::= { bgpCurCfgPeerEntry 21 }

bgpCurCfgPeerOrig OBJECT-TYPE
    SYNTAX INTEGER (1..65535)
    MAX-ACCESS read-only
    STATUS current
    DESCRIPTION
        "The min time between route originations"
    ::= { bgpCurCfgPeerEntry 22 }

bgpCurCfgPeerRipState OBJECT-TYPE
    SYNTAX INTEGER {
        enabled(1),
        disabled(2)
        }
    MAX-ACCESS read-only
    STATUS current
    DESCRIPTION
    "Enable/disable advertising RIP routes"
    ::= { bgpCurCfgPeerEntry 23 }

bgpCurCfgPeerPassword OBJECT-TYPE
    SYNTAX DisplayString (SIZE(0..16)) 
    MAX-ACCESS read-only
    STATUS current
    DESCRIPTION
    "Peer BGP password"
    ::= { bgpCurCfgPeerEntry 24 }

    bgpCurCfgPeerPassive OBJECT-TYPE  
    SYNTAX INTEGER {
        enabled(1),
        disabled(2)
        }
    MAX-ACCESS read-only
    STATUS current
    DESCRIPTION
    "Enable/disable BGP passive peer"
    ::= { bgpCurCfgPeerEntry 25 }

bgpCurCfgPeerUpdateSrcIf OBJECT-TYPE
    SYNTAX INTEGER 
    MAX-ACCESS read-only
    STATUS current
    DESCRIPTION
        "BGP peer update source interface index"
    ::= { bgpCurCfgPeerEntry 30 }

bgpCurCfgPeerUpdateSrcLoopIf OBJECT-TYPE
    SYNTAX INTEGER
    MAX-ACCESS read-only
    STATUS current
    DESCRIPTION
        "BGP peer update source loopback interface index"
    ::= { bgpCurCfgPeerEntry 31 }

bgpCurCfgPeerTtlSecHops OBJECT-TYPE
    SYNTAX INTEGER (0..254)
    MAX-ACCESS read-only
    STATUS current
    DESCRIPTION
        "The BGP ttl security hops. 0 means none."
    ::= { bgpCurCfgPeerEntry 32 }

    bgpCurCfgPeerNexthopSelf OBJECT-TYPE  
    SYNTAX INTEGER {
        enabled(1),
        disabled(2)
        }
    MAX-ACCESS read-only
    STATUS current
    DESCRIPTION
	"Enable/Disable using this router as next-hop in BGP updates."
    ::= { bgpCurCfgPeerEntry 33 }
    bgpCurCfgPeerClient OBJECT-TYPE  
    SYNTAX INTEGER {
        enabled(1),
        disabled(2)
        }
    MAX-ACCESS read-only
    STATUS current
    DESCRIPTION
	"Enable/disable BGP client peer"
    ::= { bgpCurCfgPeerEntry 34 }

bgpNewCfgPeerTable OBJECT-TYPE
    SYNTAX SEQUENCE OF BgpNewCfgPeerEntry
    MAX-ACCESS not-accessible
    STATUS current
    DESCRIPTION
      "The table of BGP peer in the new configuration block."
    ::= { bgpCfg 4 }

bgpNewCfgPeerEntry OBJECT-TYPE
    SYNTAX BgpNewCfgPeerEntry
    MAX-ACCESS not-accessible
    STATUS current
    DESCRIPTION
      "Information about a BGP peer."
    INDEX { bgpNewCfgPeerIndex }
    ::= { bgpNewCfgPeerTable 1 }
 
BgpNewCfgPeerEntry ::= SEQUENCE {
    bgpNewCfgPeerIndex      Integer32,
    bgpNewCfgPeerRemoteAddr IpAddress,
    bgpNewCfgPeerRemoteAs   INTEGER,
    bgpNewCfgPeerPassive        INTEGER,
    bgpNewCfgPeerHold       INTEGER,    
    bgpNewCfgPeerAlive      INTEGER,
    bgpNewCfgPeerAdvert     INTEGER,
    bgpNewCfgPeerRetry      INTEGER,
    bgpNewCfgPeerOrig       INTEGER,        
    bgpNewCfgPeerRipState       INTEGER,
    bgpNewCfgPeerTtl        INTEGER,
    bgpNewCfgPeerPassword       DisplayString,
    bgpNewCfgPeerState      INTEGER,
    bgpNewCfgPeerDelete     INTEGER,
    bgpNewCfgPeerMetric     Unsigned32,
    bgpNewCfgPeerDefaultAction  INTEGER,
    bgpNewCfgPeerOspfState  INTEGER,
    bgpNewCfgPeerFixedState     INTEGER,
    bgpNewCfgPeerStaticState    INTEGER,
    bgpNewCfgPeerInRmapList OCTET STRING,
    bgpNewCfgPeerOutRmapList    OCTET STRING,
    bgpNewCfgPeerAddInRmap  Integer32,
    bgpNewCfgPeerAddOutRmap Integer32,
    bgpNewCfgPeerRemoveInRmap   Integer32,
    bgpNewCfgPeerRemoveOutRmap  Integer32
    , bgpNewCfgPeerUpdateSrcIf        INTEGER
    , bgpNewCfgPeerUpdateSrcLoopIf    INTEGER
    , bgpNewCfgPeerTtlSecHops   INTEGER
    ,bgpNewCfgPeerNexthopSelf    INTEGER
    , bgpNewCfgPeerClient             INTEGER
    }
 
bgpNewCfgPeerIndex OBJECT-TYPE
    SYNTAX Integer32
    MAX-ACCESS read-only
    STATUS current
    DESCRIPTION
    "The BGP peer number for which the BGP peer table is related."
    ::= { bgpNewCfgPeerEntry 1}

bgpNewCfgPeerRemoteAddr OBJECT-TYPE
    SYNTAX IpAddress
    MAX-ACCESS read-create
    STATUS current
    DESCRIPTION
    "The remote IP address of the BGP peer." 
    ::= { bgpNewCfgPeerEntry 2 }

bgpNewCfgPeerRemoteAs OBJECT-TYPE
    SYNTAX INTEGER (1..65535) 
    MAX-ACCESS read-create
    STATUS current
    DESCRIPTION
    "The remote AS number of the BGP peer.  0 means none" 
    ::= { bgpNewCfgPeerEntry 3 }

bgpNewCfgPeerTtl OBJECT-TYPE
    SYNTAX INTEGER (0..255)
    MAX-ACCESS read-create
    STATUS current
    DESCRIPTION
        "The time-to-live value of the BGP peer IP datagram. 0 means none."
    ::= { bgpNewCfgPeerEntry 4 }

bgpNewCfgPeerState OBJECT-TYPE
    SYNTAX INTEGER { 
        enabled(1),
        disabled(2)
    }
    MAX-ACCESS  read-create
    STATUS  current  
    DESCRIPTION
    "Enable or disable the peer."
    ::= { bgpNewCfgPeerEntry 5 }

bgpNewCfgPeerDelete OBJECT-TYPE
    SYNTAX INTEGER { 
        other(1),
        delete(2)
        }
    MAX-ACCESS read-create
    STATUS current
    DESCRIPTION
    "When set to the value of 2 (delete), the entire row is deleted. 
     When read, other(1) is returned. Setting the value to anything 
     other than 2(delete) has no effect on the state of the row."
    ::= { bgpNewCfgPeerEntry 6 }

bgpNewCfgPeerMetric OBJECT-TYPE
    SYNTAX Unsigned32 (0..4294967294) 
    MAX-ACCESS read-create
    STATUS current
    DESCRIPTION
    "The metric value of the BGP peer. A value of '0' means none" 
    ::= { bgpNewCfgPeerEntry 10 }

bgpNewCfgPeerDefaultAction OBJECT-TYPE
    SYNTAX INTEGER { 
        none(1),
        import(2),
    originate(3),
    redistribute(4)
    }
    MAX-ACCESS  read-create
    STATUS  current  
    DESCRIPTION
    "The value of default route action."
    ::= { bgpNewCfgPeerEntry 11 }

bgpNewCfgPeerOspfState OBJECT-TYPE
    SYNTAX INTEGER { 
        enabled(1),
        disabled(2)
    }
    MAX-ACCESS  read-create
    STATUS  current  
    DESCRIPTION
    "Enable or disable advertising OSPF routes."
    ::= { bgpNewCfgPeerEntry 12 }

bgpNewCfgPeerFixedState OBJECT-TYPE
    SYNTAX INTEGER { 
        enabled(1),
        disabled(2)
    }
    MAX-ACCESS  read-create
    STATUS  current  
    DESCRIPTION
    "Enable or disable advertising fixed routes."
    ::= { bgpNewCfgPeerEntry 13 }

bgpNewCfgPeerStaticState OBJECT-TYPE
    SYNTAX INTEGER { 
        enabled(1),
        disabled(2)
    }
    MAX-ACCESS  read-create
    STATUS  current  
    DESCRIPTION
    "Enable or disable advertising static routes."
    ::= { bgpNewCfgPeerEntry 14 }


bgpNewCfgPeerInRmapList OBJECT-TYPE
    SYNTAX OCTET STRING
    MAX-ACCESS read-only
    STATUS current
    DESCRIPTION
        "The route maps present in the in route map list. 
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected"
    ::= { bgpNewCfgPeerEntry 16 }

bgpNewCfgPeerOutRmapList OBJECT-TYPE
    SYNTAX OCTET STRING
    MAX-ACCESS read-only
    STATUS current
    DESCRIPTION
        "The route maps present in the out route map list. 
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected"
    ::= { bgpNewCfgPeerEntry 17 }

bgpNewCfgPeerAddInRmap OBJECT-TYPE
    SYNTAX Integer32 
    MAX-ACCESS  read-create
    STATUS  current  
    DESCRIPTION
    "The route map to be add into in-rmap list. When read,
     0 is returned."
    ::= { bgpNewCfgPeerEntry 18 }

bgpNewCfgPeerAddOutRmap OBJECT-TYPE
    SYNTAX Integer32 
    MAX-ACCESS  read-create
    STATUS  current  
    DESCRIPTION
    "The route map to be add into out-rmap list. When read,
     0 is returned."
    ::= { bgpNewCfgPeerEntry 19 }

bgpNewCfgPeerRemoveInRmap OBJECT-TYPE
    SYNTAX Integer32 
    MAX-ACCESS  read-create
    STATUS  current  
    DESCRIPTION
    "The route map to be removed from out-rmap list. When read,
     0 is returned."
    ::= { bgpNewCfgPeerEntry 20 }

bgpNewCfgPeerRemoveOutRmap OBJECT-TYPE
    SYNTAX Integer32 
    MAX-ACCESS  read-create
    STATUS  current  
    DESCRIPTION
    "The route map to be removed from out-rmap list. When read,
     0 is returned."
    ::= { bgpNewCfgPeerEntry 21 }

bgpNewCfgPeerHold OBJECT-TYPE
    SYNTAX INTEGER (0..65535)
    MAX-ACCESS read-create
    STATUS current
    DESCRIPTION
        "The hold time"
    ::= { bgpNewCfgPeerEntry 22 }

bgpNewCfgPeerAlive OBJECT-TYPE
    SYNTAX INTEGER (0..21845)
    MAX-ACCESS read-create
    STATUS current
    DESCRIPTION
        "The keep alive time"
    ::= { bgpNewCfgPeerEntry 23 }

bgpNewCfgPeerAdvert OBJECT-TYPE
    SYNTAX INTEGER (1..65535)
    MAX-ACCESS read-create
    STATUS current
    DESCRIPTION
        "The min time between advertisements"
    ::= { bgpNewCfgPeerEntry 24 }

bgpNewCfgPeerRetry OBJECT-TYPE
    SYNTAX INTEGER (1..65535)
    MAX-ACCESS read-create
    STATUS current
    DESCRIPTION
    "The connect retry interval"
    ::= { bgpNewCfgPeerEntry 25 } 

bgpNewCfgPeerOrig OBJECT-TYPE
    SYNTAX INTEGER (1..65535)
    MAX-ACCESS read-create
    STATUS current
    DESCRIPTION
        "The min time between route originations"
    ::= { bgpNewCfgPeerEntry 26 }

bgpNewCfgPeerRipState OBJECT-TYPE
    SYNTAX INTEGER {
        enabled(1),
        disabled(2)
        }
    MAX-ACCESS read-create
    STATUS current
    DESCRIPTION
    "Enable/disable advertising RIP routes"
    ::= { bgpNewCfgPeerEntry 27 }

bgpNewCfgPeerPassword OBJECT-TYPE
    SYNTAX DisplayString (SIZE(0..16))
    MAX-ACCESS read-create
    STATUS current
    DESCRIPTION
        "Peer BGP password"
    ::= { bgpNewCfgPeerEntry 28 }

bgpNewCfgPeerPassive OBJECT-TYPE  
    SYNTAX INTEGER {
        enabled(1),
        disabled(2)
        }
    MAX-ACCESS read-create
    STATUS current
    DESCRIPTION
    "Enable/disable BGP passive peer"
    ::= { bgpNewCfgPeerEntry 29 }

bgpNewCfgPeerUpdateSrcIf OBJECT-TYPE
    SYNTAX INTEGER
    MAX-ACCESS read-create
    STATUS current
    DESCRIPTION
        "BGP peer update source interface index"
    ::= { bgpNewCfgPeerEntry 30 }

bgpNewCfgPeerUpdateSrcLoopIf OBJECT-TYPE
    SYNTAX INTEGER
    MAX-ACCESS read-create
    STATUS current
    DESCRIPTION
        "BGP peer update source loopback interface index"
    ::= { bgpNewCfgPeerEntry 31 }

bgpNewCfgPeerTtlSecHops OBJECT-TYPE
    SYNTAX INTEGER (0..254)
    MAX-ACCESS read-create
    STATUS current
    DESCRIPTION
        "The BGP ttl security hops. 0 means none."
    ::= { bgpNewCfgPeerEntry 32 }
bgpNewCfgPeerNexthopSelf OBJECT-TYPE  
    SYNTAX INTEGER {
        enabled(1),
        disabled(2)
        }
    MAX-ACCESS read-create
    STATUS current
    DESCRIPTION
	"Enable/Disable using this router as next-hop in BGP updates."
    ::= { bgpNewCfgPeerEntry 33 }
bgpNewCfgPeerClient OBJECT-TYPE  
    SYNTAX INTEGER {
        enabled(1),
        disabled(2)
        }
    MAX-ACCESS read-create
    STATUS current
    DESCRIPTION
	"Enable/disable BGP client peer"
    ::= { bgpNewCfgPeerEntry 34 }

--
-- BGP Aggregation Table
--
bgpAggrTableMax OBJECT-TYPE
    SYNTAX Integer32
    MAX-ACCESS read-only
    STATUS current
    DESCRIPTION
    "The maximum number of rows in the BGP aggregation table."
    ::= { bgpCfg 5 }

bgpCurCfgAggrTable OBJECT-TYPE
    SYNTAX SEQUENCE OF BgpCurCfgAggrEntry
    MAX-ACCESS not-accessible
    STATUS current
    DESCRIPTION
      "The table of BGP aggregation configuration."
    ::= { bgpCfg 6 }

bgpCurCfgAggrEntry OBJECT-TYPE
    SYNTAX BgpCurCfgAggrEntry
    MAX-ACCESS not-accessible
    STATUS current
    DESCRIPTION
      "Information about a BGP aggregation."
    INDEX { bgpCurCfgAggrIndex }
    ::= { bgpCurCfgAggrTable 1 }
 
BgpCurCfgAggrEntry ::= SEQUENCE {
    bgpCurCfgAggrIndex     Integer32,
    bgpCurCfgAggrAddr      IpAddress,
    bgpCurCfgAggrMask      IpAddress,
    bgpCurCfgAggrState     INTEGER
    }
 
bgpCurCfgAggrIndex OBJECT-TYPE
    SYNTAX Integer32
    MAX-ACCESS read-only
    STATUS current
    DESCRIPTION
    "The aggregation number for which the BGP aggregation is related."
    ::= { bgpCurCfgAggrEntry 1}

bgpCurCfgAggrAddr OBJECT-TYPE
    SYNTAX IpAddress
    MAX-ACCESS read-only
    STATUS current
    DESCRIPTION
    "The IP address of the BGP aggregation."
    ::= { bgpCurCfgAggrEntry 2 }

bgpCurCfgAggrMask OBJECT-TYPE
    SYNTAX IpAddress
    MAX-ACCESS read-only
    STATUS current  
    DESCRIPTION
    "The subnet mask of the BGP aggregation."
    ::= { bgpCurCfgAggrEntry 3 }

bgpCurCfgAggrState OBJECT-TYPE
    SYNTAX INTEGER { 
        enabled(1),
        disabled(2)
    }
    MAX-ACCESS  read-only
    STATUS  current  
    DESCRIPTION
    "Enable or disable the BGP aggregation."
    ::= { bgpCurCfgAggrEntry 4 }

bgpNewCfgAggrTable OBJECT-TYPE
    SYNTAX SEQUENCE OF BgpNewCfgAggrEntry
    MAX-ACCESS not-accessible
    STATUS current
    DESCRIPTION
      "The table of BGP aggregation configuration."
    ::= { bgpCfg 7 }

bgpNewCfgAggrEntry OBJECT-TYPE
    SYNTAX BgpNewCfgAggrEntry
    MAX-ACCESS not-accessible
    STATUS current
    DESCRIPTION
      "Information about an BGP aggregation."
    INDEX { bgpNewCfgAggrIndex }
    ::= { bgpNewCfgAggrTable 1 }
 
BgpNewCfgAggrEntry ::= SEQUENCE {
    bgpNewCfgAggrIndex     Integer32,
    bgpNewCfgAggrAddr      IpAddress,
    bgpNewCfgAggrMask      IpAddress,
    bgpNewCfgAggrState     INTEGER,
    bgpNewCfgAggrDelete    INTEGER
    }
 
bgpNewCfgAggrIndex OBJECT-TYPE
    SYNTAX Integer32
    MAX-ACCESS read-only
    STATUS current
    DESCRIPTION
    "The aggregation number for which the BGP aggregation is related."
    ::= { bgpNewCfgAggrEntry 1}

bgpNewCfgAggrAddr OBJECT-TYPE
    SYNTAX IpAddress
    MAX-ACCESS read-create
    STATUS current
    DESCRIPTION
    "The IP address of the BGP aggregation."
    ::= { bgpNewCfgAggrEntry 2 }

bgpNewCfgAggrMask OBJECT-TYPE
    SYNTAX IpAddress
    MAX-ACCESS read-create
    STATUS current  
    DESCRIPTION
    "The subnet mask of the BGP aggregation."
    ::= { bgpNewCfgAggrEntry 3 }

bgpNewCfgAggrState OBJECT-TYPE
    SYNTAX INTEGER { 
        enabled(1),
        disabled(2)
    }
    MAX-ACCESS  read-create
    STATUS  current  
    DESCRIPTION
    "Enable or disable the BGP aggregation."
    ::= { bgpNewCfgAggrEntry 4 }

bgpNewCfgAggrDelete OBJECT-TYPE
    SYNTAX INTEGER { 
        other(1),
        delete(2)
        }
    MAX-ACCESS read-create
    STATUS current
    DESCRIPTION
    "When set to the value of 2 (delete), the entire row is deleted. 
     When read, other(1) is returned. Setting the value to anything 
     other than 2(delete) has no effect on the state of the row."
    ::= { bgpNewCfgAggrEntry 5 }

bgpGroupTableMax OBJECT-TYPE
    SYNTAX      Integer32
    MAX-ACCESS  read-only
    STATUS      current
    DESCRIPTION
    "The maximum number of groups in the BGP groups table."
    ::= { bgpCfg 8 }

bgpCurCfgGroupTable OBJECT-TYPE
    SYNTAX SEQUENCE OF BgpCurCfgGroupEntry
    MAX-ACCESS      not-accessible
    STATUS          current
    DESCRIPTION
    "The table of BGP group in the current configuration block."
    ::= { bgpCfg 9 }

bgpCurCfgGroupEntry OBJECT-TYPE
    SYNTAX      BgpCurCfgGroupEntry
    MAX-ACCESS  not-accessible
    STATUS      current
    DESCRIPTION
    "Information about a BGP group."
    INDEX { bgpCurCfgGroupIndex }
    ::= { bgpCurCfgGroupTable 1 }

BgpCurCfgGroupEntry ::= SEQUENCE {
    bgpCurCfgGroupIndex         Integer32,
    bgpCurCfgGroupName          DisplayString,
    bgpCurCfgGroupRemoteAddr    IpAddress,
    bgpCurCfgGroupRemoteMask    IpAddress,
    bgpCurCfgGroupLimit         INTEGER,
    bgpCurCfgGroupUpdateSrcIf   INTEGER,
    bgpCurCfgGroupUpdateSrcLoopIf INTEGER,
    bgpCurCfgGroupHold          INTEGER,
    bgpCurCfgGroupAlive         INTEGER,
    bgpCurCfgGroupAdvert        INTEGER,
    bgpCurCfgGroupOrig          INTEGER,
    bgpCurCfgGroupMetric        Unsigned32,
    bgpCurCfgGroupTtl           INTEGER,
    bgpCurCfgGroupDefaultAction INTEGER,
    bgpCurCfgGroupOspfState     INTEGER,
    bgpCurCfgGroupRipState      INTEGER,
    bgpCurCfgGroupFixedState    INTEGER,
    bgpCurCfgGroupStaticState   INTEGER,
    bgpCurCfgGroupInRmapList    OCTET STRING,
    bgpCurCfgGroupOutRmapList   OCTET STRING,
    bgpCurCfgGroupPassword      DisplayString,
    bgpCurCfgGroupState         INTEGER
    , bgpCurCfgGroupTtlSecHops  INTEGER
    ,bgpCurCfgGroupNexthopSelf  INTEGER
    , bgpCurCfgGroupClient      INTEGER
    } 

bgpCurCfgGroupIndex OBJECT-TYPE
    SYNTAX      Integer32
    MAX-ACCESS  read-only
    STATUS      current
    DESCRIPTION
    "The BGP group number for which the BGP group table is related."
    ::= { bgpCurCfgGroupEntry 1 }

bgpCurCfgGroupName OBJECT-TYPE
    SYNTAX          DisplayString (SIZE(0..32))
    MAX-ACCESS      read-only
    STATUS          current
    DESCRIPTION
    "The group name."
    ::= { bgpCurCfgGroupEntry 2 }

bgpCurCfgGroupRemoteAddr OBJECT-TYPE
    SYNTAX      IpAddress
    MAX-ACCESS  read-only
    STATUS      current
    DESCRIPTION
    "The IP address of the BGP group."
    ::= { bgpCurCfgGroupEntry 3 }

bgpCurCfgGroupRemoteMask OBJECT-TYPE
    SYNTAX      IpAddress
    MAX-ACCESS  read-only
    STATUS      current
    DESCRIPTION
    "The subnet mask of the BGP group."
    ::= { bgpCurCfgGroupEntry 4 }
  
bgpCurCfgGroupLimit OBJECT-TYPE
    SYNTAX      INTEGER (1..96)
    MAX-ACCESS  read-only
    STATUS      current
    DESCRIPTION
    " The maximum number of BGP dynamic peers."
    ::= { bgpCurCfgGroupEntry 5 }

bgpCurCfgGroupUpdateSrcIf OBJECT-TYPE
    SYNTAX INTEGER
    MAX-ACCESS read-only
    STATUS current
    DESCRIPTION
        "BGP group update source interface index"
    ::= { bgpCurCfgGroupEntry 6 }

bgpCurCfgGroupUpdateSrcLoopIf OBJECT-TYPE
    SYNTAX INTEGER
    MAX-ACCESS read-only
    STATUS current
    DESCRIPTION
        "BGP group update source loopback interface index"
    ::= { bgpCurCfgGroupEntry 7 }

bgpCurCfgGroupHold OBJECT-TYPE
    SYNTAX      INTEGER (0..65535)
    MAX-ACCESS  read-only
    STATUS      current
    DESCRIPTION
    "The hold time"
    ::= { bgpCurCfgGroupEntry 8 }

bgpCurCfgGroupAlive OBJECT-TYPE
    SYNTAX INTEGER  (0..21845)
    MAX-ACCESS      read-only
    STATUS          current
    DESCRIPTION
    "The keep alive time"
    ::= { bgpCurCfgGroupEntry 9 }

bgpCurCfgGroupAdvert OBJECT-TYPE
    SYNTAX INTEGER  (1..65535)
    MAX-ACCESS      read-only
    STATUS          current
    DESCRIPTION
    "The min time between advertisements"
    ::= { bgpCurCfgGroupEntry 10 }

bgpCurCfgGroupOrig OBJECT-TYPE
    SYNTAX INTEGER  (1..65535)
    MAX-ACCESS      read-only
    STATUS          current
    DESCRIPTION
    "The min time between route originations"
    ::= { bgpCurCfgGroupEntry 11 }

bgpCurCfgGroupMetric OBJECT-TYPE
    SYNTAX      Unsigned32 (0..4294967294)
    MAX-ACCESS  read-only
    STATUS      current
    DESCRIPTION
    "The metric value of the BGP group.  A value of '0' means none"
    ::= { bgpCurCfgGroupEntry 12 }

bgpCurCfgGroupTtl OBJECT-TYPE
    SYNTAX      INTEGER (0..255)
    MAX-ACCESS  read-only
    STATUS      current
    DESCRIPTION
    "The time-to-live value of the BGP peer IP datagram. 0 means none."
    ::= { bgpCurCfgGroupEntry 13 }

bgpCurCfgGroupDefaultAction OBJECT-TYPE
    SYNTAX INTEGER {
        none(1),
        import(2),
        originate(3),
        redistribute(4)
        }
    MAX-ACCESS      read-only
    STATUS          current
    DESCRIPTION
    "The value of default route action."
    ::= { bgpCurCfgGroupEntry 14 }

bgpCurCfgGroupOspfState OBJECT-TYPE
    SYNTAX INTEGER {
        enabled(1),
        disabled(2)
        }
    MAX-ACCESS      read-only
    STATUS          current
    DESCRIPTION
    "Enable or disable advertising OSPF routes."
    ::= { bgpCurCfgGroupEntry 15 }

bgpCurCfgGroupRipState OBJECT-TYPE
    SYNTAX INTEGER {
        enabled(1),
        disabled(2)
        }
    MAX-ACCESS      read-only
    STATUS          current
    DESCRIPTION
    "Enable/disable advertising RIP routes"
    ::= { bgpCurCfgGroupEntry 16 }

bgpCurCfgGroupFixedState OBJECT-TYPE
    SYNTAX INTEGER {
        enabled(1),
        disabled(2)
        }
    MAX-ACCESS      read-only
    STATUS          current
    DESCRIPTION    
    "Enable or disable advertising fixed routes."
    ::= { bgpCurCfgGroupEntry 17 }

bgpCurCfgGroupStaticState OBJECT-TYPE
    SYNTAX INTEGER {
        enabled(1),
        disabled(2)
        }
    MAX-ACCESS      read-only
    STATUS          current
    DESCRIPTION
    "Enable or disable advertising static routes."
    ::= { bgpCurCfgGroupEntry 18 }

bgpCurCfgGroupInRmapList OBJECT-TYPE
    SYNTAX      OCTET STRING
    MAX-ACCESS  read-only
    STATUS      current
    DESCRIPTION
    "The route maps present in the in route map list.
     The route maps are presented in a bitmap format.

     in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

     where x :  1 - The represented route map is selected
                0 - The represented route map is not selected"
    ::= { bgpCurCfgGroupEntry 19 }

bgpCurCfgGroupOutRmapList OBJECT-TYPE
    SYNTAX      OCTET STRING
    MAX-ACCESS  read-only
    STATUS      current
    DESCRIPTION
    "The route maps present in the out route map list.
     The route maps are presented in a bitmap format.

     in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

     where x :  1 - The represented route map is selected
                0 - The represented route map is not selected"
    ::= { bgpCurCfgGroupEntry 20 }

bgpCurCfgGroupPassword OBJECT-TYPE
    SYNTAX      DisplayString (SIZE(0..16))
    MAX-ACCESS  read-only
    STATUS      current
    DESCRIPTION
    "Peer BGP password"
    ::= { bgpCurCfgGroupEntry 21 }

bgpCurCfgGroupState OBJECT-TYPE
    SYNTAX INTEGER {
        enabled(1),
        disabled(2)
        }
    MAX-ACCESS  read-only
    STATUS      current
    DESCRIPTION
    "Enable or disable the group."
    ::= { bgpCurCfgGroupEntry 22 }

bgpCurCfgGroupTtlSecHops OBJECT-TYPE
    SYNTAX      INTEGER (0..254)
    MAX-ACCESS  read-only
    STATUS      current
    DESCRIPTION
    "The BGP ttl security hops. 0 means none."
    ::= { bgpCurCfgGroupEntry 23 }

    bgpCurCfgGroupNexthopSelf OBJECT-TYPE  
    SYNTAX INTEGER {
        enabled(1),
        disabled(2)
        }
    MAX-ACCESS read-only
    STATUS current
    DESCRIPTION
	"Enable/Disable using this router as next-hop in BGP updates."
    ::= { bgpCurCfgGroupEntry 24 }

    bgpCurCfgGroupClient OBJECT-TYPE  
    SYNTAX INTEGER {
        enabled(1),
        disabled(2)
        }
    MAX-ACCESS read-only
    STATUS current
    DESCRIPTION
	"Enable/Disable Route Reflector for this client."
    ::= { bgpCurCfgGroupEntry 25 }


bgpNewCfgGroupTable OBJECT-TYPE
    SYNTAX SEQUENCE OF BgpNewCfgGroupEntry
    MAX-ACCESS      not-accessible
    STATUS          current
    DESCRIPTION
    "The table of BGP group in the new configuration block."
    ::= { bgpCfg 10 }

bgpNewCfgGroupEntry OBJECT-TYPE
    SYNTAX      BgpNewCfgGroupEntry
    MAX-ACCESS  not-accessible
    STATUS      current
    DESCRIPTION
    "Information about a BGP group."
    INDEX { bgpNewCfgGroupIndex }
    ::= { bgpNewCfgGroupTable 1 }

BgpNewCfgGroupEntry ::= SEQUENCE {
    bgpNewCfgGroupIndex           Integer32,
    bgpNewCfgGroupName            DisplayString,
    bgpNewCfgGroupRemoteAddr      IpAddress,
    bgpNewCfgGroupRemoteMask      IpAddress,
    bgpNewCfgGroupLimit           INTEGER,
    bgpNewCfgGroupUpdateSrcIf     INTEGER,
    bgpNewCfgGroupUpdateSrcLoopIf INTEGER,
    bgpNewCfgGroupHold            INTEGER,
    bgpNewCfgGroupAlive           INTEGER,
    bgpNewCfgGroupAdvert          INTEGER,
    bgpNewCfgGroupOrig            INTEGER,
    bgpNewCfgGroupMetric          Unsigned32,
    bgpNewCfgGroupTtl             INTEGER,
    bgpNewCfgGroupDefaultAction   INTEGER,
    bgpNewCfgGroupOspfState       INTEGER,
    bgpNewCfgGroupRipState        INTEGER,
    bgpNewCfgGroupFixedState      INTEGER,
    bgpNewCfgGroupStaticState     INTEGER,
    bgpNewCfgGroupInRmapList      OCTET STRING,
    bgpNewCfgGroupOutRmapList     OCTET STRING,
    bgpNewCfgGroupAddInRmap       Integer32,
    bgpNewCfgGroupAddOutRmap      Integer32,
    bgpNewCfgGroupRemoveInRmap    Integer32,
    bgpNewCfgGroupRemoveOutRmap   Integer32,
    bgpNewCfgGroupPassword        DisplayString,
    bgpNewCfgGroupDelete          INTEGER,
    bgpNewCfgGroupState           INTEGER
    , bgpNewCfgGroupTtlSecHops    INTEGER
    , bgpNewCfgGroupNexthopSelf   INTEGER
    , bgpNewCfgGroupClient        INTEGER
    }

bgpNewCfgGroupIndex OBJECT-TYPE
    SYNTAX      Integer32
    MAX-ACCESS  read-create
    STATUS      current
    DESCRIPTION
    "The BGP group number for which the BGP group table is related."
    ::= { bgpNewCfgGroupEntry 1 }

bgpNewCfgGroupName OBJECT-TYPE
    SYNTAX          DisplayString (SIZE(0..32))
    MAX-ACCESS      read-create
    STATUS          current
    DESCRIPTION
    "The group name."
    ::= { bgpNewCfgGroupEntry 2 }

bgpNewCfgGroupRemoteAddr OBJECT-TYPE
    SYNTAX      IpAddress
    MAX-ACCESS  read-create
    STATUS      current
    DESCRIPTION
    "The IP address of the BGP group."
    ::= { bgpNewCfgGroupEntry 3 }

bgpNewCfgGroupRemoteMask OBJECT-TYPE
    SYNTAX      IpAddress
    MAX-ACCESS  read-create
    STATUS      current
    DESCRIPTION
    "The subnet mask of the BGP group."
    ::= { bgpNewCfgGroupEntry 4 }

bgpNewCfgGroupLimit OBJECT-TYPE
    SYNTAX      INTEGER (1..96)
    MAX-ACCESS  read-create
    STATUS      current
    DESCRIPTION
    " The maximum number of BGP dynamic peers."
    ::= { bgpNewCfgGroupEntry 5 }

bgpNewCfgGroupUpdateSrcIf OBJECT-TYPE
    SYNTAX INTEGER
    MAX-ACCESS read-create
    STATUS current
    DESCRIPTION
        "BGP group update source interface index"
    ::= { bgpNewCfgGroupEntry 6 }

bgpNewCfgGroupUpdateSrcLoopIf OBJECT-TYPE
    SYNTAX INTEGER
    MAX-ACCESS read-create
    STATUS current
    DESCRIPTION
        "BGP group update source loopback interface index"
    ::= { bgpNewCfgGroupEntry 7 }

bgpNewCfgGroupHold OBJECT-TYPE
    SYNTAX      INTEGER (0..65535)
    MAX-ACCESS  read-create
    STATUS      current
    DESCRIPTION
        "The hold time"
    ::= { bgpNewCfgGroupEntry 8 }

bgpNewCfgGroupAlive OBJECT-TYPE
    SYNTAX INTEGER  (0..21845)
    MAX-ACCESS      read-create
    STATUS          current
    DESCRIPTION
    "The keep alive time"
    ::= { bgpNewCfgGroupEntry 9 }

bgpNewCfgGroupAdvert OBJECT-TYPE
    SYNTAX INTEGER  (1..65535)
    MAX-ACCESS      read-create
    STATUS          current
    DESCRIPTION
    "The min time between advertisements"
    ::= { bgpNewCfgGroupEntry 10 }

bgpNewCfgGroupOrig OBJECT-TYPE
    SYNTAX INTEGER  (1..65535)
    MAX-ACCESS      read-create
    STATUS          current
    DESCRIPTION
    "The min time between route originations"
    ::= { bgpNewCfgGroupEntry 11 }

bgpNewCfgGroupMetric OBJECT-TYPE
    SYNTAX      Unsigned32 (0..4294967294)
    MAX-ACCESS  read-create
    STATUS      current
    DESCRIPTION
    "The metric value of the BGP group.  A value of '0' means none"
    ::= { bgpNewCfgGroupEntry 12 }

bgpNewCfgGroupTtl OBJECT-TYPE
    SYNTAX      INTEGER (0..255)
    MAX-ACCESS  read-create
    STATUS      current
    DESCRIPTION
    "The time-to-live value of the BGP peer IP datagram. 0 means none."
    ::= { bgpNewCfgGroupEntry 13 }

bgpNewCfgGroupDefaultAction OBJECT-TYPE
    SYNTAX INTEGER {
        none(1),
        import(2),
        originate(3),
        redistribute(4)
        }
    MAX-ACCESS      read-create
    STATUS          current
    DESCRIPTION
    "The value of default route action."
    ::= { bgpNewCfgGroupEntry 14 }

bgpNewCfgGroupOspfState OBJECT-TYPE
    SYNTAX INTEGER {
        enabled(1),
        disabled(2)
        }
    MAX-ACCESS      read-create
    STATUS          current
    DESCRIPTION
    "Enable or disable advertising OSPF routes."
    ::= { bgpNewCfgGroupEntry 15 }

bgpNewCfgGroupRipState OBJECT-TYPE
    SYNTAX INTEGER {
        enabled(1),
        disabled(2)
        }
    MAX-ACCESS      read-create
    STATUS          current
    DESCRIPTION
    "Enable/disable advertising RIP routes"
    ::= { bgpNewCfgGroupEntry 16 }

bgpNewCfgGroupFixedState OBJECT-TYPE
    SYNTAX INTEGER {
        enabled(1),
        disabled(2)
        }
    MAX-ACCESS      read-create
    STATUS          current
    DESCRIPTION
    "Enable or disable advertising fixed routes."
    ::= { bgpNewCfgGroupEntry 17 }

bgpNewCfgGroupStaticState OBJECT-TYPE
    SYNTAX INTEGER {
        enabled(1),
        disabled(2)
        }
    MAX-ACCESS      read-create
    STATUS          current
    DESCRIPTION
    "Enable or disable advertising static routes."
    ::= { bgpNewCfgGroupEntry 18 }

bgpNewCfgGroupInRmapList OBJECT-TYPE
    SYNTAX      OCTET STRING
    MAX-ACCESS  read-only
    STATUS      current
    DESCRIPTION
    "The route maps present in the in route map list.
     The route maps are presented in a bitmap format.

     in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

     where x :  1 - The represented route map is selected
                0 - The represented route map is not selected"
    ::= { bgpNewCfgGroupEntry 19 }

bgpNewCfgGroupOutRmapList OBJECT-TYPE
    SYNTAX      OCTET STRING
    MAX-ACCESS  read-only
    STATUS      current
    DESCRIPTION
    "The route maps present in the out route map list.
     The route maps are presented in a bitmap format.

     in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

     where x :  1 - The represented route map is selected
                0 - The represented route map is not selected"
    ::= { bgpNewCfgGroupEntry 20 }

bgpNewCfgGroupAddInRmap OBJECT-TYPE
    SYNTAX      Integer32
    MAX-ACCESS  read-create
    STATUS      current
    DESCRIPTION
    "The route map to be add into in-rmap list. When read,
     0 is returned."
    ::= { bgpNewCfgGroupEntry 21 }

bgpNewCfgGroupAddOutRmap OBJECT-TYPE
    SYNTAX      Integer32
    MAX-ACCESS  read-create
    STATUS      current
    DESCRIPTION
    "The route map to be add into out-rmap list. When read,
     0 is returned."
    ::= { bgpNewCfgGroupEntry 22 }

bgpNewCfgGroupRemoveInRmap OBJECT-TYPE
    SYNTAX      Integer32
    MAX-ACCESS  read-create
    STATUS      current
    DESCRIPTION
    "The route map to be removed from out-rmap list. When read,
     0 is returned."
    ::= { bgpNewCfgGroupEntry 23 }

bgpNewCfgGroupRemoveOutRmap OBJECT-TYPE
    SYNTAX      Integer32
    MAX-ACCESS  read-create
    STATUS      current
    DESCRIPTION
    "The route map to be removed from out-rmap list. When read,
     0 is returned."
    ::= { bgpNewCfgGroupEntry 24 }

bgpNewCfgGroupPassword OBJECT-TYPE
    SYNTAX      DisplayString (SIZE(0..16))
    MAX-ACCESS  read-create
    STATUS      current
    DESCRIPTION
    "Peer BGP password"
    ::= { bgpNewCfgGroupEntry 25 }


bgpNewCfgGroupDelete OBJECT-TYPE
    SYNTAX INTEGER {
        other(1),
        delete(2)
        }
    MAX-ACCESS  read-create
    STATUS      current
    DESCRIPTION
    "When set to the value of 2 (delete), the entire row is deleted.
     When read, other(1) is returned. Setting the value to anything
     other than 2(delete) has no effect on the state of the row."
    ::= { bgpNewCfgGroupEntry 26 }

bgpNewCfgGroupState OBJECT-TYPE
    SYNTAX INTEGER {
        enabled(1),
        disabled(2)
        }
    MAX-ACCESS      read-create
    STATUS          current
    DESCRIPTION
    "Enable or disable the group."
    ::= { bgpNewCfgGroupEntry 27 }

bgpNewCfgGroupTtlSecHops OBJECT-TYPE
    SYNTAX      INTEGER (0..254)
    MAX-ACCESS  read-create
    STATUS      current
    DESCRIPTION
    "The BGP ttl security hops. 0 means none."
    ::= { bgpNewCfgGroupEntry 28 }

bgpNewCfgGroupNexthopSelf OBJECT-TYPE
    SYNTAX INTEGER {
        enabled(1),
        disabled(2)
        }
    MAX-ACCESS read-create
    STATUS current
    DESCRIPTION
    "Enable/Disable using this router as next-hop in BGP updates."
    ::= { bgpNewCfgGroupEntry 29 }

bgpNewCfgGroupClient OBJECT-TYPE
    SYNTAX INTEGER {
        enabled(1),
        disabled(2)
        }
    MAX-ACCESS read-create
    STATUS current
    DESCRIPTION
    "Enable/Disable Route Reflector for this client."
    ::= { bgpNewCfgGroupEntry 30 }


bgpCurCfgGroupRASTable OBJECT-TYPE
    SYNTAX SEQUENCE OF BgpCurCfgGroupRASEntry
    MAX-ACCESS      not-accessible
    STATUS          current
    DESCRIPTION
    "The table of BGP group RASs in the current configuration block."
    ::= { bgpCfg 11 }

bgpCurCfgGroupRASEntry OBJECT-TYPE
    SYNTAX      BgpCurCfgGroupRASEntry
    MAX-ACCESS  not-accessible
    STATUS      current
    DESCRIPTION
    "Information about a BGP group RAS."
    INDEX { bgpCurCfgGroupIndex, bgpCurCfgGroupRASIndex }
    ::= { bgpCurCfgGroupRASTable 1 }

BgpCurCfgGroupRASEntry ::= SEQUENCE {
    bgpCurCfgGroupRASIndex      Integer32,
    bgpCurCfgGroupRAS           INTEGER
    } 

bgpCurCfgGroupRASIndex OBJECT-TYPE
    SYNTAX      Integer32
    MAX-ACCESS  read-only
    STATUS      current
    DESCRIPTION
    "The BGP remote-as number for which the BGP RAS table is related."
    ::= { bgpCurCfgGroupRASEntry 1 }

bgpCurCfgGroupRAS OBJECT-TYPE
    SYNTAX INTEGER (0..65535)
    MAX-ACCESS read-only
    STATUS current
    DESCRIPTION
    "The remote AS number of the BGP group bgpCurCfgGroupIndex. 0 means none" 
    ::= { bgpCurCfgGroupRASEntry 2 }

bgpNewCfgGroupRASTable OBJECT-TYPE
    SYNTAX SEQUENCE OF BgpNewCfgGroupRASEntry
    MAX-ACCESS not-accessible
    STATUS current
    DESCRIPTION
      "The table of BGP group RASs in the new configuration block."
    ::= { bgpCfg 12 }

bgpNewCfgGroupRASEntry OBJECT-TYPE
    SYNTAX BgpNewCfgGroupRASEntry
    MAX-ACCESS not-accessible
    STATUS current
    DESCRIPTION
      "Information about a BGP group RAS."
    INDEX { bgpNewCfgGroupIndex, bgpNewCfgGroupRASIndex }
    ::= { bgpNewCfgGroupRASTable 1 }
 
BgpNewCfgGroupRASEntry ::= SEQUENCE {
    bgpNewCfgGroupRASIndex      Integer32,
    bgpNewCfgGroupRAS           INTEGER
}

bgpNewCfgGroupRASIndex OBJECT-TYPE
    SYNTAX Integer32
    MAX-ACCESS read-only
    STATUS current
    DESCRIPTION
    "The BGP group RAS number for which the BGP group RASs table is related."
    ::= { bgpNewCfgGroupRASEntry 1}

bgpNewCfgGroupRAS OBJECT-TYPE
    SYNTAX INTEGER (0..65535) 
    MAX-ACCESS read-create
    STATUS current
    DESCRIPTION
    "The remote AS number of the BGP group bgpNewCfgGroupIndex.  0 means none" 
    ::= { bgpNewCfgGroupRASEntry 2 }

bgpInfoGroupTable OBJECT-TYPE
    SYNTAX SEQUENCE OF BgpInfoGroupEntry
    MAX-ACCESS not-accessible
    STATUS current
    DESCRIPTION
      "The table of BGP group in the current configuration block."
    ::= { bgpInfo 4 }

bgpInfoGroupEntry OBJECT-TYPE
    SYNTAX BgpInfoGroupEntry
    MAX-ACCESS not-accessible
    STATUS current
    DESCRIPTION
      "Information about a BGP group."
    INDEX { bgpInfoGroupIndex }
    ::= { bgpInfoGroupTable 1 }

BgpInfoGroupEntry ::= SEQUENCE {
    bgpInfoGroupIndex               Integer32,
    bgpInfoGroupName                DisplayString,
    bgpInfoGroupRemoteAddr          IpAddress,
    bgpInfoGroupRemoteMask          IpAddress,
    bgpInfoGroupLimit               Integer32,
    bgpInfoGroupPeersNum            Integer32,
    bgpInfoGroupState               INTEGER
    }

bgpInfoGroupIndex OBJECT-TYPE
    SYNTAX Integer32
    MAX-ACCESS read-only
    STATUS current
    DESCRIPTION
        "The BGP group number for which the BGP group table is related."
    ::= { bgpInfoGroupEntry 1 }

bgpInfoGroupName OBJECT-TYPE
    SYNTAX DisplayString
    MAX-ACCESS read-only
    STATUS current
    DESCRIPTION
        "The BGP group nname for which the BGP group table is related."
    ::= { bgpInfoGroupEntry 2 }

bgpInfoGroupRemoteAddr OBJECT-TYPE
    SYNTAX IpAddress
    MAX-ACCESS read-only
    STATUS current
    DESCRIPTION
        "The remote IP address of the BGP group."
    ::= { bgpInfoGroupEntry 3 }

bgpInfoGroupRemoteMask OBJECT-TYPE  
    SYNTAX IpAddress          
    MAX-ACCESS read-only
    STATUS current
    DESCRIPTION
        "The remote mask of the BGP group."
    ::= { bgpInfoGroupEntry 4 }

bgpInfoGroupLimit OBJECT-TYPE
    SYNTAX Integer32
    MAX-ACCESS read-only
    STATUS current
    DESCRIPTION
        "The maximum number of BGP dynamic peers."
    ::= { bgpInfoGroupEntry 5 }

bgpInfoGroupPeersNum OBJECT-TYPE
    SYNTAX Integer32
    MAX-ACCESS read-only
    STATUS current
    DESCRIPTION
        "The total number of BGP dynamic peers."
    ::= { bgpInfoGroupEntry 6 }

bgpInfoGroupState OBJECT-TYPE
    SYNTAX INTEGER {
        enabled(1),
        disabled(2)
        }
    MAX-ACCESS  read-only
    STATUS      current
    DESCRIPTION
        "BGP group state."
    ::= { bgpInfoGroupEntry 7 }

bgpInfoGroupRASTable OBJECT-TYPE
    SYNTAX SEQUENCE OF BgpInfoGroupRASEntry
    MAX-ACCESS not-accessible
    STATUS current
    DESCRIPTION
      "The table of BGP group RASs in the current configuration block."
    ::= { bgpInfo 5 }

bgpInfoGroupRASEntry OBJECT-TYPE
    SYNTAX BgpInfoGroupRASEntry
    MAX-ACCESS not-accessible
    STATUS current
    DESCRIPTION
      "Information about a BGP group RAS."
    INDEX { bgpInfoGroupIndex, bgpInfoGroupRASIndex }
    ::= { bgpInfoGroupRASTable 1 }

BgpInfoGroupRASEntry ::= SEQUENCE {
    bgpInfoGroupRASIndex         Integer32,
    bgpInfoGroupRAS              INTEGER
    }

bgpInfoGroupRASIndex OBJECT-TYPE
    SYNTAX Integer32
    MAX-ACCESS read-only
    STATUS current
    DESCRIPTION
        "The BGP group RAS number for which the BGP group RAS table is related."
    ::= { bgpInfoGroupRASEntry 1 }

bgpInfoGroupRAS OBJECT-TYPE
    SYNTAX INTEGER
    MAX-ACCESS read-only
    STATUS current
    DESCRIPTION
        "The remote AS number of the BGP group bgpInfoGroupIndex."
    ::= { bgpInfoGroupRASEntry 2 }

bgpInfoDynamicPeerTable OBJECT-TYPE
    SYNTAX SEQUENCE OF BgpInfoDynamicPeerEntry
    MAX-ACCESS not-accessible
    STATUS current
    DESCRIPTION
      "The table of BGP dynamic peers."
    ::= { bgpInfo 6 }

bgpInfoDynamicPeerEntry OBJECT-TYPE
    SYNTAX BgpInfoDynamicPeerEntry
    MAX-ACCESS not-accessible
    STATUS current
    DESCRIPTION
      "Information about a BGP dynamic peer."
    INDEX { bgpInfoDynamicPeerIndex }
    ::= { bgpInfoDynamicPeerTable 1 }

BgpInfoDynamicPeerEntry ::= SEQUENCE {
    bgpInfoDynamicPeerIndex               Integer32,
    bgpInfoDynamicPeerRemoteAddr          IpAddress,
    bgpInfoDynamicPeerGroup               Integer32,
    bgpInfoDynamicPeerVersion             Integer32,
    bgpInfoDynamicPeerTtl                 Integer32,
    bgpInfoDynamicPeerRemoteAs            Integer32,
    bgpInfoDynamicPeerRouterId            IpAddress,
    bgpInfoDynamicTotalReceivedPackets    Integer32,
    bgpInfoDynamicTotalSentPackets        Integer32,
    bgpInfoDynamicReceivedUpdates         Integer32,
    bgpInfoDynamicSentUpdates             Integer32,
    bgpInfoDynamicKeepalive               Integer32,
    bgpInfoDynamicHoldtime                Integer32,
    bgpInfoDynamicMinAdvTime              Integer32
    }

bgpInfoDynamicPeerIndex OBJECT-TYPE
    SYNTAX Integer32
    MAX-ACCESS read-only
    STATUS current
    DESCRIPTION
        "The BGP dynamic peer number for which the BGP peer table
         is related."
    ::= { bgpInfoDynamicPeerEntry 1 }

bgpInfoDynamicPeerRemoteAddr OBJECT-TYPE
    SYNTAX IpAddress
    MAX-ACCESS read-only
    STATUS current
    DESCRIPTION
        "The remote IP address of the BGP dynamic peer."
    ::= { bgpInfoDynamicPeerEntry 2 }

bgpInfoDynamicPeerGroup OBJECT-TYPE
    SYNTAX Integer32
    MAX-ACCESS read-only
    STATUS current
    DESCRIPTION
        "The group of BGP dynamic peer."
    ::= { bgpInfoDynamicPeerEntry 3 }

bgpInfoDynamicPeerVersion OBJECT-TYPE
    SYNTAX Integer32
    MAX-ACCESS read-only
    STATUS current
    DESCRIPTION
        "The version negotiated by the BGP dynamic peer."
    ::= { bgpInfoDynamicPeerEntry 4 }

bgpInfoDynamicPeerTtl OBJECT-TYPE
    SYNTAX Integer32
    MAX-ACCESS read-only
    STATUS current
    DESCRIPTION
        "The time-to-live value of the BGP dynamic peer IP datagram."
    ::= { bgpInfoDynamicPeerEntry 5 }

bgpInfoDynamicPeerRemoteAs OBJECT-TYPE
    SYNTAX Integer32
    MAX-ACCESS read-only
    STATUS current
    DESCRIPTION
        "The remote AS number of the BGP dynamic peer."
    ::= { bgpInfoDynamicPeerEntry 6 }

bgpInfoDynamicPeerRouterId OBJECT-TYPE
    SYNTAX IpAddress
    MAX-ACCESS read-only
    STATUS current
    DESCRIPTION
        "The router IP address."
    ::= { bgpInfoDynamicPeerEntry 7 }

bgpInfoDynamicTotalReceivedPackets OBJECT-TYPE
    SYNTAX Integer32
    MAX-ACCESS read-only
    STATUS current
    DESCRIPTION
        "The total number of received packets."
    ::= { bgpInfoDynamicPeerEntry 8 }

bgpInfoDynamicTotalSentPackets OBJECT-TYPE
    SYNTAX Integer32
    MAX-ACCESS read-only
    STATUS current
    DESCRIPTION
        "The total number of sent packets."
    ::= { bgpInfoDynamicPeerEntry 9 }

bgpInfoDynamicReceivedUpdates OBJECT-TYPE
    SYNTAX Integer32
    MAX-ACCESS read-only
    STATUS current
    DESCRIPTION
        "The number of received updates."
    ::= { bgpInfoDynamicPeerEntry 10 }

bgpInfoDynamicSentUpdates OBJECT-TYPE
    SYNTAX Integer32
    MAX-ACCESS read-only
    STATUS current
    DESCRIPTION
        "The number of sent updates."
    ::= { bgpInfoDynamicPeerEntry 11 }

bgpInfoDynamicKeepalive OBJECT-TYPE
    SYNTAX Integer32
    MAX-ACCESS read-only
    STATUS current
    DESCRIPTION
        "The keep alive time."
    ::= { bgpInfoDynamicPeerEntry 12 }

bgpInfoDynamicHoldtime OBJECT-TYPE
    SYNTAX Integer32
    MAX-ACCESS read-only
    STATUS current
    DESCRIPTION
        "The hold time."
    ::= { bgpInfoDynamicPeerEntry 13 }

bgpInfoDynamicMinAdvTime OBJECT-TYPE
    SYNTAX Integer32
    MAX-ACCESS read-only
    STATUS current
    DESCRIPTION
        "The MinAdvTime."
    ::= { bgpInfoDynamicPeerEntry 14 }

--
-- IP OSPF configuration
--
ospfGeneral OBJECT IDENTIFIER ::= { ospfCfg 1 }

ospfCurCfgDefaultRouteMetric OBJECT-TYPE
    SYNTAX INTEGER (0..16777214)
    MAX-ACCESS read-only
    STATUS current
    DESCRIPTION
    "Specify the metric to be assigned."
    ::= { ospfGeneral 1 }

ospfNewCfgDefaultRouteMetric OBJECT-TYPE
    SYNTAX INTEGER (0..16777214)
    MAX-ACCESS read-write
    STATUS current
    DESCRIPTION
    "Specify the metric to be assigned."
    ::= { ospfGeneral 2 }

ospfCurCfgDefaultRouteMetricType OBJECT-TYPE
    SYNTAX INTEGER {
        none(1),
        type1(2),
        type2(3)
        }
    MAX-ACCESS read-only
    STATUS current
    DESCRIPTION
    "Specify the AS External metric type to be assigned."
    ::= { ospfGeneral 3 }

ospfNewCfgDefaultRouteMetricType OBJECT-TYPE
    SYNTAX INTEGER {
        none(1),
        type1(2),
        type2(3)
        }
    MAX-ACCESS read-write
    STATUS current
    DESCRIPTION
    "Specify the AS External metric type to be assigned."
    ::= { ospfGeneral 4 }

ospfIntfTableMaxSize OBJECT-TYPE
    SYNTAX Integer32
    MAX-ACCESS read-only
    STATUS current
    DESCRIPTION
        "The maximum number of rows in the OSPF Interface table."
    ::= { ospfGeneral 5 }

ospfAreaTableMaxSize OBJECT-TYPE
    SYNTAX Integer32
    MAX-ACCESS read-only
    STATUS current
    DESCRIPTION
        "The maximum number of rows in the OSPF Area table."
    ::= { ospfGeneral 6 }

ospfRangeTableMaxSize OBJECT-TYPE
    SYNTAX Integer32
    MAX-ACCESS read-only
    STATUS current
    DESCRIPTION
        "The maximum number of rows in the OSPF Range table."
    ::= { ospfGeneral 7 }

ospfVirtIntfTableMaxSize OBJECT-TYPE
    SYNTAX Integer32
    MAX-ACCESS read-only
    STATUS current
    DESCRIPTION
        "The maximum number of rows in the OSPF Virtual Interface
         table."
    ::= { ospfGeneral 8 }

ospfHostTableMaxSize OBJECT-TYPE
    SYNTAX Integer32
    MAX-ACCESS read-only
    STATUS current
    DESCRIPTION
        "The maximum number of rows in the OSPF Host table."
    ::= { ospfGeneral 9 }

ospfCurCfgState OBJECT-TYPE
    SYNTAX INTEGER {
        on(1),
        off(2)
        }
    MAX-ACCESS read-only
    STATUS current
    DESCRIPTION
    "OSPF global state."
    ::= { ospfGeneral 10 }

ospfNewCfgState OBJECT-TYPE
    SYNTAX INTEGER {
        on(1),
        off(2)
        }
    MAX-ACCESS read-write
    STATUS current
    DESCRIPTION
    "Globally turn OSPF on or off."
    ::= { ospfGeneral 11 }

ospfCurCfgLSDB OBJECT-TYPE
    SYNTAX  Integer32
    MAX-ACCESS read-only
    STATUS current
    DESCRIPTION
    "The LSDB limit for external LSA."
    ::= { ospfGeneral 12 }

ospfNewCfgLSDB OBJECT-TYPE
    SYNTAX  Integer32
    MAX-ACCESS read-write
    STATUS current
    DESCRIPTION
    "Set the LSDB limit for external LSA."
    ::= { ospfGeneral 13 }

ospfCurCfgAreaTable OBJECT-TYPE
    SYNTAX SEQUENCE OF OspfCurCfgAreaEntry
    MAX-ACCESS not-accessible
    STATUS current
    DESCRIPTION
      "The table of OSPF area in the current configuration block."
    ::= { ospfCfg 2 }

ospfCurCfgAreaEntry OBJECT-TYPE
    SYNTAX OspfCurCfgAreaEntry
    MAX-ACCESS not-accessible
    STATUS current
    DESCRIPTION
      "Information about a OSPF area."
    INDEX { ospfCurCfgAreaIndex }
    ::= { ospfCurCfgAreaTable 1 }
 
OspfCurCfgAreaEntry ::= SEQUENCE {
    ospfCurCfgAreaIndex         Integer32,
    ospfCurCfgAreaId            IpAddress,
    ospfCurCfgAreaSpfInterval   INTEGER,
    ospfCurCfgAreaAuthType      INTEGER,
    ospfCurCfgAreaType          INTEGER,
    ospfCurCfgAreaMetric    INTEGER,
    ospfCurCfgAreaStatus        INTEGER
    }
 
ospfCurCfgAreaIndex OBJECT-TYPE
    SYNTAX Integer32
    MAX-ACCESS read-only
    STATUS current
    DESCRIPTION
    "The OSPF area number for which the OSPF area table is related."
    ::= { ospfCurCfgAreaEntry 1}

ospfCurCfgAreaId OBJECT-TYPE
    SYNTAX IpAddress 
    MAX-ACCESS read-only
    STATUS current
    DESCRIPTION
    "The IP Address of the OSPF area." 
    ::= { ospfCurCfgAreaEntry 2 }

ospfCurCfgAreaSpfInterval OBJECT-TYPE
    SYNTAX INTEGER (1..255) 
    MAX-ACCESS read-only
    STATUS current
    DESCRIPTION
    "The SPF interval for the OSPF area." 
    ::= { ospfCurCfgAreaEntry 3 }

ospfCurCfgAreaAuthType OBJECT-TYPE
    SYNTAX  INTEGER {
        none(1),
        password(2),
    md5(3)
        }
    MAX-ACCESS  read-only
    STATUS  current
    DESCRIPTION
        "Type of authentication being used.
     none(1) - no authentication
     password(2) - use password
     md5(3) - use MD5 authentication."
    
    ::= { ospfCurCfgAreaEntry 4 }

ospfCurCfgAreaType OBJECT-TYPE
    SYNTAX INTEGER {
        transit(0),
        stub(1),
        nssa(2)
           }
    MAX-ACCESS   read-only
    STATUS  current
    DESCRIPTION
        "Type of Area.
        transit(0)
        stub(1)
        nssa(2)"
           
    ::= { ospfCurCfgAreaEntry 5 }
    
ospfCurCfgAreaMetric OBJECT-TYPE
    SYNTAX  INTEGER (1..65535)
    MAX-ACCESS  read-only
    STATUS  current
    DESCRIPTION
        "Metric (1-65535)"
    
    ::= { ospfCurCfgAreaEntry 6 }

ospfCurCfgAreaStatus OBJECT-TYPE
    SYNTAX  INTEGER {
        disabled(0), 
     enabled(1)
        }
    MAX-ACCESS  read-only
    STATUS  current
    DESCRIPTION
        "Status
       disabled(0)
       enabled(1)"
    
    ::= { ospfCurCfgAreaEntry 7 }

ospfNewCfgAreaTable OBJECT-TYPE
    SYNTAX SEQUENCE OF OspfNewCfgAreaEntry
    MAX-ACCESS not-accessible
    STATUS current
    DESCRIPTION
      "The table of OSPF area in the new configuration block."
    ::= { ospfCfg 3 }

ospfNewCfgAreaEntry OBJECT-TYPE
    SYNTAX OspfNewCfgAreaEntry
    MAX-ACCESS not-accessible
    STATUS current
    DESCRIPTION
      "Information about a OSPF area."
    INDEX { ospfNewCfgAreaIndex }
    ::= { ospfNewCfgAreaTable 1 }
 
OspfNewCfgAreaEntry ::= SEQUENCE {
    ospfNewCfgAreaIndex         Integer32,
    ospfNewCfgAreaId            IpAddress, 
    ospfNewCfgAreaSpfInterval   INTEGER,
    ospfNewCfgAreaAuthType      INTEGER,    
    ospfNewCfgAreaType          INTEGER,
    ospfNewCfgAreaMetric    INTEGER,
    ospfNewCfgAreaStatus        INTEGER,
    ospfNewCfgAreaDelete        INTEGER 
    }
 
ospfNewCfgAreaIndex OBJECT-TYPE
    SYNTAX Integer32
    MAX-ACCESS read-only 
    STATUS current
    DESCRIPTION
    "The OSPF area number for which the OSPF area table is related."
    ::= { ospfNewCfgAreaEntry 1}

ospfNewCfgAreaId OBJECT-TYPE
    SYNTAX IpAddress 
    MAX-ACCESS read-create
    STATUS current
    DESCRIPTION
    "The IP Address of the OSPF area." 
    ::= { ospfNewCfgAreaEntry 2 }

ospfNewCfgAreaSpfInterval OBJECT-TYPE
    SYNTAX INTEGER (1..255) 
    MAX-ACCESS read-create
    STATUS current
    DESCRIPTION
    "The SPF interval for the OSPF area." 
    ::= { ospfNewCfgAreaEntry 3 }

ospfNewCfgAreaAuthType OBJECT-TYPE
    SYNTAX  INTEGER {
        none(1),
        password(2),
    md5(3)
        }
    MAX-ACCESS  read-create
    STATUS  current
    DESCRIPTION
        "Type of authentication being used.
     none(1) - no authentication
     password(2) - use password.
         md5(3) - use MD5 authentication."
    ::= { ospfNewCfgAreaEntry 4 }

ospfNewCfgAreaType OBJECT-TYPE
    SYNTAX INTEGER {
        transit(0),
        stub(1),
        nssa(2)
           }
    MAX-ACCESS   read-write
    STATUS  current
    DESCRIPTION
        "Type of Area.
        transit(0)
        stub(1)
           nssa(2)"
           
    ::= { ospfNewCfgAreaEntry 5 }
    
ospfNewCfgAreaMetric OBJECT-TYPE
    SYNTAX  INTEGER (1..65535)
    MAX-ACCESS  read-write
    STATUS  current
    DESCRIPTION
        "Metric (1-65535)"
    
    ::= { ospfNewCfgAreaEntry 6 }

ospfNewCfgAreaStatus OBJECT-TYPE
    SYNTAX  INTEGER {
        disabled(0), 
     enabled(1)
        }
    MAX-ACCESS  read-write
    STATUS current
    DESCRIPTION
        "Status
       disabled(0)
       enabled(1)"
    
    ::= { ospfNewCfgAreaEntry 7 }

ospfNewCfgAreaDelete OBJECT-TYPE
   SYNTAX INTEGER {
    no(0),
    yes(1)
    }
   MAX-ACCESS read-write
   STATUS current
   DESCRIPTION
    "Delete the area
        no(0),
            yes(1)"

    ::= { ospfNewCfgAreaEntry 8 }


-- OSPF Host Table

ospfCurCfgHostTable OBJECT-TYPE
    SYNTAX SEQUENCE OF OspfCurCfgHostEntry
    MAX-ACCESS not-accessible
    STATUS current
    DESCRIPTION
      "The table of OSPF Host configuration."
    ::= { ospfCfg 12 }

ospfCurCfgHostEntry OBJECT-TYPE
    SYNTAX OspfCurCfgHostEntry
    MAX-ACCESS not-accessible
    STATUS current
    DESCRIPTION
      "Information about a OSPF host."
    INDEX { ospfCurCfgHostIndex }
    ::= { ospfCurCfgHostTable 1 }
 
OspfCurCfgHostEntry ::= SEQUENCE {
    ospfCurCfgHostIndex         Integer32,
    ospfCurCfgHostIpAddr        IpAddress,
    ospfCurCfgHostAreaIndex     Integer32,
    ospfCurCfgHostCost          INTEGER,
    ospfCurCfgHostState     INTEGER
    }
 
ospfCurCfgHostIndex OBJECT-TYPE
    SYNTAX Integer32
    MAX-ACCESS read-only
    STATUS current
    DESCRIPTION
    "The OSPF host number for which the OSPF host table is related."
    ::= { ospfCurCfgHostEntry 1}

ospfCurCfgHostIpAddr OBJECT-TYPE
    SYNTAX IpAddress 
    MAX-ACCESS read-only
    STATUS current
    DESCRIPTION
    "The IP Address of the OSPF host." 
    ::= { ospfCurCfgHostEntry 2 }

ospfCurCfgHostAreaIndex OBJECT-TYPE
    SYNTAX Integer32
    MAX-ACCESS read-only
    STATUS current
    DESCRIPTION
    "The area index."
    ::= { ospfCurCfgHostEntry 3 }

ospfCurCfgHostCost OBJECT-TYPE
    SYNTAX  INTEGER (1..65535)
    MAX-ACCESS  read-only
    STATUS  current
    DESCRIPTION
        "The cost of the OSPF host."
    ::= { ospfCurCfgHostEntry 4 }

ospfCurCfgHostState OBJECT-TYPE
    SYNTAX  INTEGER  {
    enabled(2),
    disabled(3)
    }
    MAX-ACCESS  read-only
    STATUS  current
    DESCRIPTION
        "Enable or disable an OSPF Host"
    ::= { ospfCurCfgHostEntry 5 }

ospfNewCfgHostTable OBJECT-TYPE
    SYNTAX SEQUENCE OF OspfNewCfgHostEntry
    MAX-ACCESS not-accessible
    STATUS current
    DESCRIPTION
      "The table of OSPF Host configuration."
    ::= { ospfCfg 13 }

ospfNewCfgHostEntry OBJECT-TYPE
    SYNTAX OspfNewCfgHostEntry
    MAX-ACCESS not-accessible
    STATUS current
    DESCRIPTION
      "Information about a OSPF host."
    INDEX { ospfNewCfgHostIndex }
    ::= { ospfNewCfgHostTable 1 }
 
OspfNewCfgHostEntry ::= SEQUENCE {
    ospfNewCfgHostIndex         Integer32,
    ospfNewCfgHostIpAddr        IpAddress, 
    ospfNewCfgHostAreaIndex     Integer32,
    ospfNewCfgHostCost          INTEGER,
    ospfNewCfgHostState     INTEGER,
    ospfNewCfgHostDelete        INTEGER
    }
 
ospfNewCfgHostIndex OBJECT-TYPE
    SYNTAX Integer32
    MAX-ACCESS read-only 
    STATUS current
    DESCRIPTION
    "The OSPF host number for which the OSPF host table is related."
    ::= { ospfNewCfgHostEntry 1}

ospfNewCfgHostIpAddr OBJECT-TYPE
    SYNTAX IpAddress 
    MAX-ACCESS read-create
    STATUS current
    DESCRIPTION
    "The IP Address of the OSPF host." 
    ::= { ospfNewCfgHostEntry 2 }

ospfNewCfgHostAreaIndex OBJECT-TYPE
    SYNTAX Integer32 
    MAX-ACCESS read-create
    STATUS current
    DESCRIPTION
    "The OSPF area index."
    ::= { ospfNewCfgHostEntry 3 }

ospfNewCfgHostCost OBJECT-TYPE
    SYNTAX  INTEGER (1..65535)
    MAX-ACCESS  read-create
    STATUS  current
    DESCRIPTION
        "The cost of the OSPF host."
    ::= { ospfNewCfgHostEntry 4 }

ospfNewCfgHostState OBJECT-TYPE
    SYNTAX  INTEGER  {
    enabled(2),
    disabled(3)
    }
    MAX-ACCESS  read-create
    STATUS  current
    DESCRIPTION
        "Enable or disable an OSPF Host"
    ::= { ospfNewCfgHostEntry 5 }

ospfNewCfgHostDelete  OBJECT-TYPE
    SYNTAX  INTEGER {
        no(0),
        yes(1)
        }
    MAX-ACCESS read-write
    STATUS current
    DESCRIPTION
    "Delete the OSPF host:
         no(0),
         yes(1)" 
    ::= { ospfNewCfgHostEntry 6 }

ospfMdkeyTableMaxSize OBJECT-TYPE
    SYNTAX  Integer32
    MAX-ACCESS  read-only
    STATUS  current
    DESCRIPTION
        "The maximum number of rows in the OSPF Mdkey table."
    ::= { ospfCfg 11 }

ospfCurCfgMdkeyTable OBJECT-TYPE
    SYNTAX SEQUENCE OF OspfCurCfgMdkeyEntry
    MAX-ACCESS not-accessible
    STATUS current
    DESCRIPTION
      "The table of OSPF MD5 keys in the current configuration block."
    ::= { ospfCfg 5 }

ospfCurCfgMdkeyEntry OBJECT-TYPE
    SYNTAX OspfCurCfgMdkeyEntry
    MAX-ACCESS not-accessible
    STATUS current
    DESCRIPTION
      "Information about an OSPF MD keys table."
    INDEX { ospfCurCfgMdkeyIndex }
    ::= { ospfCurCfgMdkeyTable 1 }
 
OspfCurCfgMdkeyEntry ::= SEQUENCE {
    ospfCurCfgMdkeyIndex        Integer32,
    ospfCurCfgMdkeyKey          DisplayString
    }
 
ospfCurCfgMdkeyIndex OBJECT-TYPE
    SYNTAX Integer32
    MAX-ACCESS read-only 
    STATUS current
    DESCRIPTION
    "The OSPF MD5 Key number for which the OSPF MdKey table is related."
    ::= { ospfCurCfgMdkeyEntry 1}

ospfCurCfgMdkeyKey OBJECT-TYPE
    SYNTAX DisplayString (SIZE(0..16)) 
    MAX-ACCESS read-only
    STATUS current
    DESCRIPTION
    "The character string representing the MD5 Key." 
    ::= { ospfCurCfgMdkeyEntry 2 }

ospfNewCfgMdkeyTable OBJECT-TYPE
    SYNTAX SEQUENCE OF OspfNewCfgMdkeyEntry
    MAX-ACCESS not-accessible
    STATUS current
    DESCRIPTION
      "The table of OSPF MD5 keys in the new configuration block."
    ::= { ospfCfg 6 }

ospfNewCfgMdkeyEntry OBJECT-TYPE
    SYNTAX OspfNewCfgMdkeyEntry
    MAX-ACCESS not-accessible
    STATUS current
    DESCRIPTION
      "Information about an OSPF MD keys table."
    INDEX { ospfNewCfgMdkeyIndex }
    ::= { ospfNewCfgMdkeyTable 1 }
 
OspfNewCfgMdkeyEntry ::= SEQUENCE {
    ospfNewCfgMdkeyIndex        Integer32,
    ospfNewCfgMdkeyKey          DisplayString,
    ospfNewCfgMdkeyDelete       INTEGER 
    }
 
ospfNewCfgMdkeyIndex OBJECT-TYPE
    SYNTAX Integer32
    MAX-ACCESS read-only 
    STATUS current
    DESCRIPTION
    "The OSPF MD5 Key number for which the OSPF MdKey table is related."
    ::= { ospfNewCfgMdkeyEntry 1}

ospfNewCfgMdkeyKey OBJECT-TYPE
    SYNTAX DisplayString (SIZE(0..16)) 
    MAX-ACCESS read-create
    STATUS current
    DESCRIPTION
    "The character string representing the MD5 Key." 
    ::= { ospfNewCfgMdkeyEntry 2 }

ospfNewCfgMdkeyDelete OBJECT-TYPE
    SYNTAX  INTEGER { 
    other(1),
        delete(2)
    }
    MAX-ACCESS read-create 
    STATUS current
    DESCRIPTION
    "When set to the value of 2 (delete), the entire row is deleted. 
     When read, other(1) is returned. Setting the value to anything 
     other than 2(delete) has no effect on the state of the row."
    ::= { ospfNewCfgMdkeyEntry 3}


ospfCurCfgIntfTable OBJECT-TYPE
    SYNTAX SEQUENCE OF OspfCurCfgIntfEntry
    MAX-ACCESS not-accessible
    STATUS current
    DESCRIPTION
      "The table of OSPF Interface in the current configuration block."
    ::= { ospfCfg 7 }

ospfCurCfgIntfEntry OBJECT-TYPE
    SYNTAX OspfCurCfgIntfEntry
    MAX-ACCESS not-accessible
    STATUS current
    DESCRIPTION
      "Information about an OSPF Interface."
    INDEX { ospfCurCfgIntfIndex }
    ::= { ospfCurCfgIntfTable 1 }
 
OspfCurCfgIntfEntry ::= SEQUENCE {
    ospfCurCfgIntfIndex         Integer32,
    ospfCurCfgIntfArea          INTEGER,
    ospfCurCfgIntfMdkey         INTEGER, 
    ospfCurCfgIntfCost          INTEGER,
    ospfCurCfgIntfPrio          INTEGER,
    ospfCurCfgIntfHello         INTEGER,
    ospfCurCfgIntfHelloMS         INTEGER,
    ospfCurCfgIntfDead          INTEGER,
    ospfCurCfgIntfDeadMS        INTEGER,
    ospfCurCfgIntfTrans         INTEGER,
    ospfCurCfgIntfRetra         INTEGER,
    ospfCurCfgIntfAuthKey       DisplayString,
    ospfCurCfgIntfPassive       INTEGER,
    ospfCurCfgIntfPtop          INTEGER,
    ospfCurCfgIntfStatus        INTEGER
    }
 
ospfCurCfgIntfIndex OBJECT-TYPE
    SYNTAX Integer32
    MAX-ACCESS read-only
    STATUS current
    DESCRIPTION
    "The OSPF Interface number for which the OSPF Interface table is 
         related."
    ::= { ospfCurCfgIntfEntry 1}

ospfCurCfgIntfArea OBJECT-TYPE
    SYNTAX INTEGER (0..2) 
    MAX-ACCESS read-only
    STATUS current
    DESCRIPTION
    "The index of the area that the interface belongs (0..2)"
    ::= { ospfCurCfgIntfEntry 2 }

ospfCurCfgIntfMdkey OBJECT-TYPE
    SYNTAX INTEGER (0..255) 
    MAX-ACCESS read-only
    STATUS current
    DESCRIPTION
    "The MD5 key for the OSPF interface
         0 (none) no MD5 authentication." 
    ::= { ospfCurCfgIntfEntry 3 }

ospfCurCfgIntfCost  OBJECT-TYPE 
    SYNTAX INTEGER (1..65535) 
    MAX-ACCESS read-only
    STATUS current
    DESCRIPTION
    "Interface cost" 
    ::= { ospfCurCfgIntfEntry 4 }

ospfCurCfgIntfPrio   OBJECT-TYPE
   SYNTAX INTEGER (1..255) 
    MAX-ACCESS read-only
    STATUS current 
    DESCRIPTION
    "Interface router priority" 
    ::= { ospfCurCfgIntfEntry 5 }

ospfCurCfgIntfHello  OBJECT-TYPE 
    SYNTAX INTEGER (1..65535) 
    MAX-ACCESS read-only
    STATUS current
    DESCRIPTION
    "Hello interval" 
    ::= { ospfCurCfgIntfEntry 6 }

ospfCurCfgIntfHelloMS  OBJECT-TYPE
    SYNTAX  INTEGER {
        seconds(0),
        milliseconds(1)
        }
    MAX-ACCESS read-only
    STATUS current
    DESCRIPTION
    "Units of time measurement for Hello interval
    seconds(0),
        milliseconds(1)" 
    ::= { ospfCurCfgIntfEntry 7 }

ospfCurCfgIntfDead   OBJECT-TYPE
   SYNTAX INTEGER (1..65535) 
    MAX-ACCESS read-only
    STATUS current 
    DESCRIPTION
    "Dead interval" 
    ::= { ospfCurCfgIntfEntry 8 }

ospfCurCfgIntfDeadMS  OBJECT-TYPE
    SYNTAX  INTEGER {
        seconds(0),
        milliseconds(1)
        }
    MAX-ACCESS read-only
    STATUS current
    DESCRIPTION
    "Units of time measurement for Dead interval
    seconds(0),
        milliseconds(1)" 
    ::= { ospfCurCfgIntfEntry 9 }

ospfCurCfgIntfTrans  OBJECT-TYPE
   SYNTAX INTEGER (1..3600) 
    MAX-ACCESS read-only
    STATUS current
    DESCRIPTION
    "Transit delay" 
    ::= { ospfCurCfgIntfEntry 10 }
    
ospfCurCfgIntfRetra OBJECT-TYPE
    SYNTAX INTEGER (1..3600) 
    MAX-ACCESS read-only
    STATUS current
    DESCRIPTION
    "Retransmit interval" 
    ::= { ospfCurCfgIntfEntry 11 }

ospfCurCfgIntfAuthKey OBJECT-TYPE  
   SYNTAX DisplayString (SIZE(0..8))
    MAX-ACCESS read-only
    STATUS current
    DESCRIPTION
    "Authentication Key" 
    ::= { ospfCurCfgIntfEntry 12 }

ospfCurCfgIntfPassive  OBJECT-TYPE
    SYNTAX  INTEGER {
        disabled(0),
        enabled(1)
        }
    MAX-ACCESS read-only
    STATUS current
    DESCRIPTION
    "Passive interface
    disabled(0),
        enabled(1)" 
    ::= { ospfCurCfgIntfEntry 13 }

ospfCurCfgIntfPtop  OBJECT-TYPE
    SYNTAX  INTEGER {
        disabled(0),
        enabled(1)
        }
    MAX-ACCESS read-only
    STATUS current
    DESCRIPTION
    "Point-to-point interface
    disabled(0),
        enabled(1)" 
    ::= { ospfCurCfgIntfEntry 15 }

ospfCurCfgIntfStatus  OBJECT-TYPE
    SYNTAX  INTEGER {
        disabled(0),
        enabled(1)
        }
    MAX-ACCESS read-only
    STATUS current
    DESCRIPTION
    "Status of the interface
    disabled(0),
        enabled(1)" 
    ::= { ospfCurCfgIntfEntry 14 }

ospfNewCfgIntfTable OBJECT-TYPE
    SYNTAX SEQUENCE OF OspfNewCfgIntfEntry
    MAX-ACCESS not-accessible
    STATUS current
    DESCRIPTION
      "The table of OSPF interface in the new configuration block."
    ::= { ospfCfg 8 }

ospfNewCfgIntfEntry OBJECT-TYPE
    SYNTAX OspfNewCfgIntfEntry
    MAX-ACCESS not-accessible
    STATUS current
    DESCRIPTION
      "Information about an OSPF interface."
    INDEX { ospfNewCfgIntfIndex }
    ::= { ospfNewCfgIntfTable 1 }

OspfNewCfgIntfEntry ::= SEQUENCE {
    ospfNewCfgIntfIndex         Integer32,
    ospfNewCfgIntfArea          INTEGER,
    ospfNewCfgIntfMdkey         INTEGER,
    ospfNewCfgIntfCost      INTEGER,
    ospfNewCfgIntfPrio      INTEGER,
    ospfNewCfgIntfHello         INTEGER,
    ospfNewCfgIntfHelloMS       INTEGER,
    ospfNewCfgIntfDead          INTEGER,
    ospfNewCfgIntfDeadMS        INTEGER,
    ospfNewCfgIntfTrans         INTEGER,
    ospfNewCfgIntfRetra         INTEGER,
    ospfNewCfgIntfAuthKey       DisplayString,
    ospfNewCfgIntfPassive       INTEGER,
    ospfNewCfgIntfPtop          INTEGER, 
    ospfNewCfgIntfStatus        INTEGER, 
    ospfNewCfgIntfDelete        INTEGER
    }
 
ospfNewCfgIntfIndex OBJECT-TYPE
    SYNTAX Integer32
    MAX-ACCESS read-only
    STATUS current
    DESCRIPTION
    "The OSPF Interface number for which the OSPF Interface table is 
         related."
    ::= { ospfNewCfgIntfEntry 1}

ospfNewCfgIntfArea OBJECT-TYPE
    SYNTAX INTEGER (0..19)
    MAX-ACCESS read-create
    STATUS current
    DESCRIPTION
    "The index of the area that the interface belongs" 
    ::= { ospfNewCfgIntfEntry 2 }

ospfNewCfgIntfMdkey OBJECT-TYPE
    SYNTAX INTEGER (0..255) 
    MAX-ACCESS read-create
    STATUS current
    DESCRIPTION
    "The MD5 key for the OSPF interface
         0 (none) no MD5 authentication." 
    ::= { ospfNewCfgIntfEntry 3 }

ospfNewCfgIntfCost  OBJECT-TYPE 
    SYNTAX INTEGER (1..65535) 
    MAX-ACCESS read-create
    STATUS current
    DESCRIPTION
    "Interface cost(1..65535)" 
    ::= { ospfNewCfgIntfEntry 4 }

ospfNewCfgIntfPrio   OBJECT-TYPE
   SYNTAX INTEGER (0..255) 
    MAX-ACCESS read-create
    STATUS current 
    DESCRIPTION
    "Interface router priority(0..255)" 
    ::= { ospfNewCfgIntfEntry 5 }


ospfNewCfgIntfHello  OBJECT-TYPE 
    SYNTAX INTEGER (1..65535) 
    MAX-ACCESS read-create
    STATUS current
    DESCRIPTION
    "Hello interval(1..65535s | 50..65535ms)"
    ::= { ospfNewCfgIntfEntry 6 }


ospfNewCfgIntfHelloMS  OBJECT-TYPE
    SYNTAX  INTEGER {
        seconds(0),
        milliseconds(1)
        }
    MAX-ACCESS read-create
    STATUS current
    DESCRIPTION
    "Units of time measurement for Hello interval
    seconds(0),
        milliseconds(1)" 
    ::= { ospfNewCfgIntfEntry 7 }

ospfNewCfgIntfDead   OBJECT-TYPE
   SYNTAX INTEGER (1..65535) 
    MAX-ACCESS read-create
    STATUS current
    DESCRIPTION
    "Dead interval(1..65535s |1000..65535ms)"
    ::= { ospfNewCfgIntfEntry 8 }

ospfNewCfgIntfDeadMS  OBJECT-TYPE
    SYNTAX  INTEGER {
        seconds(0),
        milliseconds(1)
        }
    MAX-ACCESS read-create
    STATUS current
    DESCRIPTION
    "Units of time measurement for Dead interval
    seconds(0),
        milliseconds(1)" 
    ::= { ospfNewCfgIntfEntry 9 }

ospfNewCfgIntfTrans  OBJECT-TYPE
   SYNTAX INTEGER (1..3600) 
    MAX-ACCESS read-create
    STATUS current
    DESCRIPTION
    "Transit delay(1..3600)" 
    ::= { ospfNewCfgIntfEntry 10 }

ospfNewCfgIntfRetra OBJECT-TYPE
  SYNTAX INTEGER (1..3600) 
    MAX-ACCESS read-create
    STATUS current
    DESCRIPTION
    "Retransmit interval(1..3600)" 
    ::= { ospfNewCfgIntfEntry 11 }

ospfNewCfgIntfAuthKey OBJECT-TYPE  
   SYNTAX DisplayString (SIZE(0..8))
    MAX-ACCESS read-create
    STATUS current
    DESCRIPTION
    "Authentication Key" 
    ::= { ospfNewCfgIntfEntry 12 }

ospfNewCfgIntfPassive  OBJECT-TYPE
    SYNTAX  INTEGER {
        disabled(0),
        enabled(1)
        }
    MAX-ACCESS read-create
    STATUS current
    DESCRIPTION
    "Passive interface
    disabled(0),
        enabled(1)" 
    ::= { ospfNewCfgIntfEntry 13 }

ospfNewCfgIntfPtop  OBJECT-TYPE
    SYNTAX  INTEGER {
        disabled(0),
        enabled(1)
        }
    MAX-ACCESS read-create
    STATUS current
    DESCRIPTION
    "Point-to-point interface
    disabled(0),
        enabled(1)" 
    ::= { ospfNewCfgIntfEntry 16 }

ospfNewCfgIntfStatus  OBJECT-TYPE
    SYNTAX  INTEGER {
        disabled(0),
        enabled(1)
        }
    MAX-ACCESS read-create
    STATUS current
    DESCRIPTION
    "Status of the interface
    disabled(0),
        enabled(1)" 
    ::= { ospfNewCfgIntfEntry 14 }

ospfNewCfgIntfDelete  OBJECT-TYPE
    SYNTAX  INTEGER {
        other(0),
        delete(1)
        }
    MAX-ACCESS read-write
    STATUS current
    DESCRIPTION
    "Delete the interface
         other(0),
         delete(1)" 
    ::= { ospfNewCfgIntfEntry 15 }

ospfCurCfgLoopIfTable OBJECT-TYPE
    SYNTAX SEQUENCE OF OspfCurCfgLoopIfEntry
    MAX-ACCESS not-accessible
    STATUS current
    DESCRIPTION
      "The table of OSPF Loopback Interfaces 
       in the current configuration block."
    ::= { ospfCfg 20 }

ospfCurCfgLoopIfEntry OBJECT-TYPE
    SYNTAX OspfCurCfgLoopIfEntry
    MAX-ACCESS not-accessible
    STATUS current
    DESCRIPTION
      "Information about an OSPF Loopback Interface."
    INDEX { ospfCurCfgLoopIfIndex }
    ::= { ospfCurCfgLoopIfTable 1 }

OspfCurCfgLoopIfEntry ::= SEQUENCE {
    ospfCurCfgLoopIfIndex         Integer32,
    ospfCurCfgLoopIfArea          INTEGER,
    ospfCurCfgLoopIfStatus        INTEGER
    }

ospfCurCfgLoopIfIndex OBJECT-TYPE
    SYNTAX Integer32
    MAX-ACCESS read-only
    STATUS current
    DESCRIPTION
        "The OSPF Loopback Interface number for which 
         the OSPF Interface table is related."
    ::= { ospfCurCfgLoopIfEntry 1}

ospfCurCfgLoopIfArea OBJECT-TYPE
    SYNTAX INTEGER 
    MAX-ACCESS read-only
    STATUS current
    DESCRIPTION
        "The index of the area that the loopback interface belongs"
    ::= { ospfCurCfgLoopIfEntry 2 }

ospfCurCfgLoopIfStatus  OBJECT-TYPE
    SYNTAX  INTEGER {
        disabled(0),
        enabled(1)
        }
    MAX-ACCESS read-only
    STATUS current
    DESCRIPTION
        "Status of the loopback interface
        disabled(0),
        enabled(1)"
    ::= { ospfCurCfgLoopIfEntry 3 }

ospfNewCfgLoopIfTable OBJECT-TYPE
    SYNTAX SEQUENCE OF OspfNewCfgLoopIfEntry
    MAX-ACCESS not-accessible
    STATUS current
    DESCRIPTION
      "The table of OSPF loopback interface in the new configuration block."
    ::= { ospfCfg 21 }

ospfNewCfgLoopIfEntry OBJECT-TYPE
    SYNTAX OspfNewCfgLoopIfEntry
    MAX-ACCESS not-accessible
    STATUS current
    DESCRIPTION
      "Information about an OSPF loopback interface."
    INDEX { ospfNewCfgLoopIfIndex }
    ::= { ospfNewCfgLoopIfTable 1 }

OspfNewCfgLoopIfEntry ::= SEQUENCE {
    ospfNewCfgLoopIfIndex         Integer32,
    ospfNewCfgLoopIfArea          INTEGER,
    ospfNewCfgLoopIfStatus        INTEGER,
    ospfNewCfgLoopIfDelete        INTEGER
    }

ospfNewCfgLoopIfIndex OBJECT-TYPE
    SYNTAX Integer32
    MAX-ACCESS read-only
    STATUS current
    DESCRIPTION
        "The OSPF loopback interface number for which 
         the OSPF Loopback Interface table is related."
    ::= { ospfNewCfgLoopIfEntry 1}

ospfNewCfgLoopIfArea OBJECT-TYPE
    SYNTAX INTEGER (0..2)
    MAX-ACCESS read-create
    STATUS current
    DESCRIPTION
        "The index of the area that the loopback interface belongs (0..2)"
    ::= { ospfNewCfgLoopIfEntry 2 }

ospfNewCfgLoopIfStatus  OBJECT-TYPE
    SYNTAX  INTEGER {
        disabled(0),
        enabled(1)
        }
    MAX-ACCESS read-create
    STATUS current
    DESCRIPTION
        "Status of the loopback interface
        disabled(0),
        enabled(1)"
    ::= { ospfNewCfgLoopIfEntry 3 }

ospfNewCfgLoopIfDelete  OBJECT-TYPE
    SYNTAX  INTEGER {
        other(0),
        delete(1)
        }
    MAX-ACCESS read-write
    STATUS current
    DESCRIPTION
        "Delete the loopback interface
         other(0),
         delete(1)"
    ::= { ospfNewCfgLoopIfEntry 4 }

ospfCurCfgVirtIntfTable OBJECT-TYPE
    SYNTAX SEQUENCE OF OspfCurCfgVirtIntfEntry
    MAX-ACCESS not-accessible
    STATUS current
    DESCRIPTION
      "The table of OSPF Virtual Interface configuration in the current 
       configuration."
    ::= { ospfCfg 9 }

ospfCurCfgVirtIntfEntry OBJECT-TYPE
    SYNTAX OspfCurCfgVirtIntfEntry
    MAX-ACCESS not-accessible
    STATUS current
    DESCRIPTION
      "Information about an OSPF virtual Interface."
    INDEX { ospfCurCfgVirtIntfIndex }
    ::= { ospfCurCfgVirtIntfTable 1 }
 
OspfCurCfgVirtIntfEntry ::= SEQUENCE {
    ospfCurCfgVirtIntfIndex         Integer32,
    ospfCurCfgVirtIntfAreaId        INTEGER,
    ospfCurCfgVirtIntfNbr           IpAddress,
    ospfCurCfgVirtIntfMdkey         INTEGER,
    ospfCurCfgVirtIntfHello         INTEGER,
    ospfCurCfgVirtIntfHelloMS       INTEGER,
    ospfCurCfgVirtIntfDead          INTEGER,
    ospfCurCfgVirtIntfDeadMS        INTEGER,
    ospfCurCfgVirtIntfTrans         INTEGER,
    ospfCurCfgVirtIntfRetra         INTEGER,
    ospfCurCfgVirtIntfAuthKey       DisplayString,
    ospfCurCfgVirtIntfStatus        INTEGER 
    }
 
ospfCurCfgVirtIntfIndex OBJECT-TYPE
    SYNTAX Integer32
    MAX-ACCESS read-only
    STATUS current
    DESCRIPTION
    "The OSPF Virtual Interface number for which the OSPF 
         Virtual Interface table is related."
    ::= { ospfCurCfgVirtIntfEntry 1}

ospfCurCfgVirtIntfAreaId OBJECT-TYPE
    SYNTAX INTEGER (0..19)
    MAX-ACCESS read-only
    STATUS current
    DESCRIPTION
    "The index of the OSPF area to which this virtual interface
         belongs." 
    ::= { ospfCurCfgVirtIntfEntry 2 }

ospfCurCfgVirtIntfNbr OBJECT-TYPE
    SYNTAX IpAddress 
    MAX-ACCESS read-only
    STATUS current
    DESCRIPTION
    "The IP Address of the OSPF neighbor for this virtual interface."
    ::= { ospfCurCfgVirtIntfEntry 3 }

ospfCurCfgVirtIntfMdkey OBJECT-TYPE
    SYNTAX INTEGER (0..255) 
    MAX-ACCESS read-only
    STATUS current
    DESCRIPTION
    "The MD5 key for the OSPF virtual interface
         0 (none) no MD5 authentication." 
    ::= { ospfCurCfgVirtIntfEntry 4 }

ospfCurCfgVirtIntfHello  OBJECT-TYPE 
    SYNTAX INTEGER (1..65535) 
    MAX-ACCESS read-only
    STATUS current
    DESCRIPTION
    "Hello interval" 
    ::= { ospfCurCfgVirtIntfEntry 5 }

ospfCurCfgVirtIntfHelloMS  OBJECT-TYPE
    SYNTAX  INTEGER {
        seconds(0),
        milliseconds(1)
        }
    MAX-ACCESS read-only
    STATUS current
    DESCRIPTION
    "Units of time measurement for Hello interval
     seconds(0),
        milliseconds(1)" 
    ::= { ospfCurCfgVirtIntfEntry 6 }

ospfCurCfgVirtIntfDead   OBJECT-TYPE
   SYNTAX INTEGER (1..65535) 
    MAX-ACCESS read-only
    STATUS current 
    DESCRIPTION
    "Dead interval" 
    ::= { ospfCurCfgVirtIntfEntry 7 }

ospfCurCfgVirtIntfDeadMS  OBJECT-TYPE
    SYNTAX  INTEGER {
        seconds(0),
        milliseconds(1)
        }
    MAX-ACCESS read-only
    STATUS current
    DESCRIPTION
    "Units of time measurement for Dead interval
     seconds(0),
        milliseconds(1)" 
    ::= { ospfCurCfgVirtIntfEntry 8 }

ospfCurCfgVirtIntfTrans  OBJECT-TYPE
   SYNTAX INTEGER (1..3600) 
    MAX-ACCESS read-only
    STATUS current
    DESCRIPTION
    "Transit delay" 
    ::= { ospfCurCfgVirtIntfEntry 9 }
    

ospfCurCfgVirtIntfRetra OBJECT-TYPE
    SYNTAX INTEGER (1..3600) 
    MAX-ACCESS read-only
    STATUS current
    DESCRIPTION
    "Retransmit interval" 
    ::= { ospfCurCfgVirtIntfEntry 10 }

ospfCurCfgVirtIntfAuthKey OBJECT-TYPE  
   SYNTAX DisplayString (SIZE(0..8))
    MAX-ACCESS read-only
    STATUS current
    DESCRIPTION
    "Authentication Key" 
    ::= { ospfCurCfgVirtIntfEntry 11 }
 
    
ospfCurCfgVirtIntfStatus  OBJECT-TYPE
    SYNTAX  INTEGER {
        disabled(0),
        enabled(1)
        }
    MAX-ACCESS read-only
    STATUS current
    DESCRIPTION
    "Status
     disabled(0),
        enabled(1)" 
    ::= { ospfCurCfgVirtIntfEntry 12 }

ospfNewCfgVirtIntfTable OBJECT-TYPE
    SYNTAX SEQUENCE OF OspfNewCfgVirtIntfEntry
    MAX-ACCESS not-accessible
    STATUS current
    DESCRIPTION
      "The table of OSPF Virtual interface in the new configuration block."
    ::= { ospfCfg 10 }

ospfNewCfgVirtIntfEntry OBJECT-TYPE
    SYNTAX OspfNewCfgVirtIntfEntry
    MAX-ACCESS not-accessible
    STATUS current
    DESCRIPTION
      "Information about an OSPF virtual interface."
    INDEX { ospfNewCfgVirtIntfIndex }
    ::= { ospfNewCfgVirtIntfTable 1 }
 
OspfNewCfgVirtIntfEntry ::= SEQUENCE {
    ospfNewCfgVirtIntfIndex         Integer32,
    ospfNewCfgVirtIntfAreaId        INTEGER,
    ospfNewCfgVirtIntfNbr           IpAddress,
    ospfNewCfgVirtIntfMdkey         INTEGER,
    ospfNewCfgVirtIntfHello         INTEGER,
    ospfNewCfgVirtIntfHelloMS       INTEGER,
    ospfNewCfgVirtIntfDead          INTEGER,
    ospfNewCfgVirtIntfDeadMS        INTEGER,
    ospfNewCfgVirtIntfTrans         INTEGER,
    ospfNewCfgVirtIntfRetra         INTEGER,
    ospfNewCfgVirtIntfAuthKey       DisplayString,
    ospfNewCfgVirtIntfStatus        INTEGER, 
    ospfNewCfgVirtIntfDelete        INTEGER
    }
 
ospfNewCfgVirtIntfIndex OBJECT-TYPE
    SYNTAX Integer32
    MAX-ACCESS read-only
    STATUS current
    DESCRIPTION
    "The OSPF Virtual Interface number for which the OSPF 
         Virtual Interface table is related."
    ::= { ospfNewCfgVirtIntfEntry 1}

ospfNewCfgVirtIntfAreaId OBJECT-TYPE
    SYNTAX INTEGER (0..19)

    MAX-ACCESS read-create
    STATUS current
    DESCRIPTION
    "The index of the OSPF area to which this virtual interface
         belongs." 
    ::= { ospfNewCfgVirtIntfEntry 2 }

ospfNewCfgVirtIntfNbr OBJECT-TYPE
    SYNTAX IpAddress 
    MAX-ACCESS read-create
    STATUS current
    DESCRIPTION
    "The IP Address of the OSPF neighbor for this virtual interface."
    ::= { ospfNewCfgVirtIntfEntry 3 }

ospfNewCfgVirtIntfMdkey OBJECT-TYPE
    SYNTAX INTEGER (0..255) 
    MAX-ACCESS read-create
    STATUS current
    DESCRIPTION
    "The MD5 key for the OSPF virtual interface
         0 (none) no MD5 authentication." 
    ::= { ospfNewCfgVirtIntfEntry 4 }

ospfNewCfgVirtIntfHello  OBJECT-TYPE 
    SYNTAX INTEGER (1..65535) 
    MAX-ACCESS read-create
    STATUS current
    DESCRIPTION
    "Hello interval(1..65535s | 50..65535ms)"
    ::= { ospfNewCfgVirtIntfEntry 5 }

ospfNewCfgVirtIntfHelloMS  OBJECT-TYPE
    SYNTAX  INTEGER {
        seconds(0),
        milliseconds(1)
        }
    MAX-ACCESS read-create
    STATUS current
    DESCRIPTION
    "Units of time measurement fo Hello interval 
         seconds(0),
         milliseconds(1) " 
    ::= { ospfNewCfgVirtIntfEntry 6 }

ospfNewCfgVirtIntfDead   OBJECT-TYPE
   SYNTAX INTEGER (1..65535) 
    MAX-ACCESS read-create
    STATUS current
    DESCRIPTION
    "Dead interval(1..65535s | 1000..65535ms)"
    ::= { ospfNewCfgVirtIntfEntry 7 }

ospfNewCfgVirtIntfDeadMS  OBJECT-TYPE
    SYNTAX  INTEGER {
        seconds(0),
        milliseconds(1)
        }
    MAX-ACCESS read-create
    STATUS current
    DESCRIPTION
    "Units of time measurement fo Dead interval 
         seconds(0),
         milliseconds(1) " 
    ::= { ospfNewCfgVirtIntfEntry 8 }

ospfNewCfgVirtIntfTrans  OBJECT-TYPE
   SYNTAX INTEGER (1..3600) 
    MAX-ACCESS read-create
    STATUS current
    DESCRIPTION
    "Transit delay(1..3600)" 
    ::= { ospfNewCfgVirtIntfEntry 9 }
    

ospfNewCfgVirtIntfRetra OBJECT-TYPE
  SYNTAX INTEGER (1..3600) 
    MAX-ACCESS read-create
    STATUS current
    DESCRIPTION
    "Retransmit interval(1..3600)" 
    ::= { ospfNewCfgVirtIntfEntry 10 }


ospfNewCfgVirtIntfAuthKey OBJECT-TYPE  
   SYNTAX DisplayString (SIZE(0..8))
    MAX-ACCESS read-create
    STATUS current
    DESCRIPTION
    "Authentication Key SIZE(0..8)" 
    ::= { ospfNewCfgVirtIntfEntry 11 }
     
ospfNewCfgVirtIntfStatus  OBJECT-TYPE
    SYNTAX  INTEGER {
        disabled(0),
        enabled(1)
        }
    MAX-ACCESS read-create
    STATUS current
    DESCRIPTION
    "Status 
         disabled(0),
         enabled(1) " 
    ::= { ospfNewCfgVirtIntfEntry 12 }
      
ospfNewCfgVirtIntfDelete  OBJECT-TYPE
    SYNTAX  INTEGER {
        other(0),
        delete(1)
        }
    MAX-ACCESS read-write
    STATUS current
    DESCRIPTION
    "Delete
     other(0),
         delete(1)" 
    ::= { ospfNewCfgVirtIntfEntry 13 }


-- ospf range

ospfCurCfgRangeTable OBJECT-TYPE
    SYNTAX SEQUENCE OF OspfCurCfgRangeEntry
    MAX-ACCESS not-accessible
    STATUS current
    DESCRIPTION
      "The table of OSPF summary range in the current configuration." 
    ::= { ospfCfg 14 }

ospfCurCfgRangeEntry OBJECT-TYPE
    SYNTAX OspfCurCfgRangeEntry 
    MAX-ACCESS not-accessible
    STATUS current
    DESCRIPTION
      "Information about an OSPF summary range."
    INDEX { ospfCurCfgRangeIndex }
    ::= { ospfCurCfgRangeTable 1 }
 
OspfCurCfgRangeEntry ::= SEQUENCE {
    ospfCurCfgRangeIndex            Integer32,
    ospfCurCfgRangeAddr             IpAddress,
    ospfCurCfgRangeMask             IpAddress,
    ospfCurCfgRangeAreaIndex        Integer32,
    ospfCurCfgRangeHideState        INTEGER,
    ospfCurCfgRangeState            INTEGER
    }
 
ospfCurCfgRangeIndex OBJECT-TYPE
    SYNTAX Integer32
    MAX-ACCESS read-only
    STATUS current
    DESCRIPTION
    "The range number for which the OSPF summary range table is related." 
    ::= { ospfCurCfgRangeEntry 1}

ospfCurCfgRangeAddr OBJECT-TYPE
    SYNTAX IpAddress 
    MAX-ACCESS read-only
    STATUS current
    DESCRIPTION
    "The IP Address of the range." 
    ::= { ospfCurCfgRangeEntry 2 }

ospfCurCfgRangeMask OBJECT-TYPE
    SYNTAX IpAddress 
    MAX-ACCESS read-only
    STATUS current
    DESCRIPTION
    "The mask of the range."
    ::= { ospfCurCfgRangeEntry 3 }

ospfCurCfgRangeAreaIndex OBJECT-TYPE
    SYNTAX Integer32
    MAX-ACCESS read-only
    STATUS current
    DESCRIPTION
        "The area index."
    ::= { ospfCurCfgRangeEntry 4 }

ospfCurCfgRangeHideState OBJECT-TYPE
    SYNTAX  INTEGER {
        enabled(1),
        disabled(2)
        }
    MAX-ACCESS  read-only
    STATUS  current
    DESCRIPTION
        "The state of the hide range."
    ::= { ospfCurCfgRangeEntry 5 }

ospfCurCfgRangeState OBJECT-TYPE
    SYNTAX  INTEGER {
        enabled(1),
        disabled(2)
        }
    MAX-ACCESS  read-only
    STATUS  current
    DESCRIPTION
        "The state of the range."
    ::= { ospfCurCfgRangeEntry 6 }

ospfNewCfgRangeTable OBJECT-TYPE
    SYNTAX SEQUENCE OF OspfNewCfgRangeEntry
    MAX-ACCESS not-accessible
    STATUS current
    DESCRIPTION
      "The table of OSPF summary range in the new configuration." 
    ::= { ospfCfg 15 }

ospfNewCfgRangeEntry OBJECT-TYPE
    SYNTAX OspfNewCfgRangeEntry 
    MAX-ACCESS not-accessible
    STATUS current
    DESCRIPTION
      "Information about an OSPF summary range."
    INDEX { ospfNewCfgRangeIndex }
    ::= { ospfNewCfgRangeTable 1 }
 
OspfNewCfgRangeEntry ::= SEQUENCE {
    ospfNewCfgRangeIndex            Integer32,
    ospfNewCfgRangeAddr             IpAddress,
    ospfNewCfgRangeMask             IpAddress,
    ospfNewCfgRangeAreaIndex        Integer32,
    ospfNewCfgRangeHideState        INTEGER,
    ospfNewCfgRangeState            INTEGER,
    ospfNewCfgRangeDelete           INTEGER
    }
 
ospfNewCfgRangeIndex OBJECT-TYPE
    SYNTAX Integer32
    MAX-ACCESS read-only
    STATUS current
    DESCRIPTION
    "The range number for which the OSPF summary range table is related." 
    ::= { ospfNewCfgRangeEntry 1}

ospfNewCfgRangeAddr OBJECT-TYPE
    SYNTAX IpAddress 
    MAX-ACCESS read-create 
    STATUS current
    DESCRIPTION
    "The IP Address of the range." 
    ::= { ospfNewCfgRangeEntry 2 }

ospfNewCfgRangeMask OBJECT-TYPE
    SYNTAX IpAddress 
    MAX-ACCESS read-create 
    STATUS current
    DESCRIPTION
    "The mask of the range."
    ::= { ospfNewCfgRangeEntry 3 }

ospfNewCfgRangeAreaIndex OBJECT-TYPE
    SYNTAX Integer32
    MAX-ACCESS read-create 
    STATUS current
    DESCRIPTION
        "The area index."
    ::= { ospfNewCfgRangeEntry 4 }

ospfNewCfgRangeHideState OBJECT-TYPE
    SYNTAX  INTEGER {
        enabled(1),
        disabled(2)
        }
    MAX-ACCESS read-create 
    STATUS  current
    DESCRIPTION
        "The state of the hide range."
    ::= { ospfNewCfgRangeEntry 5 }

ospfNewCfgRangeState OBJECT-TYPE
    SYNTAX  INTEGER {
        enabled(1),
        disabled(2)
        }
    MAX-ACCESS read-create 
    STATUS  current
    DESCRIPTION
        "The state of the range."
    ::= { ospfNewCfgRangeEntry 6 }

ospfNewCfgRangeDelete OBJECT-TYPE
    SYNTAX  INTEGER {
        other(1),
        delete(2)
        }
    MAX-ACCESS  read-create
    STATUS  current
    DESCRIPTION
        "When set to the value of 2 (delete), the entire row is deleted.
         When read, other(1) is returned. Setting the value to anything
         other than 2(delete) has no effect on the state of the row."
    ::= { ospfNewCfgRangeEntry 7 }


ospfRouteRedistribution   OBJECT IDENTIFIER ::= { ospfCfg 4 }

ospfRedistributeStatic    OBJECT IDENTIFIER ::= { ospfRouteRedistribution 1 }

ospfCurCfgStaticMetric OBJECT-TYPE
    SYNTAX INTEGER (0..16777214)
    MAX-ACCESS read-only
    STATUS current
    DESCRIPTION
    "The metric to be assigned to static routes." 
    ::= { ospfRedistributeStatic 1 }

ospfNewCfgStaticMetric OBJECT-TYPE
    SYNTAX INTEGER (0..16777214)
    MAX-ACCESS read-write
    STATUS current
    DESCRIPTION
    "The metric to be assigned to static routes." 
    ::= { ospfRedistributeStatic 2 }

ospfCurCfgStaticMetricType OBJECT-TYPE
    SYNTAX INTEGER {
        none(1),
        type1(2),
        type2(3)
        }
    MAX-ACCESS read-only
    STATUS current
    DESCRIPTION
    "The AS External metric type for static routes."
    ::= { ospfRedistributeStatic 3 }

ospfNewCfgStaticMetricType OBJECT-TYPE
    SYNTAX INTEGER {
        none(1),
        type1(2),
        type2(3)
        }
    MAX-ACCESS read-write
    STATUS current
    DESCRIPTION
    "The AS External metric type for static routes."
    ::= { ospfRedistributeStatic 4 }

ospfCurCfgStaticOutRmapList OBJECT-TYPE
    SYNTAX OCTET STRING
    MAX-ACCESS read-only
    STATUS current
    DESCRIPTION
        "The route maps present in the out route map list. 
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected"
    ::= { ospfRedistributeStatic 5 }

ospfNewCfgStaticOutRmapList OBJECT-TYPE
    SYNTAX OCTET STRING
    MAX-ACCESS read-only
    STATUS current
    DESCRIPTION
        "The route maps present in the out route map list. 
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected"
    ::= { ospfRedistributeStatic 6 }

ospfNewCfgStaticAddOutRmap OBJECT-TYPE
    SYNTAX Integer32 
    MAX-ACCESS read-write
    STATUS current  
    DESCRIPTION
    "The route map to be add into out-rmap list. When read, 0 is returned."
    ::= { ospfRedistributeStatic 7 }

ospfNewCfgStaticRemoveOutRmap OBJECT-TYPE
    SYNTAX Integer32 
    MAX-ACCESS read-write
    STATUS current  
    DESCRIPTION
    "The route map to be removed from out-rmap list. When read, 
         0 is returned."
    ::= { ospfRedistributeStatic 8 }

ospfRedistributeEbgp    OBJECT IDENTIFIER ::= { ospfRouteRedistribution 2 }

ospfCurCfgEbgpMetric OBJECT-TYPE
    SYNTAX INTEGER (0..16777214)
    MAX-ACCESS read-only
    STATUS current
    DESCRIPTION
    "The export metric to be assigned to External BGP routes."
    ::= { ospfRedistributeEbgp 1 }

ospfNewCfgEbgpMetric OBJECT-TYPE
    SYNTAX INTEGER (0..16777214)
    MAX-ACCESS read-write
    STATUS current
    DESCRIPTION
    "The export metric to be assigned to External BGP routes."
    ::= { ospfRedistributeEbgp 2 }

ospfCurCfgEbgpMetricType OBJECT-TYPE
    SYNTAX INTEGER {
        none(1),
        type1(2),
        type2(3)
        }
    MAX-ACCESS read-only
    STATUS current
    DESCRIPTION
    "The AS External metric type for External BGP routes."
    ::= { ospfRedistributeEbgp 3 }

ospfNewCfgEbgpMetricType OBJECT-TYPE
    SYNTAX INTEGER {
        none(1),
        type1(2),
        type2(3)
        }
    MAX-ACCESS read-write
    STATUS current
    DESCRIPTION
    "The AS External metric type for External BGP routes."
    ::= { ospfRedistributeEbgp 4 }

ospfCurCfgEbgpOutRmapList OBJECT-TYPE
    SYNTAX OCTET STRING
    MAX-ACCESS read-only
    STATUS current
    DESCRIPTION
        "The route maps present in the out route map list. 
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected"
    ::= { ospfRedistributeEbgp 5 }

ospfNewCfgEbgpOutRmapList OBJECT-TYPE
    SYNTAX OCTET STRING
    MAX-ACCESS read-only
    STATUS current
    DESCRIPTION
        "The route maps present in the out route map list. 
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected"
    ::= { ospfRedistributeEbgp 6 }

ospfNewCfgEbgpAddOutRmap OBJECT-TYPE
    SYNTAX Integer32 
    MAX-ACCESS read-write
    STATUS current  
    DESCRIPTION
    "The route map to be add into out-rmap list. When read, 0 is returned."
    ::= { ospfRedistributeEbgp 7 }

ospfNewCfgEbgpRemoveOutRmap OBJECT-TYPE
    SYNTAX Integer32 
    MAX-ACCESS read-write
    STATUS current  
    DESCRIPTION
    "The route map to be removed from out-rmap list. When read, 
         0 is returned."
    ::= { ospfRedistributeEbgp 8 }

ospfRedistributeIbgp    OBJECT IDENTIFIER ::= { ospfRouteRedistribution 3 }

ospfCurCfgIbgpMetric OBJECT-TYPE
    SYNTAX INTEGER (0..16777214)
    MAX-ACCESS read-only
    STATUS current
    DESCRIPTION
    "The export metric for Internal BGP routes."
    ::= { ospfRedistributeIbgp 1 }

ospfNewCfgIbgpMetric OBJECT-TYPE
    SYNTAX INTEGER (0..16777214)
    MAX-ACCESS read-write
    STATUS current
    DESCRIPTION
    "The export metric for Internal BGP routes."
    ::= { ospfRedistributeIbgp 2 }

ospfCurCfgIbgpMetricType OBJECT-TYPE
    SYNTAX INTEGER {
        none(1),
        type1(2),
        type2(3)
        }
    MAX-ACCESS read-only
    STATUS current
    DESCRIPTION
    "The AS External metric type for Internal BGP routes."
    ::= { ospfRedistributeIbgp 3 }

ospfNewCfgIbgpMetricType OBJECT-TYPE
    SYNTAX INTEGER {
        none(1),
        type1(2),
        type2(3)
        }
    MAX-ACCESS read-write
    STATUS current
    DESCRIPTION
    "The AS External metric type for Internal BGP routes."
    ::= { ospfRedistributeIbgp 4 }

ospfCurCfgIbgpOutRmapList OBJECT-TYPE
    SYNTAX OCTET STRING
    MAX-ACCESS read-only
    STATUS current
    DESCRIPTION
        "The route maps present in the out route map list. 
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected"
    ::= { ospfRedistributeIbgp 5 }

ospfNewCfgIbgpOutRmapList OBJECT-TYPE
    SYNTAX OCTET STRING
    MAX-ACCESS read-only
    STATUS current
    DESCRIPTION
        "The route maps present in the out route map list. 
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected"
    ::= { ospfRedistributeIbgp 6 }

ospfNewCfgIbgpAddOutRmap OBJECT-TYPE
    SYNTAX Integer32 
    MAX-ACCESS read-write
    STATUS current  
    DESCRIPTION
    "The route map to be add into out-rmap list. When read, 0 is returned."
    ::= { ospfRedistributeIbgp 7 }

ospfNewCfgIbgpRemoveOutRmap OBJECT-TYPE
    SYNTAX Integer32 
    MAX-ACCESS read-write
    STATUS current  
    DESCRIPTION
    "The route map to be removed from out-rmap list. When read, 
         0 is returned."
    ::= { ospfRedistributeIbgp 8 }

ospfRedistributeFixed    OBJECT IDENTIFIER ::= { ospfRouteRedistribution 4 }

ospfCurCfgFixedMetric OBJECT-TYPE
    SYNTAX INTEGER (0..16777214)
    MAX-ACCESS read-only
    STATUS current
    DESCRIPTION
    "The export metric for fixed routes."
    ::= { ospfRedistributeFixed 1 }

ospfNewCfgFixedMetric OBJECT-TYPE
    SYNTAX INTEGER (0..16777214)
    MAX-ACCESS read-write
    STATUS current
    DESCRIPTION
    "The export metric for fixed routes."
    ::= { ospfRedistributeFixed 2 }

ospfCurCfgFixedMetricType OBJECT-TYPE
    SYNTAX INTEGER {
        none(1),
        type1(2),
        type2(3)
        }
    MAX-ACCESS read-only
    STATUS current
    DESCRIPTION
    "The AS External metric type for fixed routes."
    ::= { ospfRedistributeFixed 3 }

ospfNewCfgFixedMetricType OBJECT-TYPE
    SYNTAX INTEGER {
        none(1),
        type1(2),
        type2(3)
        }
    MAX-ACCESS read-write
    STATUS current
    DESCRIPTION
    "The AS External metric type for fixed routes."
    ::= { ospfRedistributeFixed 4 }

ospfCurCfgFixedOutRmapList OBJECT-TYPE
    SYNTAX OCTET STRING
    MAX-ACCESS read-only
    STATUS current
    DESCRIPTION
        "The route maps present in the out route map list. 
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected"
    ::= { ospfRedistributeFixed 5 }

ospfNewCfgFixedOutRmapList OBJECT-TYPE
    SYNTAX OCTET STRING
    MAX-ACCESS read-only
    STATUS current
    DESCRIPTION
        "The route maps present in the out route map list. 
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected"
    ::= { ospfRedistributeFixed 6 }

ospfNewCfgFixedAddOutRmap OBJECT-TYPE
    SYNTAX Integer32 
    MAX-ACCESS read-write
    STATUS current  
    DESCRIPTION
    "The route map to be add into out-rmap list. When read, 0 is returned."
    ::= { ospfRedistributeFixed 7 }

ospfNewCfgFixedRemoveOutRmap OBJECT-TYPE
    SYNTAX Integer32 
    MAX-ACCESS read-write
    STATUS current  
    DESCRIPTION
    "The route map to be removed from out-rmap list. When read, 
         0 is returned."
    ::= { ospfRedistributeFixed 8 }

ospfRedistributeRip    OBJECT IDENTIFIER ::= { ospfRouteRedistribution 5 }

ospfCurCfgRipMetric OBJECT-TYPE
    SYNTAX INTEGER (0..16777214)
    MAX-ACCESS read-only
    STATUS current
    DESCRIPTION
    "The export metric for RIP routes.  "
    ::= { ospfRedistributeRip 1 }

ospfNewCfgRipMetric OBJECT-TYPE
    SYNTAX INTEGER (0..16777214)
    MAX-ACCESS read-write
    STATUS current
    DESCRIPTION
    "The export metric for RIP routes.  "
    ::= { ospfRedistributeRip 2 }

ospfCurCfgRipMetricType OBJECT-TYPE
    SYNTAX INTEGER {
        none(1),
        type1(2),
        type2(3)
        }
    MAX-ACCESS read-only
    STATUS current
    DESCRIPTION
    "The AS External metric type for RIP routes."
    ::= { ospfRedistributeRip 3 }

ospfNewCfgRipMetricType OBJECT-TYPE
    SYNTAX INTEGER {
        none(1),
        type1(2),
        type2(3)
        }
    MAX-ACCESS read-write
    STATUS current
    DESCRIPTION
    "The AS External metric type for RIP routes."
    ::= { ospfRedistributeRip 4 }

ospfCurCfgRipOutRmapList OBJECT-TYPE
    SYNTAX OCTET STRING
    MAX-ACCESS read-only
    STATUS current
    DESCRIPTION
        "The route maps present in the out route map list. 
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected"
    ::= { ospfRedistributeRip 5 }

ospfNewCfgRipOutRmapList OBJECT-TYPE
    SYNTAX OCTET STRING
    MAX-ACCESS read-only
    STATUS current
    DESCRIPTION
        "The route maps present in the out route map list. 
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected"
    ::= { ospfRedistributeRip 6 }

ospfNewCfgRipAddOutRmap OBJECT-TYPE
    SYNTAX Integer32 
    MAX-ACCESS read-write
    STATUS current  
    DESCRIPTION
    "The route map to be add into out-rmap list. When read, 0 is returned."
    ::= { ospfRedistributeRip 7 }

ospfNewCfgRipRemoveOutRmap OBJECT-TYPE
    SYNTAX Integer32 
    MAX-ACCESS read-write
    STATUS current  
    DESCRIPTION
    "The route map to be removed from out-rmap list. When read, 
         0 is returned."
    ::= { ospfRedistributeRip 8 }

--
-- IP OSPFv3 configuration
--
ospf3General    OBJECT IDENTIFIER ::= { ospf3Cfg 1 }

ospf3IntfTableMaxSize OBJECT-TYPE
    SYNTAX Integer32
    MAX-ACCESS read-only
    STATUS current
    DESCRIPTION
        "The maximum number of rows in the OSPFv3 Interface table."
    ::= { ospf3General 1 }

ospf3AreaTableMaxSize OBJECT-TYPE
    SYNTAX Integer32
    MAX-ACCESS read-only
    STATUS current
    DESCRIPTION
        "The maximum number of rows in the OSPFv3 Area table."
    ::= { ospf3General 2 }

ospf3RangeTableMaxSize OBJECT-TYPE
    SYNTAX Integer32
    MAX-ACCESS read-only
    STATUS current
    DESCRIPTION
        "The maximum number of rows in the OSPFv3 Range table."
    ::= { ospf3General 3 }

ospf3ExtRangeTableMaxSize OBJECT-TYPE
    SYNTAX Integer32
    MAX-ACCESS read-only
    STATUS current
    DESCRIPTION
        "The maximum number of rows in the OSPFv3 Summary Prefix table."
    ::= { ospf3General 4 }

ospf3RedistTableMaxSize OBJECT-TYPE
    SYNTAX Integer32
    MAX-ACCESS read-only
    STATUS current
    DESCRIPTION
        "The maximum number of rows in the OSPFv3 Redist Config table."
    ::= { ospf3General 5 }

ospf3VirtIntfTableMaxSize OBJECT-TYPE
    SYNTAX Integer32
    MAX-ACCESS read-only
    STATUS current
    DESCRIPTION
        "The maximum number of rows in the OSPFv3 Virtual Interface
         table."
    ::= { ospf3General 6 }

ospf3HostTableMaxSize OBJECT-TYPE
    SYNTAX Integer32
    MAX-ACCESS read-only
    STATUS current
    DESCRIPTION
        "The maximum number of rows in the OSPFv3 Host table."
    ::= { ospf3General 7 }

 ospf3NbrTableMaxSize OBJECT-TYPE
    SYNTAX Integer32
    MAX-ACCESS read-only
    STATUS current
    DESCRIPTION
        "The maximum number of rows in the OSPFv3 Neighbor table."
    ::= { ospf3General 8 }

ospf3CurCfgState OBJECT-TYPE
    SYNTAX INTEGER {
        on(1),
        off(2)
        }
    MAX-ACCESS read-only
    STATUS current
    DESCRIPTION
    "OSPFv3 global state."
    ::= { ospf3General 9 }

ospf3NewCfgState OBJECT-TYPE
    SYNTAX INTEGER {
        on(1),
        off(2)
        }
    MAX-ACCESS read-write
    STATUS current
    DESCRIPTION
    "Globally turn OSPFv3 on or off."
    ::= { ospf3General 10 }

ospf3CurCfgRouterId OBJECT-TYPE
    SYNTAX IpAddress 
    MAX-ACCESS read-only
    STATUS current
    DESCRIPTION
    "The router ID." 
    ::= { ospf3General 11 }

ospf3NewCfgRouterId OBJECT-TYPE
    SYNTAX IpAddress 
    MAX-ACCESS read-create
    STATUS current
    DESCRIPTION
    "The router ID." 
    ::= { ospf3General 12 }

ospf3CurCfgAbrType OBJECT-TYPE
    SYNTAX INTEGER {
        standard(1),
        cisco(2),
        ibm(3)
        }
    MAX-ACCESS read-only
    STATUS current
    DESCRIPTION
    "OSPFv3 alternative ABR type."
    ::= { ospf3General 13 }

ospf3NewCfgAbrType OBJECT-TYPE
    SYNTAX INTEGER {
        standard(1),
        cisco(2),
        ibm(3)
        }
    MAX-ACCESS read-write
    STATUS current
    DESCRIPTION
    "Set the OSPFv3 alternative ABR type."
    ::= { ospf3General 14 }
 
ospf3CurCfgLSDB OBJECT-TYPE
    SYNTAX  INTEGER (-1..2147483647)
    MAX-ACCESS read-only
    STATUS current
    DESCRIPTION
    "The LSDB limit for external LSA."
    ::= { ospf3General 15 }

ospf3NewCfgLSDB OBJECT-TYPE
    SYNTAX  INTEGER (-1..2147483647)
    MAX-ACCESS read-write
    STATUS current
    DESCRIPTION
    "Set the LSDB limit for external LSA, -1 for none."
    ::= { ospf3General 16 }

ospf3CurCfgExitOverflow OBJECT-TYPE
    SYNTAX  Unsigned32 (0..4294967295)
    MAX-ACCESS read-only
    STATUS current
    DESCRIPTION
    "The exit overflow interval in seconds."
    ::= { ospf3General 17 }

ospf3NewCfgExitOverflow OBJECT-TYPE
    SYNTAX  Unsigned32 (0..4294967295)
    MAX-ACCESS read-write
    STATUS current
    DESCRIPTION
    "Set the exit overflow interval in seconds."
    ::= { ospf3General 18 }

 ospf3CurCfgReferenceBw OBJECT-TYPE
    SYNTAX  Unsigned32 (0..4294967295)
    MAX-ACCESS read-only
    STATUS current
    DESCRIPTION
    "The reference bandwidth for default interface metric calculation."
    ::= { ospf3General 19 }

ospf3NewCfgReferenceBw OBJECT-TYPE
    SYNTAX  Unsigned32 (0..4294967295)
    MAX-ACCESS read-write
    STATUS current
    DESCRIPTION
    "The reference bandwidth for default interface metric calculation."
    ::= { ospf3General 20 }

  ospf3CurCfgSpfDelay OBJECT-TYPE
    SYNTAX  INTEGER (0..65535)
    MAX-ACCESS read-only
    STATUS current
    DESCRIPTION
    "The delay between topology change and SPF calculation."
    ::= { ospf3General 21 }

ospf3NewCfgSpfDelay OBJECT-TYPE
    SYNTAX  INTEGER (0..65535)
    MAX-ACCESS read-write
    STATUS current
    DESCRIPTION
    "The delay between topology change and SPF calculation."
    ::= { ospf3General 22 }

 ospf3CurCfgSpfHold OBJECT-TYPE
    SYNTAX  INTEGER (0..65535)
    MAX-ACCESS read-only
    STATUS current
    DESCRIPTION
    "The hold time between two consecutive SPF calculation."
    ::= { ospf3General 23 }

ospf3NewCfgSpfHold OBJECT-TYPE
    SYNTAX  INTEGER (0..65535)
    MAX-ACCESS read-write
    STATUS current
    DESCRIPTION
    "The hold time between two consecutive SPF calculation."
    ::= { ospf3General 24 }


ospf3CurCfgNssaAsbrDfRtTrans OBJECT-TYPE
    SYNTAX INTEGER {
        on(1),
        off(2)
        }
    MAX-ACCESS read-only
    STATUS current
    DESCRIPTION
    "OSPFv3 state of setting P-bit by an NSSA internal ASBR."
    ::= { ospf3General 29 }

ospf3NewCfgNssaAsbrDfRtTrans OBJECT-TYPE
    SYNTAX INTEGER {
        on(1),
        off(2)
        }
    MAX-ACCESS read-write
    STATUS current
    DESCRIPTION
    "OSPFv3 state of setting P-bit by an NSSA internal ASBR."
    ::= { ospf3General 30 }

ospf3CurCfgAreaTable OBJECT-TYPE
    SYNTAX SEQUENCE OF Ospf3CurCfgAreaEntry
    MAX-ACCESS not-accessible
    STATUS current
    DESCRIPTION
      "The table of OSPFv3 area in the current configuration block."
    ::= { ospf3Cfg 2 }

ospf3CurCfgAreaEntry OBJECT-TYPE
    SYNTAX Ospf3CurCfgAreaEntry
    MAX-ACCESS not-accessible
    STATUS current
    DESCRIPTION
      "Information about a OSPFv3 area."
    INDEX { ospf3CurCfgAreaIndex }
    ::= { ospf3CurCfgAreaTable 1 }
 
Ospf3CurCfgAreaEntry ::= SEQUENCE {
    ospf3CurCfgAreaIndex         Integer32,
    ospf3CurCfgAreaId            IpAddress,
    ospf3CurCfgAreaStbInterval   INTEGER,
    ospf3CurCfgAreaType             INTEGER,
    ospf3CurCfgAreaNoSumm           INTEGER,
    ospf3CurCfgAreaDefaultMetric    INTEGER,
    ospf3CurCfgAreaDefaultMetricType    INTEGER,
    ospf3CurCfgAreaTranslRole           INTEGER,
    ospf3CurCfgAreaStatus        INTEGER
    }
 
ospf3CurCfgAreaIndex OBJECT-TYPE
    SYNTAX Integer32
    MAX-ACCESS read-only
    STATUS current
    DESCRIPTION
    "The OSPFv3 area number for which the OSPFv3 area table is related."
    ::= { ospf3CurCfgAreaEntry 1}

ospf3CurCfgAreaId OBJECT-TYPE
    SYNTAX IpAddress 
    MAX-ACCESS read-only
    STATUS current
    DESCRIPTION
    "The IP Address of the OSPFv3 area." 
    ::= { ospf3CurCfgAreaEntry 2 }

ospf3CurCfgAreaStbInterval OBJECT-TYPE
    SYNTAX INTEGER (1..255) 
    MAX-ACCESS read-only
    STATUS current
    DESCRIPTION
    "The stability interval for the NSSA area" 
    ::= { ospf3CurCfgAreaEntry 3 }

ospf3CurCfgAreaType OBJECT-TYPE
    SYNTAX INTEGER {
        transit(1),
        stub(2),
        nssa(3)
           }
    MAX-ACCESS   read-only
    STATUS  current
    DESCRIPTION
        "Type of Area.
        transit(1)
        stub(2)
        nssa(3)"
           
    ::= { ospf3CurCfgAreaEntry 4 }

ospf3CurCfgAreaNoSumm OBJECT-TYPE
    SYNTAX  INTEGER {
        disabled(0), 
     enabled(1)
        }
    MAX-ACCESS  read-only
    STATUS  current
    DESCRIPTION
        "Status
       disabled(0)
       enabled(1)"
    
    ::= { ospf3CurCfgAreaEntry 5 }

ospf3CurCfgAreaDefaultMetric OBJECT-TYPE
    SYNTAX  INTEGER (1..16777215)
    MAX-ACCESS  read-only
    STATUS  current
    DESCRIPTION
        "Metric for stub/NSSA area (1-16777215)"
    ::= { ospf3CurCfgAreaEntry 6 }

ospf3CurCfgAreaDefaultMetricType OBJECT-TYPE
    SYNTAX INTEGER (1..3) 
    MAX-ACCESS read-only
    STATUS current
    DESCRIPTION
    "Metric Type for stub/NSSA area (1-3)" 
    ::= { ospf3CurCfgAreaEntry 7 }

ospf3CurCfgAreaTranslRole OBJECT-TYPE
    SYNTAX INTEGER {
        always(1),
        candidate(2)
           }
    MAX-ACCESS   read-only
    STATUS  current
    DESCRIPTION
        "Translation role for the NSSA area.
        always(1)
        candidate(2)"
           
    ::= { ospf3CurCfgAreaEntry 8 }

ospf3CurCfgAreaStatus OBJECT-TYPE
    SYNTAX  INTEGER {
        disabled(0), 
     enabled(1)
        }
    MAX-ACCESS  read-only
    STATUS  current
    DESCRIPTION
        "Status
       disabled(0)
       enabled(1)"
    
    ::= { ospf3CurCfgAreaEntry 9 }

ospf3NewCfgAreaTable OBJECT-TYPE
    SYNTAX SEQUENCE OF Ospf3NewCfgAreaEntry
    MAX-ACCESS not-accessible
    STATUS current
    DESCRIPTION
      "The table of OSPFv3 Area configuration in the new configuration block."
    ::= { ospf3Cfg 3 }

ospf3NewCfgAreaEntry OBJECT-TYPE
    SYNTAX Ospf3NewCfgAreaEntry
    MAX-ACCESS not-accessible
    STATUS current
    DESCRIPTION
      "Information about a OSPFv3 area."
    INDEX { ospf3NewCfgAreaIndex }
    ::= { ospf3NewCfgAreaTable 1 }
 
Ospf3NewCfgAreaEntry ::= SEQUENCE {
    ospf3NewCfgAreaIndex         Integer32,
    ospf3NewCfgAreaId            IpAddress, 
    ospf3NewCfgAreaStbInterval   INTEGER,
    ospf3NewCfgAreaType             INTEGER,
    ospf3NewCfgAreaNoSumm           INTEGER,
    ospf3NewCfgAreaDefaultMetric    INTEGER,
    ospf3NewCfgAreaDefaultMetricType    INTEGER,
    ospf3NewCfgAreaTranslRole           INTEGER,
    ospf3NewCfgAreaStatus        INTEGER,
    ospf3NewCfgAreaDelete        INTEGER    
    }
 
ospf3NewCfgAreaIndex OBJECT-TYPE
    SYNTAX Integer32
    MAX-ACCESS read-only 
    STATUS current
    DESCRIPTION
    "The OSPFv3 area number for which the OSPFv3 area table is related."
    ::= { ospf3NewCfgAreaEntry 1}

ospf3NewCfgAreaId OBJECT-TYPE
    SYNTAX IpAddress 
    MAX-ACCESS read-create
    STATUS current
    DESCRIPTION
    "The IP Address of the OSPFv3 area." 
    ::= { ospf3NewCfgAreaEntry 2 }

ospf3NewCfgAreaStbInterval OBJECT-TYPE
    SYNTAX INTEGER (1..255) 
    MAX-ACCESS read-create
    STATUS current
    DESCRIPTION
    "The Stability interval for the NSSA area." 
    ::= { ospf3NewCfgAreaEntry 3 }

ospf3NewCfgAreaType OBJECT-TYPE
    SYNTAX INTEGER {
        transit(1),
        stub(2),
        nssa(3)
           }
    MAX-ACCESS   read-write
    STATUS  current
    DESCRIPTION
        "Type of Area.
        transit(1)
        stub(2)
           nssa(3)"
           
    ::= { ospf3NewCfgAreaEntry 4 }

ospf3NewCfgAreaNoSumm OBJECT-TYPE
    SYNTAX  INTEGER {
        disabled(0), 
     enabled(1)
        }
    MAX-ACCESS  read-create
    STATUS  current
    DESCRIPTION
        "Status
       disabled(0)
       enabled(1)"
    
    ::= { ospf3NewCfgAreaEntry 5 }

ospf3NewCfgAreaDefaultMetric OBJECT-TYPE
    SYNTAX  INTEGER (1..16777215)
    MAX-ACCESS  read-create
    STATUS  current
    DESCRIPTION
        "Metric for stub/NSSA area (1-16777215)"
    ::= { ospf3NewCfgAreaEntry 6 }

ospf3NewCfgAreaDefaultMetricType OBJECT-TYPE
    SYNTAX INTEGER (1..3) 
    MAX-ACCESS read-create
    STATUS current
    DESCRIPTION
    "Metric Type for stub/NSSA area (1-3)" 
    ::= { ospf3NewCfgAreaEntry 7 }
 
ospf3NewCfgAreaTranslRole OBJECT-TYPE
    SYNTAX INTEGER {
        always(1),
        candidate(2)
           }
        MAX-ACCESS  read-create
    STATUS  current
    DESCRIPTION
        "Translation role for the NSSA area.
        always(1)
        candidate(2)"
    ::= { ospf3NewCfgAreaEntry 8 }

ospf3NewCfgAreaStatus OBJECT-TYPE
    SYNTAX  INTEGER {
        disabled(0), 
     enabled(1)
        }
    MAX-ACCESS  read-write
    STATUS current
    DESCRIPTION
        "Status
       disabled(0)
       enabled(1)"
    
    ::= { ospf3NewCfgAreaEntry 9 }

ospf3NewCfgAreaDelete OBJECT-TYPE
   SYNTAX INTEGER {
    no(0),
    yes(1)
    }
   MAX-ACCESS read-write
   STATUS current
   DESCRIPTION
    "Delete the area
        no(0),
            yes(1)"

    ::= { ospf3NewCfgAreaEntry 10 }


-- OSPFv3 Host Table

ospf3CurCfgHostTable OBJECT-TYPE
    SYNTAX SEQUENCE OF Ospf3CurCfgHostEntry
    MAX-ACCESS not-accessible
    STATUS current
    DESCRIPTION
      "The table of OSPFv3 Host configuration."
    ::= { ospf3Cfg 4 }

ospf3CurCfgHostEntry OBJECT-TYPE
    SYNTAX Ospf3CurCfgHostEntry
    MAX-ACCESS not-accessible
    STATUS current
    DESCRIPTION
      "Information about a OSPFv3 host."
    INDEX { ospf3CurCfgHostIndex }
    ::= { ospf3CurCfgHostTable 1 }
 
Ospf3CurCfgHostEntry ::= SEQUENCE {
    ospf3CurCfgHostIndex         Integer32,
    ospf3CurCfgHostIpAddr        DisplayString,
    ospf3CurCfgHostAreaIndex     Integer32,
    ospf3CurCfgHostCost          INTEGER,
    ospf3CurCfgHostState        INTEGER
    }
 
ospf3CurCfgHostIndex OBJECT-TYPE
    SYNTAX Integer32
    MAX-ACCESS read-only
    STATUS current
    DESCRIPTION
    "The OSPFv3 host number for which the OSPFv3 host table is related."
    ::= { ospf3CurCfgHostEntry 1}

ospf3CurCfgHostIpAddr OBJECT-TYPE
    SYNTAX DisplayString 
    MAX-ACCESS read-only
    STATUS current
    DESCRIPTION
    "The IPv6 Address of the OSPFv3 host." 
    ::= { ospf3CurCfgHostEntry 2 }

ospf3CurCfgHostAreaIndex OBJECT-TYPE
    SYNTAX Integer32
    MAX-ACCESS read-only
    STATUS current
    DESCRIPTION
    "The area index."
    ::= { ospf3CurCfgHostEntry 3 }

ospf3CurCfgHostCost OBJECT-TYPE
    SYNTAX  INTEGER (1..65535)
    MAX-ACCESS  read-only
    STATUS  current
    DESCRIPTION
        "The cost of the OSPFv3 host."
    ::= { ospf3CurCfgHostEntry 4 }

ospf3CurCfgHostState OBJECT-TYPE
    SYNTAX  INTEGER  {
    enabled(2),
    disabled(3)
    }
    MAX-ACCESS  read-only
    STATUS  current
    DESCRIPTION
        "Enable or disable an OSPFv3 Host"
    ::= { ospf3CurCfgHostEntry 5 }

ospf3NewCfgHostTable OBJECT-TYPE
    SYNTAX SEQUENCE OF Ospf3NewCfgHostEntry
    MAX-ACCESS not-accessible
    STATUS current
    DESCRIPTION
      "The table of OSPFv3 Host configuration."
    ::= { ospf3Cfg 5 }

ospf3NewCfgHostEntry OBJECT-TYPE
    SYNTAX Ospf3NewCfgHostEntry
    MAX-ACCESS not-accessible
    STATUS current
    DESCRIPTION
      "Information about a OSPFv3 host."
    INDEX { ospf3NewCfgHostIndex }
    ::= { ospf3NewCfgHostTable 1 }
 
Ospf3NewCfgHostEntry ::= SEQUENCE {
    ospf3NewCfgHostIndex         Integer32,
    ospf3NewCfgHostIpAddr        DisplayString, 
    ospf3NewCfgHostAreaIndex     Integer32,
    ospf3NewCfgHostCost          INTEGER,
    ospf3NewCfgHostState        INTEGER,
    ospf3NewCfgHostDelete        INTEGER
    }
 
ospf3NewCfgHostIndex OBJECT-TYPE
    SYNTAX Integer32
    MAX-ACCESS read-only 
    STATUS current
    DESCRIPTION
    "The OSPFv3 host number for which the OSPFv3 host table is related."
    ::= { ospf3NewCfgHostEntry 1}

ospf3NewCfgHostIpAddr OBJECT-TYPE
    SYNTAX DisplayString  (SIZE(0..40)) 
    MAX-ACCESS read-create
    STATUS current
    DESCRIPTION
    "The IP6 Address of the OSPFv3 host.
     Address should be 4-byte haxadecimal colon notation.
     Valid IPv6 address should be in any of the following forms
     xxxx:xxxx:xxxx:xxxx:xxxx:xxxx:xxxx:xxxx or
     xxxx::xxxx:xxxx:xxxx:xxxx or ::xxxx"
    ::= { ospf3NewCfgHostEntry 2 }

ospf3NewCfgHostAreaIndex OBJECT-TYPE
    SYNTAX Integer32 
    MAX-ACCESS read-create
    STATUS current
    DESCRIPTION
    "The OSPFv3 area index."
    ::= { ospf3NewCfgHostEntry 3 }

ospf3NewCfgHostCost OBJECT-TYPE
    SYNTAX  INTEGER (1..65535)
    MAX-ACCESS  read-create
    STATUS  current
    DESCRIPTION
        "The cost of the OSPFv3 host."
    ::= { ospf3NewCfgHostEntry 4 }

ospf3NewCfgHostState OBJECT-TYPE
    SYNTAX  INTEGER  {
    enabled(2),
    disabled(3)
    }
    MAX-ACCESS  read-create
    STATUS  current
    DESCRIPTION
        "Enable or disable an OSPFv3 Host"
    ::= { ospf3NewCfgHostEntry 5 }

ospf3NewCfgHostDelete  OBJECT-TYPE
    SYNTAX  INTEGER {
        no(0),
        yes(1)
        }
    MAX-ACCESS read-write
    STATUS current
    DESCRIPTION
    "Delete the OSPFv3 host:
         no(0),
         yes(1)" 
    ::= { ospf3NewCfgHostEntry 6 }

-- OSPFv3 Neighbor Table

ospf3CurCfgNbrTable OBJECT-TYPE
    SYNTAX SEQUENCE OF Ospf3CurCfgNbrEntry
    MAX-ACCESS not-accessible
    STATUS current
    DESCRIPTION
      "The table of OSPFv3 Neighbor configuration."
    ::= { ospf3Cfg 6 }

ospf3CurCfgNbrEntry OBJECT-TYPE
    SYNTAX Ospf3CurCfgNbrEntry
    MAX-ACCESS not-accessible
    STATUS current
    DESCRIPTION
      "Information about a OSPFv3 neighbor."
    INDEX { ospf3CurCfgNbrIndex }
    ::= { ospf3CurCfgNbrTable 1 }
 
Ospf3CurCfgNbrEntry ::= SEQUENCE {
    ospf3CurCfgNbrIndex         Integer32,
    ospf3CurCfgNbrIpAddr       DisplayString,
    ospf3CurCfgNbrIntfIndex   Integer32,
    ospf3CurCfgNbrPriority       INTEGER,
    ospf3CurCfgNbrState     INTEGER
    }
 
ospf3CurCfgNbrIndex OBJECT-TYPE
    SYNTAX Integer32
    MAX-ACCESS read-only
    STATUS current
    DESCRIPTION
    "The OSPFv3 neighbor number for which the OSPFv3 neighbor table is related."
    ::= { ospf3CurCfgNbrEntry 1}

ospf3CurCfgNbrIpAddr OBJECT-TYPE
    SYNTAX DisplayString 
    MAX-ACCESS read-only
    STATUS current
    DESCRIPTION
    "The IPv6 Address of the OSPFv3 neighbor." 
    ::= { ospf3CurCfgNbrEntry 2 }

ospf3CurCfgNbrIntfIndex OBJECT-TYPE
    SYNTAX Integer32
    MAX-ACCESS read-only
    STATUS current
    DESCRIPTION
    "The interface index."
    ::= { ospf3CurCfgNbrEntry 3 }

ospf3CurCfgNbrPriority OBJECT-TYPE
    SYNTAX  INTEGER (0..255)
    MAX-ACCESS  read-only
    STATUS  current
    DESCRIPTION
        "The priority of the OSPFv3 neighbor."
    ::= { ospf3CurCfgNbrEntry 4 }

ospf3CurCfgNbrState OBJECT-TYPE
    SYNTAX  INTEGER  {
    enabled(2),
    disabled(3)
    }
    MAX-ACCESS  read-only
    STATUS  current
    DESCRIPTION
        "Enable or disable an OSPFv3 neighbor"
    ::= { ospf3CurCfgNbrEntry 5 }

ospf3NewCfgNbrTable OBJECT-TYPE
    SYNTAX SEQUENCE OF Ospf3NewCfgNbrEntry
    MAX-ACCESS not-accessible
    STATUS current
    DESCRIPTION
      "The table of OSPFv3 Neighbor configuration."
    ::= { ospf3Cfg 7 }

ospf3NewCfgNbrEntry OBJECT-TYPE
    SYNTAX Ospf3NewCfgNbrEntry
    MAX-ACCESS not-accessible
    STATUS current
    DESCRIPTION
      "Information about a OSPFv3 neighbor."
    INDEX { ospf3NewCfgNbrIndex }
    ::= { ospf3NewCfgNbrTable 1 }
 
Ospf3NewCfgNbrEntry ::= SEQUENCE {
    ospf3NewCfgNbrIndex         Integer32,
    ospf3NewCfgNbrIpAddr       DisplayString, 
    ospf3NewCfgNbrIntfIndex   Integer32,
    ospf3NewCfgNbrPriority       INTEGER,
    ospf3NewCfgNbrState   INTEGER,
    ospf3NewCfgNbrDelete        INTEGER
    }
 
ospf3NewCfgNbrIndex OBJECT-TYPE
    SYNTAX Integer32
    MAX-ACCESS read-only 
    STATUS current
    DESCRIPTION
    "The OSPFv3 neighbor number for which the OSPFv3 neighbor table is related."
    ::= { ospf3NewCfgNbrEntry 1}

ospf3NewCfgNbrIpAddr OBJECT-TYPE
    SYNTAX DisplayString  (SIZE(0..40)) 
    MAX-ACCESS read-create
    STATUS current
    DESCRIPTION
    "The IP6 Address of the OSPFv3 neighbor.
     Address should be 4-byte haxadecimal colon notation.
     Valid IPv6 address should be in any of the following forms
     xxxx:xxxx:xxxx:xxxx:xxxx:xxxx:xxxx:xxxx or
     xxxx::xxxx:xxxx:xxxx:xxxx or ::xxxx"
    ::= { ospf3NewCfgNbrEntry 2 }

ospf3NewCfgNbrIntfIndex OBJECT-TYPE
    SYNTAX Integer32 
    MAX-ACCESS read-create
    STATUS current
    DESCRIPTION
    "The OSPFv3 interface index."
    ::= { ospf3NewCfgNbrEntry 3 }

ospf3NewCfgNbrPriority OBJECT-TYPE
    SYNTAX  INTEGER (0..255)
    MAX-ACCESS  read-create
    STATUS  current
    DESCRIPTION
        "The cost of the OSPFv3 neighbor."
    ::= { ospf3NewCfgNbrEntry 4 }

ospf3NewCfgNbrState OBJECT-TYPE
    SYNTAX  INTEGER  {
    enabled(2),
    disabled(3)
    }
    MAX-ACCESS  read-create
    STATUS  current
    DESCRIPTION
        "Enable or disable an OSPFv3 Neighbor"
    ::= { ospf3NewCfgNbrEntry 5 }

ospf3NewCfgNbrDelete  OBJECT-TYPE
    SYNTAX  INTEGER {
        no(0),
        yes(1)
        }
    MAX-ACCESS read-write
    STATUS current
    DESCRIPTION
    "Delete the OSPFv3 neighbor:
         no(0),
         yes(1)" 
    ::= { ospf3NewCfgNbrEntry 6 }

ospf3CurCfgIntfTable OBJECT-TYPE
    SYNTAX SEQUENCE OF Ospf3CurCfgIntfEntry
    MAX-ACCESS not-accessible
    STATUS current
    DESCRIPTION
      "The table of OSPFv3 Interface in the current configuration block."
    ::= { ospf3Cfg 8 }

ospf3CurCfgIntfEntry OBJECT-TYPE
    SYNTAX Ospf3CurCfgIntfEntry
    MAX-ACCESS not-accessible
    STATUS current
    DESCRIPTION
      "Information about an OSPFv3 Interface."
    INDEX { ospf3CurCfgIntfIndex }
    ::= { ospf3CurCfgIntfTable 1 }
 
Ospf3CurCfgIntfEntry ::= SEQUENCE {
    ospf3CurCfgIntfIndex         Integer32,
    ospf3CurCfgIntfInstId        INTEGER,
    ospf3CurCfgIntfArea          INTEGER,
    ospf3CurCfgIntfCost          INTEGER,
    ospf3CurCfgIntfPrio          INTEGER,
    ospf3CurCfgIntfHello         INTEGER,
    ospf3CurCfgIntfDead          INTEGER,
    ospf3CurCfgIntfPoll             Unsigned32,
    ospf3CurCfgIntfTrans         INTEGER,
    ospf3CurCfgIntfRetra         INTEGER,
    ospf3CurCfgIntfPassive       INTEGER,
    ospf3CurCfgIntfNetworkType                  INTEGER,
    ospf3CurCfgIntfStatus        INTEGER
    ,
    ospf3CurCfgIntfAuthSpi            Unsigned32,
    ospf3CurCfgIntfAuthEnable         INTEGER,
    ospf3CurCfgIntfAuthType           INTEGER,
    ospf3CurCfgIntfAuthKey            OCTET STRING,
    ospf3CurCfgIntfEncrySpi           Unsigned32,
    ospf3CurCfgIntfEncryEnable        INTEGER,
    ospf3CurCfgIntfEncryType          INTEGER,
    ospf3CurCfgIntfEncryKey           OCTET STRING,
    ospf3CurCfgIntfEncryAuthType      INTEGER,
    ospf3CurCfgIntfEncryAuthKey       OCTET STRING
    ,
    ospf3CurCfgIntfLsaSupress                   INTEGER
    }
 
ospf3CurCfgIntfIndex OBJECT-TYPE
    SYNTAX Integer32
    MAX-ACCESS read-only
    STATUS current
    DESCRIPTION
    "The OSPFv3 Interface number for which the OSPFv3 Interface table is 
         related."
    ::= { ospf3CurCfgIntfEntry 1}

ospf3CurCfgIntfInstId  OBJECT-TYPE
    SYNTAX INTEGER (0..255)
    MAX-ACCESS read-only
    STATUS current
    DESCRIPTION
        "Interface Instance Id"
    ::= { ospf3CurCfgIntfEntry 2 }

ospf3CurCfgIntfArea OBJECT-TYPE
    SYNTAX INTEGER (0..2) 
    MAX-ACCESS read-only
    STATUS current
    DESCRIPTION
    "The index of the area that the interface belongs" 
    ::= { ospf3CurCfgIntfEntry 3 }

ospf3CurCfgIntfCost  OBJECT-TYPE 
    SYNTAX INTEGER (0..65535) 
    MAX-ACCESS read-only
    STATUS current
    DESCRIPTION
    "Interface cost" 
    ::= { ospf3CurCfgIntfEntry 4 }

ospf3CurCfgIntfPrio   OBJECT-TYPE
   SYNTAX INTEGER (1..255) 
    MAX-ACCESS read-only
    STATUS current 
    DESCRIPTION
    "Interface router priority" 
    ::= { ospf3CurCfgIntfEntry 5 }

ospf3CurCfgIntfHello  OBJECT-TYPE 
    SYNTAX INTEGER (1..65535) 
    MAX-ACCESS read-only
    STATUS current
    DESCRIPTION
    "Hello interval" 
    ::= { ospf3CurCfgIntfEntry 6 }

ospf3CurCfgIntfDead   OBJECT-TYPE
   SYNTAX INTEGER (1..65535) 
    MAX-ACCESS read-only
    STATUS current 
    DESCRIPTION
    "Dead interval" 
    ::= { ospf3CurCfgIntfEntry 7 }

ospf3CurCfgIntfPoll   OBJECT-TYPE
   SYNTAX Unsigned32 (1..4294967295) 
    MAX-ACCESS read-only
    STATUS current 
    DESCRIPTION
    "Poll interval(1..4294967295)" 
    ::= { ospf3CurCfgIntfEntry 8 }

ospf3CurCfgIntfTrans  OBJECT-TYPE
   SYNTAX INTEGER (1..1800) 
    MAX-ACCESS read-only
    STATUS current
    DESCRIPTION
    "Transmit delay" 
    ::= { ospf3CurCfgIntfEntry 9 }
    
ospf3CurCfgIntfRetra OBJECT-TYPE
    SYNTAX INTEGER (1..1800) 
    MAX-ACCESS read-only
    STATUS current
    DESCRIPTION
    "Retransmit interval" 
    ::= { ospf3CurCfgIntfEntry 10 }

ospf3CurCfgIntfPassive  OBJECT-TYPE
    SYNTAX  INTEGER {
        disabled(0),
        enabled(1)
        }
    MAX-ACCESS read-only
    STATUS current
    DESCRIPTION
    "Passive interface
    disabled(0),
        enabled(1)" 
    ::= { ospf3CurCfgIntfEntry 11 }

ospf3CurCfgIntfNetworkType OBJECT-TYPE
    SYNTAX INTEGER {
        broadcast(1),
        non-broadcast(2),
        point-to-point(3),
        point-to-multipoint(4)
           }
    MAX-ACCESS   read-only
    STATUS  current
    DESCRIPTION
        "Network Type.
        broadcast(1),
        non-broadcast(2),
        point-to-point(3),
        point-to-multipoint(4)"
           
    ::= { ospf3CurCfgIntfEntry 12 }


ospf3CurCfgIntfStatus  OBJECT-TYPE
    SYNTAX  INTEGER {
        disabled(0),
        enabled(1)
        }
    MAX-ACCESS read-only
    STATUS current
    DESCRIPTION
    "Status of the interface
    disabled(0),
        enabled(1)" 
    ::= { ospf3CurCfgIntfEntry 16 }

ospf3CurCfgIntfAuthSpi  OBJECT-TYPE
    SYNTAX Unsigned32 (256..4294967295)
    MAX-ACCESS read-only
    STATUS current
    DESCRIPTION
        "Spi Id(256 - 4294967295)"
    ::= { ospf3CurCfgIntfEntry 17 }

ospf3CurCfgIntfAuthEnable OBJECT-TYPE
    SYNTAX  INTEGER {
        disabled(0),
        enabled(1)
        }
    MAX-ACCESS read-only
    STATUS current
    DESCRIPTION
    "Status
     disabled(0),
     enabled(1)" 
    ::= { ospf3CurCfgIntfEntry 18 }

ospf3CurCfgIntfAuthType  OBJECT-TYPE 
    SYNTAX  INTEGER {
        none(0),
        md5(2),
        sha1(1)
        } 
    MAX-ACCESS read-only
    STATUS current
    DESCRIPTION
    "Authentication Type
        none(0),
        md5(2),
        sha1(1)" 
    ::= { ospf3CurCfgIntfEntry 19 }

ospf3CurCfgIntfAuthKey   OBJECT-TYPE
    SYNTAX OCTET STRING (SIZE(4..40)) 
    MAX-ACCESS read-only
    STATUS current 
    DESCRIPTION
    "Authentication Key
      Hex-string MD5 key - 32 chars (128 bits)
      Hex-string SHA-1 key - 40 chars (160 bits)" 
    ::= { ospf3CurCfgIntfEntry 20 }

ospf3CurCfgIntfEncrySpi  OBJECT-TYPE
    SYNTAX Unsigned32 (256..4294967295)
    MAX-ACCESS read-only
    STATUS current
    DESCRIPTION
        "Spi Id(256 - 4294967295)"
    ::= { ospf3CurCfgIntfEntry 21 }

ospf3CurCfgIntfEncryEnable OBJECT-TYPE
    SYNTAX  INTEGER {
        disabled(0),
        enabled(1)
        }
    MAX-ACCESS read-only
    STATUS current
    DESCRIPTION
    "Status
     disabled(0),
     enabled(1)" 
    ::= { ospf3CurCfgIntfEntry 22 }

ospf3CurCfgIntfEncryType  OBJECT-TYPE 
    SYNTAX  INTEGER {
        null(0),
        tripledes(2),
        aes(3)
        } 
    MAX-ACCESS read-only
    STATUS current
    DESCRIPTION
    "Encryption Type
        null(0),
        3des(2),
        aes(3)"
   ::= { ospf3CurCfgIntfEntry 23 }

ospf3CurCfgIntfEncryKey   OBJECT-TYPE
    SYNTAX OCTET STRING (SIZE(4..48)) 
    MAX-ACCESS read-only
    STATUS current 
    DESCRIPTION
    "Encryption Key
      Hex-string AES key - 32 chars (128 bits)
      Hex-string 3DES key - 48 chars (192 bits)" 
    ::= { ospf3CurCfgIntfEntry 24 }


ospf3CurCfgIntfEncryAuthType  OBJECT-TYPE
    SYNTAX  INTEGER {
        none(0),
        md5(2),
        sha1(1)
        }
    MAX-ACCESS read-only
    STATUS current
    DESCRIPTION
    "Encryption Authentication Type
        none(0),
        md5(2),
        sha1(1)"
    ::= { ospf3CurCfgIntfEntry 25 }

ospf3CurCfgIntfEncryAuthKey   OBJECT-TYPE
    SYNTAX OCTET STRING (SIZE(4..40))
    MAX-ACCESS read-only
    STATUS current
    DESCRIPTION
    "Encryption Authentication Key
    Hex-string MD5 key - 32 chars (128 bits)
    Hex-string SHA-1 key - 40 chars (160 bits)"
    ::= { ospf3CurCfgIntfEntry 26 }

ospf3CurCfgIntfLsaSupress  OBJECT-TYPE
    SYNTAX  INTEGER {
        disabled(0),
        enabled(1)
        }
    MAX-ACCESS read-only
    STATUS current
    DESCRIPTION
    "LSA Supression on interface
    disabled(0),
        enabled(1)"
    ::= { ospf3CurCfgIntfEntry 27 }

ospf3NewCfgIntfTable OBJECT-TYPE
    SYNTAX SEQUENCE OF Ospf3NewCfgIntfEntry
    MAX-ACCESS not-accessible
    STATUS current
    DESCRIPTION
      "The table of OSPFv3 interface in the new configuration block."
    ::= { ospf3Cfg 9 }

ospf3NewCfgIntfEntry OBJECT-TYPE
    SYNTAX Ospf3NewCfgIntfEntry
    MAX-ACCESS not-accessible
    STATUS current
    DESCRIPTION
      "Information about an OSPFv3 interface."
    INDEX { ospf3NewCfgIntfIndex }
    ::= { ospf3NewCfgIntfTable 1 }
 
Ospf3NewCfgIntfEntry ::= SEQUENCE {
    ospf3NewCfgIntfIndex         Integer32,
    ospf3NewCfgIntfInstId        INTEGER,
    ospf3NewCfgIntfArea          INTEGER,
    ospf3NewCfgIntfCost     INTEGER,
    ospf3NewCfgIntfPrio     INTEGER,
    ospf3NewCfgIntfHello         INTEGER,
    ospf3NewCfgIntfPoll             Unsigned32,
    ospf3NewCfgIntfDead          INTEGER,
    ospf3NewCfgIntfTrans         INTEGER,
    ospf3NewCfgIntfRetra         INTEGER,
    ospf3NewCfgIntfPassive       INTEGER,
    ospf3NewCfgIntfNetworkType                  INTEGER,
    ospf3NewCfgIntfStatus        INTEGER, 
    ospf3NewCfgIntfDelete        INTEGER
    ,
    ospf3NewCfgIntfAuthSpi            Unsigned32,
    ospf3NewCfgIntfAuthEnable         INTEGER,
    ospf3NewCfgIntfAuthType           INTEGER,
    ospf3NewCfgIntfAuthKey            OCTET STRING,
    ospf3NewCfgIntfAuthReset          INTEGER,
    ospf3NewCfgIntfEncrySpi           Unsigned32,
    ospf3NewCfgIntfEncryEnable        INTEGER,
    ospf3NewCfgIntfEncryType          INTEGER,
    ospf3NewCfgIntfEncryKey           OCTET STRING,
    ospf3NewCfgIntfEncryAuthType      INTEGER,
    ospf3NewCfgIntfEncryAuthKey       OCTET STRING,
    ospf3NewCfgIntfEncryReset         INTEGER
    ,
    ospf3NewCfgIntfLsaSupress                   INTEGER
    }
 
ospf3NewCfgIntfIndex OBJECT-TYPE
    SYNTAX Integer32
    MAX-ACCESS read-only
    STATUS current
    DESCRIPTION
    "The OSPFv3 Interface number for which the OSPFv3 Interface table is 
         related."
    ::= { ospf3NewCfgIntfEntry 1}

ospf3NewCfgIntfInstId   OBJECT-TYPE
    SYNTAX INTEGER (0..255)
    MAX-ACCESS read-create
    STATUS current
    DESCRIPTION
        "Interface Instance Id (0..255)"
    ::= { ospf3NewCfgIntfEntry 2 }

ospf3NewCfgIntfArea OBJECT-TYPE
    SYNTAX INTEGER (0..2) 
    MAX-ACCESS read-create
    STATUS current
    DESCRIPTION
    "The index of the area that the interface belongs (0..2)" 
    ::= { ospf3NewCfgIntfEntry 3 }

ospf3NewCfgIntfCost  OBJECT-TYPE 
    SYNTAX INTEGER (0..65535) 
    MAX-ACCESS read-create
    STATUS current
    DESCRIPTION
    "Interface cost(1..65535) and 0 for none" 
    ::= { ospf3NewCfgIntfEntry 4 }

ospf3NewCfgIntfPrio   OBJECT-TYPE
   SYNTAX INTEGER (0..255) 
    MAX-ACCESS read-create
    STATUS current 
    DESCRIPTION
    "Interface router priority(0..255)" 
    ::= { ospf3NewCfgIntfEntry 5 }

ospf3NewCfgIntfHello  OBJECT-TYPE 
    SYNTAX INTEGER (1..65535) 
    MAX-ACCESS read-create
    STATUS current
    DESCRIPTION
    "Hello interval(1..65535)" 
    ::= { ospf3NewCfgIntfEntry 6 }

ospf3NewCfgIntfDead   OBJECT-TYPE
   SYNTAX INTEGER (1..65535) 
    MAX-ACCESS read-create
    STATUS current
    DESCRIPTION
    "Dead interval(1..65535)" 
    ::= { ospf3NewCfgIntfEntry 7 }

ospf3NewCfgIntfPoll   OBJECT-TYPE
   SYNTAX Unsigned32 (1..4294967295) 
    MAX-ACCESS read-create
    STATUS current 
    DESCRIPTION
    "Poll interval(1..4294967295)" 
    ::= { ospf3NewCfgIntfEntry 8 }

ospf3NewCfgIntfTrans  OBJECT-TYPE
   SYNTAX INTEGER (1..1800) 
    MAX-ACCESS read-create
    STATUS current
    DESCRIPTION
    "Transmit delay(1..1800)" 
    ::= { ospf3NewCfgIntfEntry 9 }

ospf3NewCfgIntfRetra OBJECT-TYPE
  SYNTAX INTEGER (1..1800) 
    MAX-ACCESS read-create
    STATUS current
    DESCRIPTION
    "Retransmit interval(1..1800)" 
    ::= { ospf3NewCfgIntfEntry 10 }

ospf3NewCfgIntfPassive  OBJECT-TYPE
    SYNTAX  INTEGER {
        disabled(0),
        enabled(1)
        }
    MAX-ACCESS read-create
    STATUS current
    DESCRIPTION
    "Passive interface
    disabled(0),
        enabled(1)" 
    ::= { ospf3NewCfgIntfEntry 11 }

ospf3NewCfgIntfNetworkType OBJECT-TYPE
    SYNTAX INTEGER {
        broadcast(1),
        non-broadcast(2),
        point-to-point(3),
        point-to-multipoint(4)
           }
    MAX-ACCESS   read-create
    STATUS  current
    DESCRIPTION
        "Network Type.
        broadcast(1),
        non-broadcast(2),
        point-to-point(3),
        point-to-multipoint(4)"
           
    ::= { ospf3NewCfgIntfEntry 12 }


ospf3NewCfgIntfStatus  OBJECT-TYPE
    SYNTAX  INTEGER {
        disabled(0),
        enabled(1)
        }
    MAX-ACCESS read-create
    STATUS current
    DESCRIPTION
    "Status of the interface
    disabled(0),
        enabled(1)" 
    ::= { ospf3NewCfgIntfEntry 16 }

ospf3NewCfgIntfDelete  OBJECT-TYPE
    SYNTAX  INTEGER {
        other(0),
        delete(1)
        }
    MAX-ACCESS read-write
    STATUS current
    DESCRIPTION
    "Delete the interface
         other(0),
         delete(1)" 
    ::= { ospf3NewCfgIntfEntry 17 }

ospf3NewCfgIntfAuthSpi  OBJECT-TYPE
    SYNTAX Unsigned32 (256..4294967295)
    MAX-ACCESS read-write
    STATUS current
    DESCRIPTION
        "Authentication Spi Id(256 - 4294967295)"
    ::= { ospf3NewCfgIntfEntry 18 }

ospf3NewCfgIntfAuthEnable OBJECT-TYPE
    SYNTAX  INTEGER {
        disabled(0),
        enabled(1)
        }
    MAX-ACCESS read-write
    STATUS current
    DESCRIPTION
    "Authentication Status
        disabled(0),
        enabled(1)" 
    ::= { ospf3NewCfgIntfEntry 19 }

ospf3NewCfgIntfAuthType  OBJECT-TYPE 
    SYNTAX  INTEGER {
        none(0),
        md5(2),
        sha1(1)
        } 
    MAX-ACCESS read-write
    STATUS current
    DESCRIPTION
    "Authentication Type
        none(0),
        md5(2),
        sha1(1)" 
    ::= { ospf3NewCfgIntfEntry 20 }

ospf3NewCfgIntfAuthKey   OBJECT-TYPE
    SYNTAX OCTET STRING (SIZE(4..40)) 
    MAX-ACCESS read-write
    STATUS current 
    DESCRIPTION
    "Authentication Type
     Hex-string MD5 key - 32 chars (128 bits),
     Hex-string SHA-1 key - 40 chars (160 bits)" 
    ::= { ospf3NewCfgIntfEntry 21 }

ospf3NewCfgIntfAuthReset OBJECT-TYPE
    SYNTAX  INTEGER {
        other(0),
        reset(1)
        }
    MAX-ACCESS read-write
    STATUS current
    DESCRIPTION
    "Reset AH configuration
        other(0),
        reset(1)" 
    ::= { ospf3NewCfgIntfEntry 22 }

ospf3NewCfgIntfEncrySpi  OBJECT-TYPE
    SYNTAX Unsigned32 (256..4294967295)
    MAX-ACCESS read-write
    STATUS current
    DESCRIPTION
        "Encryption Spi Id(256 - 4294967295)"
    ::= { ospf3NewCfgIntfEntry 23 }

ospf3NewCfgIntfEncryEnable OBJECT-TYPE
    SYNTAX  INTEGER {
        disabled(0),
        enabled(1)
        }
    MAX-ACCESS read-write
    STATUS current
    DESCRIPTION
    "Encryption Status
        disabled(0),
        enabled(1)" 
    ::= { ospf3NewCfgIntfEntry 24 }

ospf3NewCfgIntfEncryType  OBJECT-TYPE 
    SYNTAX  INTEGER {
        null(0),
        tripledes(2),
        aes(3)
        } 
    MAX-ACCESS read-write
    STATUS current
    DESCRIPTION
    "Encryption Type
        null(0),
        3des(2),
        aes(3)"
   ::= { ospf3NewCfgIntfEntry 25 }

ospf3NewCfgIntfEncryKey   OBJECT-TYPE
    SYNTAX OCTET STRING (SIZE(4..48)) 
    MAX-ACCESS read-write
    STATUS current 
    DESCRIPTION
    "Encryption Key
    Hex-string AES key - 32 chars (128 bits)
    Hex-string 3DES key - 48 chars (192 bits)" 
    ::= { ospf3NewCfgIntfEntry 26 }


ospf3NewCfgIntfEncryAuthType  OBJECT-TYPE 
    SYNTAX  INTEGER {
        none(0),
        md5(2),
        sha1(1)
        } 
    MAX-ACCESS read-write
    STATUS current
    DESCRIPTION
    "Encryption Authentication Type
        none(0),
        md5(2),
        sha1(1)" 
    ::= { ospf3NewCfgIntfEntry 27 }

ospf3NewCfgIntfEncryAuthKey   OBJECT-TYPE
    SYNTAX OCTET STRING (SIZE(4..40)) 
    MAX-ACCESS read-write
    STATUS current 
    DESCRIPTION
    "Encryption Authentication Key
     Hex-string MD5 key - 32 chars (128 bits),
     Hex-string SHA-1 key - 40 chars (160 bits)" 
    ::= { ospf3NewCfgIntfEntry 28 }

ospf3NewCfgIntfEncryReset OBJECT-TYPE
    SYNTAX  INTEGER {
        other(0),
        reset(1)
        }
    MAX-ACCESS read-write
    STATUS current
    DESCRIPTION
    "Reset Encryption configuration
        other(0),
        reset(1)" 
    ::= { ospf3NewCfgIntfEntry 29 }



ospf3NewCfgIntfLsaSupress  OBJECT-TYPE
    SYNTAX  INTEGER {
        disabled(0),
        enabled(1)
        }
    MAX-ACCESS read-create
    STATUS current
    DESCRIPTION
    "LSA Supression on interface
    disabled(0),
        enabled(1)"
    ::= { ospf3NewCfgIntfEntry 30 }



ospf3CurCfgVirtIntfTable OBJECT-TYPE
    SYNTAX SEQUENCE OF Ospf3CurCfgVirtIntfEntry
    MAX-ACCESS not-accessible
    STATUS current
    DESCRIPTION
      "The table of OSPFv3 Virtual Interface configuration in the current 
       configuration."
    ::= { ospf3Cfg 10 }

ospf3CurCfgVirtIntfEntry OBJECT-TYPE
    SYNTAX Ospf3CurCfgVirtIntfEntry
    MAX-ACCESS not-accessible
    STATUS current
    DESCRIPTION
      "Information about an OSPFv3v3 virtual Interface."
    INDEX { ospf3CurCfgVirtIntfIndex }
    ::= { ospf3CurCfgVirtIntfTable 1 }
 
Ospf3CurCfgVirtIntfEntry ::= SEQUENCE {
    ospf3CurCfgVirtIntfIndex         Integer32,
    ospf3CurCfgVirtIntfAreaId        INTEGER,
    ospf3CurCfgVirtIntfNbr           IpAddress,
    ospf3CurCfgVirtIntfHello         INTEGER,
    ospf3CurCfgVirtIntfDead          INTEGER,
    ospf3CurCfgVirtIntfTrans         INTEGER,
    ospf3CurCfgVirtIntfRetra         INTEGER,
    ospf3CurCfgVirtIntfStatus        INTEGER 
    }
 
ospf3CurCfgVirtIntfIndex OBJECT-TYPE
    SYNTAX Integer32
    MAX-ACCESS read-only
    STATUS current
    DESCRIPTION
    "The OSPFv3 Virtual Interface number for which the OSPFv3 
         Virtual Interface table is related."
    ::= { ospf3CurCfgVirtIntfEntry 1}

ospf3CurCfgVirtIntfAreaId OBJECT-TYPE
    SYNTAX INTEGER (0..2) 
    MAX-ACCESS read-only
    STATUS current
    DESCRIPTION
    "The index of the OSPFv3 area to which this virtual interface
         belongs." 
    ::= { ospf3CurCfgVirtIntfEntry 3 }

ospf3CurCfgVirtIntfNbr OBJECT-TYPE
    SYNTAX IpAddress 
    MAX-ACCESS read-only
    STATUS current
    DESCRIPTION
    "The IP Address of the OSPFv3 neighbor for this virtual interface."
    ::= { ospf3CurCfgVirtIntfEntry 4 }

ospf3CurCfgVirtIntfHello  OBJECT-TYPE 
    SYNTAX INTEGER (1..65535) 
    MAX-ACCESS read-only
    STATUS current
    DESCRIPTION
    "Hello interval" 
    ::= { ospf3CurCfgVirtIntfEntry 5 }

ospf3CurCfgVirtIntfDead   OBJECT-TYPE
   SYNTAX INTEGER (1..65535) 
    MAX-ACCESS read-only
    STATUS current 
    DESCRIPTION
    "Dead interval" 
    ::= { ospf3CurCfgVirtIntfEntry 6 }

ospf3CurCfgVirtIntfTrans  OBJECT-TYPE
   SYNTAX INTEGER (1..3600) 
    MAX-ACCESS read-only
    STATUS current
    DESCRIPTION
    "Transmit delay" 
    ::= { ospf3CurCfgVirtIntfEntry 7 }
    
ospf3CurCfgVirtIntfRetra OBJECT-TYPE
    SYNTAX INTEGER (1..3600) 
    MAX-ACCESS read-only
    STATUS current
    DESCRIPTION
    "Retransmit interval" 
    ::= { ospf3CurCfgVirtIntfEntry 8 }

ospf3CurCfgVirtIntfStatus  OBJECT-TYPE
    SYNTAX  INTEGER {
        disabled(0),
        enabled(1)
        }
    MAX-ACCESS read-only
    STATUS current
    DESCRIPTION
    "Status
     disabled(0),
        enabled(1)" 
    ::= { ospf3CurCfgVirtIntfEntry 9 }

ospf3NewCfgVirtIntfTable OBJECT-TYPE
    SYNTAX SEQUENCE OF Ospf3NewCfgVirtIntfEntry
    MAX-ACCESS not-accessible
    STATUS current
    DESCRIPTION
      "The table of OSPFv3 Virtual interface in the new configuration block."
    ::= { ospf3Cfg 11 }

ospf3NewCfgVirtIntfEntry OBJECT-TYPE
    SYNTAX Ospf3NewCfgVirtIntfEntry
    MAX-ACCESS not-accessible
    STATUS current
    DESCRIPTION
      "Information about an OSPFv3 virtual interface."
    INDEX { ospf3NewCfgVirtIntfIndex }
    ::= { ospf3NewCfgVirtIntfTable 1 }
 
Ospf3NewCfgVirtIntfEntry ::= SEQUENCE {
    ospf3NewCfgVirtIntfIndex         Integer32,
    ospf3NewCfgVirtIntfAreaId        INTEGER,
    ospf3NewCfgVirtIntfNbr           IpAddress,
    ospf3NewCfgVirtIntfHello         INTEGER,
    ospf3NewCfgVirtIntfDead          INTEGER,
    ospf3NewCfgVirtIntfTrans         INTEGER,
    ospf3NewCfgVirtIntfRetra         INTEGER,
    ospf3NewCfgVirtIntfStatus        INTEGER, 
    ospf3NewCfgVirtIntfDelete        INTEGER
    }
 
ospf3NewCfgVirtIntfIndex OBJECT-TYPE
    SYNTAX Integer32
    MAX-ACCESS read-only
    STATUS current
    DESCRIPTION
    "The OSPFv3 Virtual Interface number for which the OSPFv3 
         Virtual Interface table is related."
    ::= { ospf3NewCfgVirtIntfEntry 1}

ospf3NewCfgVirtIntfAreaId OBJECT-TYPE
    SYNTAX INTEGER (0..2)
    MAX-ACCESS read-create
    STATUS current
    DESCRIPTION
    "The index of the OSPFv3 area to which this virtual interface
         belongs." 
    ::= { ospf3NewCfgVirtIntfEntry 3 }

ospf3NewCfgVirtIntfNbr OBJECT-TYPE
    SYNTAX IpAddress 
    MAX-ACCESS read-create
    STATUS current
    DESCRIPTION
    "The IP Address of the OSPFv3 neighbor for this virtual interface."
    ::= { ospf3NewCfgVirtIntfEntry 4 }

ospf3NewCfgVirtIntfHello  OBJECT-TYPE 
    SYNTAX INTEGER (1..65535) 
    MAX-ACCESS read-create
    STATUS current
    DESCRIPTION
    "Hello interval(1..65535)" 
    ::= { ospf3NewCfgVirtIntfEntry 5 }

ospf3NewCfgVirtIntfDead   OBJECT-TYPE
   SYNTAX INTEGER (1..65535) 
    MAX-ACCESS read-create
    STATUS current
    DESCRIPTION
    "Dead interval(1..65535)" 
    ::= { ospf3NewCfgVirtIntfEntry 6 }

ospf3NewCfgVirtIntfTrans  OBJECT-TYPE
   SYNTAX INTEGER (1..3600) 
    MAX-ACCESS read-create
    STATUS current
    DESCRIPTION
    "Transmit delay(1..3600)" 
    ::= { ospf3NewCfgVirtIntfEntry 7 }

ospf3NewCfgVirtIntfRetra OBJECT-TYPE
  SYNTAX INTEGER (1..3600) 
    MAX-ACCESS read-create
    STATUS current
    DESCRIPTION
    "Retransmit interval(1..3600)" 
    ::= { ospf3NewCfgVirtIntfEntry 8 }

ospf3NewCfgVirtIntfStatus  OBJECT-TYPE
    SYNTAX  INTEGER {
        disabled(0),
        enabled(1)
        }
    MAX-ACCESS read-create
    STATUS current
    DESCRIPTION
    "Status 
         disabled(0),
         enabled(1) " 
    ::= { ospf3NewCfgVirtIntfEntry 9 }

ospf3NewCfgVirtIntfDelete  OBJECT-TYPE
    SYNTAX  INTEGER {
        other(0),
        delete(1)
        }
    MAX-ACCESS read-write
    STATUS current
    DESCRIPTION
    "Delete
     other(0),
         delete(1)" 
    ::= { ospf3NewCfgVirtIntfEntry 10}


-- ospfv3 range

ospf3CurCfgRangeTable OBJECT-TYPE
    SYNTAX SEQUENCE OF Ospf3CurCfgRangeEntry
    MAX-ACCESS not-accessible
    STATUS current
    DESCRIPTION
      "The table of OSPFv3 summary range in the current configuration." 
    ::= { ospf3Cfg 12 }

ospf3CurCfgRangeEntry OBJECT-TYPE
    SYNTAX Ospf3CurCfgRangeEntry 
    MAX-ACCESS not-accessible
    STATUS current
    DESCRIPTION
      "Information about an OSPFv3 summary range."
    INDEX { ospf3CurCfgRangeIndex }
    ::= { ospf3CurCfgRangeTable 1 }
 
Ospf3CurCfgRangeEntry ::= SEQUENCE {
    ospf3CurCfgRangeIndex           Integer32,
    ospf3CurCfgRangeAddr             DisplayString,
    ospf3CurCfgRangePrefixLen      INTEGER,
    ospf3CurCfgRangeAreaIndex    Integer32,
    ospf3CurCfgRangeHideState     INTEGER,
    ospf3CurCfgRangeLsaType       INTEGER,
    ospf3CurCfgRangeRouteTag     Unsigned32,
    ospf3CurCfgRangeState            INTEGER
    }
 
ospf3CurCfgRangeIndex OBJECT-TYPE
    SYNTAX Integer32
    MAX-ACCESS read-only
    STATUS current
    DESCRIPTION
    "The range number for which the OSPFv3 summary range table is related." 
    ::= { ospf3CurCfgRangeEntry 1}

ospf3CurCfgRangeAddr OBJECT-TYPE
    SYNTAX DisplayString 
    MAX-ACCESS read-only
    STATUS current
    DESCRIPTION
    "The IPv6 Address of the range." 
    ::= { ospf3CurCfgRangeEntry 2 }

ospf3CurCfgRangePrefixLen OBJECT-TYPE
    SYNTAX  INTEGER (1..128)
    MAX-ACCESS read-only
    STATUS current
    DESCRIPTION
    "The prefix length of the range."
    ::= { ospf3CurCfgRangeEntry 3 }

ospf3CurCfgRangeAreaIndex OBJECT-TYPE
    SYNTAX Integer32
    MAX-ACCESS read-only
    STATUS current
    DESCRIPTION
        "The area index."
    ::= { ospf3CurCfgRangeEntry 4 }

ospf3CurCfgRangeHideState OBJECT-TYPE
    SYNTAX  INTEGER {
        enabled(1),
        disabled(2)
        }
    MAX-ACCESS  read-only
    STATUS  current
    DESCRIPTION
        "The state of the hide range."
    ::= { ospf3CurCfgRangeEntry 5 }

ospf3CurCfgRangeLsaType OBJECT-TYPE
    SYNTAX  INTEGER {
        summary(8195),
        type7(8199)
        }
    MAX-ACCESS  read-only
    STATUS  current
    DESCRIPTION
        "The LSA type for aggregation.
        summary(8195),
        type7(8199)"
    ::= { ospf3CurCfgRangeEntry 6 }

ospf3CurCfgRangeRouteTag OBJECT-TYPE
    SYNTAX  Unsigned32 (0..4294967295)
    MAX-ACCESS read-only
    STATUS current
    DESCRIPTION
    "The route tag of the range."
    ::= { ospf3CurCfgRangeEntry 7 }

ospf3CurCfgRangeState OBJECT-TYPE
    SYNTAX  INTEGER {
        enabled(1),
        disabled(2)
        }
    MAX-ACCESS  read-only
    STATUS  current
    DESCRIPTION
        "The state of the range."
    ::= { ospf3CurCfgRangeEntry 8 }

ospf3NewCfgRangeTable OBJECT-TYPE
    SYNTAX SEQUENCE OF Ospf3NewCfgRangeEntry
    MAX-ACCESS not-accessible
    STATUS current
    DESCRIPTION
      "The table of OSPFv3 summary range in the new configuration." 
    ::= { ospf3Cfg 13 }

ospf3NewCfgRangeEntry OBJECT-TYPE
    SYNTAX Ospf3NewCfgRangeEntry 
    MAX-ACCESS not-accessible
    STATUS current
    DESCRIPTION
      "Information about an OSPFv3 summary range."
    INDEX { ospf3NewCfgRangeIndex }
    ::= { ospf3NewCfgRangeTable 1 }
 
Ospf3NewCfgRangeEntry ::= SEQUENCE {
    ospf3NewCfgRangeIndex         Integer32,
    ospf3NewCfgRangeAddr           DisplayString,
    ospf3NewCfgRangePrefixLen   INTEGER,
    ospf3NewCfgRangeAreaIndex Integer32,
    ospf3NewCfgRangeHideState   INTEGER,
    ospf3NewCfgRangeLsaType      INTEGER,
    ospf3NewCfgRangeRouteTag    Unsigned32,
    ospf3NewCfgRangeState          INTEGER,
    ospf3NewCfgRangeDelete        INTEGER
    }
 
ospf3NewCfgRangeIndex OBJECT-TYPE
    SYNTAX Integer32
    MAX-ACCESS read-only
    STATUS current
    DESCRIPTION
    "The range number for which the OSPFv3 summary range table is related." 
    ::= { ospf3NewCfgRangeEntry 1}

ospf3NewCfgRangeAddr OBJECT-TYPE
    SYNTAX  DisplayString  (SIZE(0..40))
    MAX-ACCESS read-create 
    STATUS current
    DESCRIPTION
    "The IPv6 Address of the range.
     Address should be 4-byte haxadecimal colon notation.
     Valid IPv6 address should be in any of the following forms
     xxxx:xxxx:xxxx:xxxx:xxxx:xxxx:xxxx:xxxx or
     xxxx::xxxx:xxxx:xxxx:xxxx or ::xxxx"
    ::= { ospf3NewCfgRangeEntry 2 }

ospf3NewCfgRangePrefixLen OBJECT-TYPE
    SYNTAX  INTEGER (1..128) 
    MAX-ACCESS read-create 
    STATUS current
    DESCRIPTION
    "The prefix length of the range."
    ::= { ospf3NewCfgRangeEntry 3 }

ospf3NewCfgRangeAreaIndex OBJECT-TYPE
    SYNTAX Integer32
    MAX-ACCESS read-create 
    STATUS current
    DESCRIPTION
        "The area index."
    ::= { ospf3NewCfgRangeEntry 4 }

ospf3NewCfgRangeHideState OBJECT-TYPE
    SYNTAX  INTEGER {
        enabled(1),
        disabled(2)
        }
    MAX-ACCESS read-create 
    STATUS  current
    DESCRIPTION
        "The state of the hide range."
    ::= { ospf3NewCfgRangeEntry 5 }

ospf3NewCfgRangeLsaType OBJECT-TYPE
    SYNTAX  INTEGER {
        summary(8195),
        type7(8199)
        }
    MAX-ACCESS  read-create
    STATUS  current
    DESCRIPTION
        "The LSA type for aggregation.
        summary(8195),
        type7(8199)"
    ::= { ospf3NewCfgRangeEntry 6 }

ospf3NewCfgRangeRouteTag OBJECT-TYPE
    SYNTAX  Unsigned32 (0..4294967295)
    MAX-ACCESS read-create
    STATUS current
    DESCRIPTION
    "The route tag of the range."
    ::= { ospf3NewCfgRangeEntry 7 }

ospf3NewCfgRangeState OBJECT-TYPE
    SYNTAX  INTEGER {
        enabled(1),
        disabled(2)
        }
    MAX-ACCESS read-create 
    STATUS  current
    DESCRIPTION
        "The state of the range."
    ::= { ospf3NewCfgRangeEntry 8 }

ospf3NewCfgRangeDelete OBJECT-TYPE
    SYNTAX  INTEGER {
        other(1),
        delete(2)
        }
    MAX-ACCESS  read-create
    STATUS  current
    DESCRIPTION
        "When set to the value of 2 (delete), the entire row is deleted.
         When read, other(1) is returned. Setting the value to anything
         other than 2(delete) has no effect on the state of the row."
    ::= { ospf3NewCfgRangeEntry 9 }

-- ospfv3 summary prefix

ospf3CurCfgExtRangeTable OBJECT-TYPE
    SYNTAX SEQUENCE OF Ospf3CurCfgExtRangeEntry
    MAX-ACCESS not-accessible
    STATUS current
    DESCRIPTION
      "The table of OSPFv3 AS-External range in the current configuration." 
    ::= { ospf3Cfg 14 }

ospf3CurCfgExtRangeEntry OBJECT-TYPE
    SYNTAX Ospf3CurCfgExtRangeEntry 
    MAX-ACCESS not-accessible
    STATUS current
    DESCRIPTION
      "Information about an OSPFv3 AS-External range."
    INDEX { ospf3CurCfgExtRangeIndex }
    ::= { ospf3CurCfgExtRangeTable 1 }
 
Ospf3CurCfgExtRangeEntry ::= SEQUENCE {
    ospf3CurCfgExtRangeIndex           Integer32,
    ospf3CurCfgExtRangeAddr             DisplayString,
    ospf3CurCfgExtRangePrefixLen      INTEGER,
    ospf3CurCfgExtRangeAreaIndex    Integer32,
    ospf3CurCfgExtRangeTranslation   INTEGER,
    ospf3CurCfgExtRangeAggrEffect   INTEGER,
    ospf3CurCfgExtRangeState            INTEGER
    }
 
ospf3CurCfgExtRangeIndex OBJECT-TYPE
    SYNTAX Integer32
    MAX-ACCESS read-only
    STATUS current
    DESCRIPTION
    "The range number for which the OSPFv3 AS-External range table is related." 
    ::= { ospf3CurCfgExtRangeEntry 1}

ospf3CurCfgExtRangeAddr OBJECT-TYPE
    SYNTAX DisplayString 
    MAX-ACCESS read-only
    STATUS current
    DESCRIPTION
    "The IPv6 Address of the AS-External range." 
    ::= { ospf3CurCfgExtRangeEntry 2 }

ospf3CurCfgExtRangePrefixLen OBJECT-TYPE
    SYNTAX  INTEGER (1..128)
    MAX-ACCESS read-only
    STATUS current
    DESCRIPTION
    "The prefix length of the AS-External range."
    ::= { ospf3CurCfgExtRangeEntry 3 }

ospf3CurCfgExtRangeAreaIndex OBJECT-TYPE
    SYNTAX Integer32
    MAX-ACCESS read-only
    STATUS current
    DESCRIPTION
        "The area index."
    ::= { ospf3CurCfgExtRangeEntry 4 }

ospf3CurCfgExtRangeTranslation OBJECT-TYPE
    SYNTAX  INTEGER {
        enabled(1),
        disabled(2)
        }
    MAX-ACCESS  read-only
    STATUS  current
    DESCRIPTION
        "The state of the setting the P-bit in the generated LSA."
    ::= { ospf3CurCfgExtRangeEntry 5 }

ospf3CurCfgExtRangeAggrEffect OBJECT-TYPE
    SYNTAX  INTEGER {
        advertise(1),
        not-advertise(2),
        allowAll(3),
        denyAll(4)
        }
    MAX-ACCESS  read-only
    STATUS  current
    DESCRIPTION
        "The aggregation effect.
        advertise(1),
        not-advertise(2),
        allowAll(3),
        denyAll(4)"
    ::= { ospf3CurCfgExtRangeEntry 6 }

ospf3CurCfgExtRangeState OBJECT-TYPE
    SYNTAX  INTEGER {
        enabled(1),
        disabled(2)
        }
    MAX-ACCESS  read-only
    STATUS  current
    DESCRIPTION
        "The state of the AS-External range."
    ::= { ospf3CurCfgExtRangeEntry 7 }

ospf3NewCfgExtRangeTable OBJECT-TYPE
    SYNTAX SEQUENCE OF Ospf3NewCfgExtRangeEntry
    MAX-ACCESS not-accessible
    STATUS current
    DESCRIPTION
      "The table of OSPFv3 summary AS-External range in the new configuration." 
    ::= { ospf3Cfg 15 }

ospf3NewCfgExtRangeEntry OBJECT-TYPE
    SYNTAX Ospf3NewCfgExtRangeEntry 
    MAX-ACCESS not-accessible
    STATUS current
    DESCRIPTION
      "Information about an OSPFv3 summary AS-External range."
    INDEX { ospf3NewCfgExtRangeIndex }
    ::= { ospf3NewCfgExtRangeTable 1 }
 
Ospf3NewCfgExtRangeEntry ::= SEQUENCE {
    ospf3NewCfgExtRangeIndex          Integer32,
    ospf3NewCfgExtRangeAddr           DisplayString,
    ospf3NewCfgExtRangePrefixLen    INTEGER,
    ospf3NewCfgExtRangeAreaIndex  Integer32,
    ospf3NewCfgExtRangeTranslation  INTEGER,
    ospf3NewCfgExtRangeAggrEffect  INTEGER,
    ospf3NewCfgExtRangeState           INTEGER,
    ospf3NewCfgExtRangeDelete         INTEGER
    }
 
ospf3NewCfgExtRangeIndex OBJECT-TYPE
    SYNTAX Integer32
    MAX-ACCESS read-only
    STATUS current
    DESCRIPTION
    "The range number for which the OSPFv3 AS-External range table is related." 
    ::= { ospf3NewCfgExtRangeEntry 1}

ospf3NewCfgExtRangeAddr OBJECT-TYPE
    SYNTAX  DisplayString  (SIZE(0..40))
    MAX-ACCESS read-create 
    STATUS current
    DESCRIPTION
    "The IPv6 Address of the AS-External range.
     Address should be 4-byte haxadecimal colon notation.
     Valid IPv6 address should be in any of the following forms
     xxxx:xxxx:xxxx:xxxx:xxxx:xxxx:xxxx:xxxx or
     xxxx::xxxx:xxxx:xxxx:xxxx or ::xxxx"
    ::= { ospf3NewCfgExtRangeEntry 2 }

ospf3NewCfgExtRangePrefixLen OBJECT-TYPE
    SYNTAX  INTEGER (1..128) 
    MAX-ACCESS read-create 
    STATUS current
    DESCRIPTION
    "The prefix length of the AS-External range."
    ::= { ospf3NewCfgExtRangeEntry 3 }

ospf3NewCfgExtRangeAreaIndex OBJECT-TYPE
    SYNTAX Integer32
    MAX-ACCESS read-create 
    STATUS current
    DESCRIPTION
        "The area index."
    ::= { ospf3NewCfgExtRangeEntry 4 }

ospf3NewCfgExtRangeTranslation OBJECT-TYPE
    SYNTAX  INTEGER {
        enabled(1),
        disabled(2)
        }
    MAX-ACCESS  read-create
    STATUS  current
    DESCRIPTION
        "The state of the setting the P-bit in the generated LSA."
    ::= { ospf3NewCfgExtRangeEntry 5 }

ospf3NewCfgExtRangeAggrEffect OBJECT-TYPE
    SYNTAX  INTEGER {
        advertise(1),
        not-advertise(2),
        allowAll(3),
        denyAll(4)
        }
    MAX-ACCESS  read-create
    STATUS  current
    DESCRIPTION
        "The aggregation effect.
        advertise(1),
        not-advertise(2),
        allowAll(3),
        denyAll(4)"
    ::= { ospf3NewCfgExtRangeEntry 6 }

ospf3NewCfgExtRangeState OBJECT-TYPE
    SYNTAX  INTEGER {
        enabled(1),
        disabled(2)
        }
    MAX-ACCESS read-create 
    STATUS  current
    DESCRIPTION
        "The state of the AS-External range."
    ::= { ospf3NewCfgExtRangeEntry 7 }

ospf3NewCfgExtRangeDelete OBJECT-TYPE
    SYNTAX  INTEGER {
        other(1),
        delete(2)
        }
    MAX-ACCESS  read-create
    STATUS  current
    DESCRIPTION
        "When set to the value of 2 (delete), the entire row is deleted.
         When read, other(1) is returned. Setting the value to anything
         other than 2(delete) has no effect on the state of the row."
    ::= { ospf3NewCfgExtRangeEntry 8 }

-- ospfv3 redist entries

ospf3CurCfgRedistTable OBJECT-TYPE
    SYNTAX SEQUENCE OF Ospf3CurCfgRedistEntry
    MAX-ACCESS not-accessible
    STATUS current
    DESCRIPTION
      "The table of OSPFv3 redistribution entries in the current configuration." 
    ::= { ospf3Cfg 16 }

ospf3CurCfgRedistEntry OBJECT-TYPE
    SYNTAX Ospf3CurCfgRedistEntry 
    MAX-ACCESS not-accessible
    STATUS current
    DESCRIPTION
      "Information about an OSPFv3 redistribution entry."
    INDEX { ospf3CurCfgRedistIndex }
    ::= { ospf3CurCfgRedistTable 1 }
 
Ospf3CurCfgRedistEntry ::= SEQUENCE {
    ospf3CurCfgRedistIndex           Integer32,
    ospf3CurCfgRedistAddr             DisplayString,
    ospf3CurCfgRedistPrefixLen      INTEGER,
    ospf3CurCfgRedistMetric           INTEGER,
    ospf3CurCfgRedistMetricType   INTEGER,
    ospf3CurCfgRedistRouteTagTypeManual  INTEGER,
    ospf3CurCfgRedistRouteTag     Unsigned32,
    ospf3CurCfgRedistState            INTEGER
    }
 
ospf3CurCfgRedistIndex OBJECT-TYPE
    SYNTAX Integer32
    MAX-ACCESS read-only
    STATUS current
    DESCRIPTION
    "The redistribution entry number for which the OSPFv3 redistribution entry table is related." 
    ::= { ospf3CurCfgRedistEntry 1}

ospf3CurCfgRedistAddr OBJECT-TYPE
    SYNTAX DisplayString 
    MAX-ACCESS read-only
    STATUS current
    DESCRIPTION
    "The IPv6 Address of the redistribution entry." 
    ::= { ospf3CurCfgRedistEntry 2 }

ospf3CurCfgRedistPrefixLen OBJECT-TYPE
    SYNTAX  INTEGER (1..128)
    MAX-ACCESS read-only
    STATUS current
    DESCRIPTION
    "The prefix length of the redistribution entry."
    ::= { ospf3CurCfgRedistEntry 3 }

ospf3CurCfgRedistMetric OBJECT-TYPE
    SYNTAX  INTEGER (1..16777215)
    MAX-ACCESS read-only
    STATUS current
    DESCRIPTION
    "The metric to be applied to the route."
    ::= { ospf3CurCfgRedistEntry 4 }

ospf3CurCfgRedistMetricType OBJECT-TYPE
    SYNTAX  INTEGER {
        asExttype1(3),
        asExttype2(4)
        }
    MAX-ACCESS  read-only
    STATUS  current
    DESCRIPTION
        "The metric type.
        asExttype1(3),
        asExttype2(4)"
    ::= { ospf3CurCfgRedistEntry 5 }

ospf3CurCfgRedistRouteTag OBJECT-TYPE
    SYNTAX  Unsigned32 (0..4294967295)
    MAX-ACCESS read-only
    STATUS current
    DESCRIPTION
    "The route tag of the redistribution entry."
    ::= { ospf3CurCfgRedistEntry 6 }
    
ospf3CurCfgRedistRouteTagTypeManual OBJECT-TYPE
    SYNTAX  INTEGER {
         auto(0),
         manual(1)
         }
    MAX-ACCESS read-only
    STATUS current
    DESCRIPTION
    "Indicates if the route tag is set manually. "
    ::= { ospf3CurCfgRedistEntry 7 }

ospf3CurCfgRedistState OBJECT-TYPE
    SYNTAX  INTEGER {
        enabled(1),
        disabled(2)
        }
    MAX-ACCESS  read-only
    STATUS  current
    DESCRIPTION
        "The state of the redistribution entry."
    ::= { ospf3CurCfgRedistEntry 8 }

ospf3NewCfgRedistTable OBJECT-TYPE
    SYNTAX SEQUENCE OF Ospf3NewCfgRedistEntry
    MAX-ACCESS not-accessible
    STATUS current
    DESCRIPTION
      "The table of OSPFv3 summary redistribution entry in the new configuration." 
    ::= { ospf3Cfg 17 }

ospf3NewCfgRedistEntry OBJECT-TYPE
    SYNTAX Ospf3NewCfgRedistEntry 
    MAX-ACCESS not-accessible
    STATUS current
    DESCRIPTION
      "Information about an OSPFv3 summary redistribution entry."
    INDEX { ospf3NewCfgRedistIndex }
    ::= { ospf3NewCfgRedistTable 1 }
 
Ospf3NewCfgRedistEntry ::= SEQUENCE {
    ospf3NewCfgRedistIndex          Integer32,
    ospf3NewCfgRedistAddr            DisplayString,
    ospf3NewCfgRedistPrefixLen    INTEGER,
    ospf3NewCfgRedistMetric          INTEGER,
    ospf3NewCfgRedistMetricType  INTEGER,
    ospf3NewCfgRedistRouteTagTypeManual INTEGER,
    ospf3NewCfgRedistRouteTag    Unsigned32,
    ospf3NewCfgRedistState           INTEGER,
    ospf3NewCfgRedistDelete         INTEGER
    }
 
ospf3NewCfgRedistIndex OBJECT-TYPE
    SYNTAX Integer32
    MAX-ACCESS read-only
    STATUS current
    DESCRIPTION
    "The redistribution entry number for which the OSPFv3 redistribution entry table is related." 
    ::= { ospf3NewCfgRedistEntry 1}

ospf3NewCfgRedistAddr OBJECT-TYPE
    SYNTAX  DisplayString  (SIZE(0..40))
    MAX-ACCESS read-create 
    STATUS current
    DESCRIPTION
    "The IPv6 Address of the redistribution entry.
     Address should be 4-byte haxadecimal colon notation.
     Valid IPv6 address should be in any of the following forms
     xxxx:xxxx:xxxx:xxxx:xxxx:xxxx:xxxx:xxxx or
     xxxx::xxxx:xxxx:xxxx:xxxx or ::xxxx"
    ::= { ospf3NewCfgRedistEntry 2 }

ospf3NewCfgRedistPrefixLen OBJECT-TYPE
    SYNTAX  INTEGER (1..128) 
    MAX-ACCESS read-create 
    STATUS current
    DESCRIPTION
    "The prefix length of the redistribution entry."
    ::= { ospf3NewCfgRedistEntry 3 }

ospf3NewCfgRedistMetric OBJECT-TYPE
    SYNTAX  INTEGER (1..16777215)
    MAX-ACCESS read-create
    STATUS current
    DESCRIPTION
    "The metric to be applied to the route."
    ::= { ospf3NewCfgRedistEntry 4 }

ospf3NewCfgRedistMetricType OBJECT-TYPE
    SYNTAX  INTEGER {
        asExttype1(3),
        asExttype2(4)
        }
    MAX-ACCESS  read-create
    STATUS  current
    DESCRIPTION
        "The metric type.
        asExttype1(3),
        asExttype2(4)"
    ::= { ospf3NewCfgRedistEntry 5 }

ospf3NewCfgRedistRouteTag OBJECT-TYPE
    SYNTAX  Unsigned32 (0..4294967295)
    MAX-ACCESS read-create
    STATUS current
    DESCRIPTION
    "The route tag of the redistribution entry."
    ::= { ospf3NewCfgRedistEntry 6 }

ospf3NewCfgRedistRouteTagTypeManual OBJECT-TYPE
    SYNTAX  INTEGER {
         auto(0),
         manual(1)
         }
    MAX-ACCESS read-write
    STATUS current
    DESCRIPTION
    "Indicates if the route tag is set manually. "
    ::= { ospf3NewCfgRedistEntry 7 }
    
ospf3NewCfgRedistState OBJECT-TYPE
    SYNTAX  INTEGER {
        enabled(1),
        disabled(2)
        }
    MAX-ACCESS read-create 
    STATUS  current
    DESCRIPTION
        "The state of the redistribution entry."
    ::= { ospf3NewCfgRedistEntry 8 }

ospf3NewCfgRedistDelete OBJECT-TYPE
    SYNTAX  INTEGER {
        other(1),
        delete(2)
        }
    MAX-ACCESS  read-create
    STATUS  current
    DESCRIPTION
        "When set to the value of 2 (delete), the entire row is deleted.
         When read, other(1) is returned. Setting the value to anything
         other than 2(delete) has no effect on the state of the row."
    ::= { ospf3NewCfgRedistEntry 9 }
    
    
ospf3RouteRedistribution   OBJECT IDENTIFIER ::= { ospf3Cfg 18 }

ospf3RedistributeConnected    OBJECT IDENTIFIER ::= { ospf3RouteRedistribution 1 }

ospf3CurCfgConnectedMetric OBJECT-TYPE
    SYNTAX INTEGER (0..16777215)
    MAX-ACCESS read-only
    STATUS current
    DESCRIPTION
    "The metric to be assigned to Connected routes." 
    ::= { ospf3RedistributeConnected 1 }

ospf3NewCfgConnectedMetric OBJECT-TYPE
    SYNTAX INTEGER (0..16777215)
    MAX-ACCESS read-write
    STATUS current
    DESCRIPTION
    "The metric to be assigned to Connected routes." 
    ::= { ospf3RedistributeConnected 2 }

ospf3CurCfgConnectedMetricType OBJECT-TYPE
    SYNTAX INTEGER {
        none(1),
        type1(2),
        type2(3)
        }
    MAX-ACCESS read-only
    STATUS current
    DESCRIPTION
    "The AS External metric type for Connected routes."
    ::= { ospf3RedistributeConnected 3 }

ospf3NewCfgConnectedMetricType OBJECT-TYPE
    SYNTAX INTEGER {
        none(1),
        type1(2),
        type2(3)
        }
    MAX-ACCESS read-write
    STATUS current
    DESCRIPTION
    "The AS External metric type for Connected routes."
    ::= { ospf3RedistributeConnected 4 }

ospf3CurCfgConnectedRouteTag OBJECT-TYPE
    SYNTAX Unsigned32 (0..4294967295)
    MAX-ACCESS read-only
    STATUS current
    DESCRIPTION
        "Assigned route tag "
    ::= { ospf3RedistributeConnected 5 }

ospf3NewCfgConnectedRouteTag OBJECT-TYPE
    SYNTAX Unsigned32 (0..4294967295)
    MAX-ACCESS read-write
    STATUS current
    DESCRIPTION
        "Assigned route tag "
    ::= { ospf3RedistributeConnected 6 }

ospf3CurCfgConnectedRouteTagTypeManual OBJECT-TYPE
    SYNTAX INTEGER {
        auto(0),
        manual(1)
        }
    MAX-ACCESS read-only
    STATUS current
    DESCRIPTION
        "Indicates if the route tag is set manually."
    ::= { ospf3RedistributeConnected 7 }

ospf3NewCfgConnectedRouteTagTypeManual OBJECT-TYPE
    SYNTAX INTEGER {
        auto(0),
        manual(1)
        }
    MAX-ACCESS read-write
    STATUS current
    DESCRIPTION
        "Indicates if the route tag is set manually."
    ::= { ospf3RedistributeConnected 8 }
    
ospf3RedistributeStatic    OBJECT IDENTIFIER ::= { ospf3RouteRedistribution 2 }

ospf3CurCfgStaticMetric OBJECT-TYPE
    SYNTAX INTEGER (0..16777215)
    MAX-ACCESS read-only
    STATUS current
    DESCRIPTION
    "The metric to be assigned to static routes." 
    ::= { ospf3RedistributeStatic 1 }

ospf3NewCfgStaticMetric OBJECT-TYPE
    SYNTAX INTEGER (0..16777215)
    MAX-ACCESS read-write
    STATUS current
    DESCRIPTION
    "The metric to be assigned to static routes." 
    ::= { ospf3RedistributeStatic 2 }

ospf3CurCfgStaticMetricType OBJECT-TYPE
    SYNTAX INTEGER {
        none(1),
        type1(2),
        type2(3)
        }
    MAX-ACCESS read-only
    STATUS current
    DESCRIPTION
    "The AS External metric type for static routes."
    ::= { ospf3RedistributeStatic 3 }

ospf3NewCfgStaticMetricType OBJECT-TYPE
    SYNTAX INTEGER {
        none(1),
        type1(2),
        type2(3)
        }
    MAX-ACCESS read-write
    STATUS current
    DESCRIPTION
    "The AS External metric type for static routes."
    ::= { ospf3RedistributeStatic 4 }

ospf3CurCfgStaticRouteTag OBJECT-TYPE
    SYNTAX Unsigned32 (0..4294967295)
    MAX-ACCESS read-only
    STATUS current
    DESCRIPTION
        "Assigned route tag "
    ::= { ospf3RedistributeStatic 5 }

ospf3NewCfgStaticRouteTag OBJECT-TYPE
    SYNTAX Unsigned32 (0..4294967295)
    MAX-ACCESS read-write
    STATUS current
    DESCRIPTION
        "Assigned route tag "
    ::= { ospf3RedistributeStatic 6 }

ospf3CurCfgStaticRouteTagTypeManual OBJECT-TYPE
    SYNTAX INTEGER {
        auto(0),
        manual(1)
        }
    MAX-ACCESS read-only
    STATUS current
    DESCRIPTION
        "Indicates if the route tag is set manually."
    ::= { ospf3RedistributeStatic 7 }

ospf3NewCfgStaticRouteTagTypeManual OBJECT-TYPE
    SYNTAX INTEGER {
        auto(0),
        manual(1)
        }
    MAX-ACCESS read-write
    STATUS current
    DESCRIPTION
        "Indicates if the route tag is set manually."
    ::= { ospf3RedistributeStatic 8 }


ipv6PmtuCurTimeout OBJECT-TYPE
    SYNTAX INTEGER 
    MAX-ACCESS read-only
    STATUS current
    DESCRIPTION
        "IPv6 PMTU Expired Time Value(0|10-100), 0 indicates INFINITY. Other values should be in [10, 100]"
    ::= { ipv6pmtuCfg 1 }

ipv6PmtuNewTimeout OBJECT-TYPE
    SYNTAX INTEGER 
    MAX-ACCESS read-write
    STATUS current
    DESCRIPTION
        "IPv6 PMTU Expired Time Value(0|10-100), 0 indicates INFINITY. Other values should be in [10, 100]"
    ::= { ipv6pmtuCfg 2 }

ipv6PmtuEntriesClearAll OBJECT-TYPE
    SYNTAX INTEGER {
          ok(1),
          clear(2)
          }
    MAX-ACCESS  read-write
    STATUS  current
    DESCRIPTION
          "When set to clear(2),clears all ipv6 PMTU entries. Otherwhise nothing is done."
    ::= { ipv6pmtuCfg 3}

ipCurCfgRouterID OBJECT-TYPE
    SYNTAX IpAddress 
    MAX-ACCESS read-only
    STATUS current
    DESCRIPTION
    "The router ID of the switch." 
    ::= { ipGeneralCfg 1 }

ipNewCfgRouterID OBJECT-TYPE
    SYNTAX IpAddress 
    MAX-ACCESS read-write
    STATUS current
    DESCRIPTION
    "The router ID of the switch." 
    ::= { ipGeneralCfg 2 }



vlanFloodCurCfgTable OBJECT-TYPE
    SYNTAX  SEQUENCE OF VlanFloodCurCfgTableEntry
    MAX-ACCESS  not-accessible
    STATUS  current
    DESCRIPTION
        "The table of VLAN flooding configuration."
    ::= { floodingCfg 1 }

vlanFloodCurCfgTableEntry OBJECT-TYPE
    SYNTAX  VlanFloodCurCfgTableEntry
    MAX-ACCESS  not-accessible
    STATUS  current
    DESCRIPTION
        "A row in the VLAN flooding configuration table."
    INDEX  { vlanFloodCurCfgVlanId }
    ::= { vlanFloodCurCfgTable 1 }

VlanFloodCurCfgTableEntry ::= SEQUENCE {
    vlanFloodCurCfgVlanId   Integer32,
    vlanFloodCurCfgFlood        INTEGER
    ,vlanFloodCurCfgCpu         INTEGER 
    ,vlanFloodCurCfgOptFlood    INTEGER
    }

vlanFloodCurCfgVlanId OBJECT-TYPE
    SYNTAX  Integer32
    MAX-ACCESS  read-only
    STATUS  current
    DESCRIPTION
        "The VLAN identifier."
    ::= { vlanFloodCurCfgTableEntry 1 }

vlanFloodCurCfgFlood OBJECT-TYPE
    SYNTAX  INTEGER  {
    enabled(1),
    disabled(0)
    }
    MAX-ACCESS  read-only
    STATUS  current
    DESCRIPTION
        "Enable or disable flooding unregistered IPMCs"
    ::= { vlanFloodCurCfgTableEntry 2 }

vlanFloodCurCfgCpu OBJECT-TYPE
    SYNTAX  INTEGER  {
        enabled(1),
        disabled(0)
        }
    MAX-ACCESS  read-only
    STATUS  current
    DESCRIPTION
        "Enable or disable sending unregistered IPMCs to CPU"
    ::= { vlanFloodCurCfgTableEntry 3 }

vlanFloodCurCfgOptFlood OBJECT-TYPE
    SYNTAX  INTEGER  {
        enabled(1),
        disabled(0)
        }
    MAX-ACCESS  read-only
    STATUS  current
    DESCRIPTION
        "Enable or disable optimized flooding"
    ::= { vlanFloodCurCfgTableEntry 4 }

vlanFloodNewCfgTable OBJECT-TYPE
    SYNTAX  SEQUENCE OF VlanFloodNewCfgTableEntry
    MAX-ACCESS  not-accessible
    STATUS  current
    DESCRIPTION
        "The table of VLAN flooding configuration."
    ::= { floodingCfg 2 }

vlanFloodNewCfgTableEntry OBJECT-TYPE
    SYNTAX  VlanFloodNewCfgTableEntry
    MAX-ACCESS  not-accessible
    STATUS  current
    DESCRIPTION
        "A row in the VLAN flooding configuration table."
    INDEX  { vlanFloodNewCfgVlanId }
    ::= { vlanFloodNewCfgTable 1 }

VlanFloodNewCfgTableEntry ::= SEQUENCE {
    vlanFloodNewCfgVlanId       Integer32,
    vlanFloodNewCfgFlood        INTEGER
    ,vlanFloodNewCfgCpu         INTEGER
    ,vlanFloodNewCfgOptFlood    INTEGER
    }

vlanFloodNewCfgVlanId OBJECT-TYPE
    SYNTAX  Integer32
    MAX-ACCESS  read-only
    STATUS  current
    DESCRIPTION
        "The VLAN identifier."
    ::= { vlanFloodNewCfgTableEntry 1 }

vlanFloodNewCfgFlood OBJECT-TYPE
    SYNTAX  INTEGER  {
        enabled(1),
        disabled(0)
        }
    MAX-ACCESS  read-write
    STATUS  current
    DESCRIPTION
        "Enable or disable flooding unregistered IPMCs"
    ::= { vlanFloodNewCfgTableEntry 2 }

vlanFloodNewCfgCpu OBJECT-TYPE
    SYNTAX  INTEGER  {
        enabled(1),
        disabled(0)
        }
    MAX-ACCESS  read-write
    STATUS  current
    DESCRIPTION
        "Enable or disable sending unregistered IPMCs to CPU"
    ::= { vlanFloodNewCfgTableEntry 3 }

vlanFloodNewCfgOptFlood OBJECT-TYPE
    SYNTAX  INTEGER  {
        enabled(1),
        disabled(0)
        }
    MAX-ACCESS  read-write
    STATUS  current
    DESCRIPTION
        "Enable or disable optimized flooding"
    ::= { vlanFloodNewCfgTableEntry 4 }

-- IGMP config

igmpCurCfgOnOff OBJECT-TYPE
    SYNTAX INTEGER { 
        on(1),
        off(2)
    }
    MAX-ACCESS  read-only
    STATUS  current
    DESCRIPTION
        "Globally turn IGMP On/Off."
    ::= { igmpCfg 1}

igmpNewCfgOnOff OBJECT-TYPE
    SYNTAX INTEGER { 
        on(1),
        off(2)
    }
    MAX-ACCESS  read-write
    STATUS  current
    DESCRIPTION
        "Globally turn IGMP On/Off."
    ::= { igmpCfg 2}


igmpSnoopCfg      OBJECT IDENTIFIER ::= { igmpCfg 9 }

-- IGMP Snooping config
igmpSnoopCurCfgMrto OBJECT-TYPE
    SYNTAX  Integer32 
    MAX-ACCESS  read-only
    STATUS  current
    DESCRIPTION
        "The value of multicast router timeout in the current config."
    ::= { igmpSnoopCfg 7 }

igmpSnoopNewCfgMrto OBJECT-TYPE
    SYNTAX  Integer32 
    MAX-ACCESS  read-write
    STATUS  current
    DESCRIPTION
        "The value of multicast router timeout in the new config."
    ::= { igmpSnoopCfg 8 }

igmpSnoopCurCfgAggrEnaDis OBJECT-TYPE
    SYNTAX INTEGER {
       enable(1),
       disable(2)
      }
    MAX-ACCESS  read-only
    STATUS  current
    DESCRIPTION
        "Enable/Disable of IGMP Report aggregation."
    ::= { igmpSnoopCfg 9}

igmpSnoopNewCfgAggrEnaDis OBJECT-TYPE
    SYNTAX INTEGER {
        enable(1),
        disable(2)
      }
    MAX-ACCESS  read-write
    STATUS  current
    DESCRIPTION
        "Enable/Disable of IGMP Report aggregation."
    ::= { igmpSnoopCfg 10}
igmpSnoopCurCfgEnaDis OBJECT-TYPE
    SYNTAX INTEGER {
        enabled(1),
        disabled(2)
        }
    MAX-ACCESS  read-only
    STATUS  current
    DESCRIPTION
        "The current status of IGMP Snooping."
    ::= { igmpSnoopCfg 11}

igmpSnoopNewCfgEnaDis OBJECT-TYPE
    SYNTAX INTEGER {
        enable(1),
        disable(2)
        }
    MAX-ACCESS  read-write
    STATUS  current
    DESCRIPTION
        "Set Enable/Disable of IGMP Snooping."
    ::= { igmpSnoopCfg 12}

igmpSnoopNewCfgVlanAdd OBJECT-TYPE
    SYNTAX  Integer32 
    MAX-ACCESS  read-write
    STATUS  current
    DESCRIPTION
        "The VLAN to be added to snooping vlan list. When read,
         0 is returned."
    ::= { igmpSnoopCfg 13 }

igmpSnoopNewCfgVlanRem OBJECT-TYPE
    SYNTAX  Integer32 
    MAX-ACCESS  read-write
    STATUS  current
    DESCRIPTION
        "The VLAN to be removed from snooping vlan list. When read,
         0 is returned."
    ::= { igmpSnoopCfg 14 }

igmpSnoopNewCfgVlanClear OBJECT-TYPE
    SYNTAX  INTEGER {
        clear(1),
        ok(2)
        }
    MAX-ACCESS  read-write
    STATUS  current
    DESCRIPTION
        "Removing ALL Snooping Vlans."
    ::= { igmpSnoopCfg 15 }

igmpSnoopCurCfgVlanBmap OBJECT-TYPE
    SYNTAX OCTET STRING
    MAX-ACCESS read-only
    STATUS current
    DESCRIPTION
        "The snooping vlans present in the vlan map list.
         The snooping vlans are presented in a bitmap format.

         in receiving order:

         OCTET 1  OCTET 2  .....
         xxxxxxxx xxxxxxxx .....
         ||    || |_ Vlan 9
         ||    ||
         ||    ||___ Vlan 8
         ||    |____ Vlan 7
         ||      .    .   .
         ||_________ Vlan 2
         |__________ Vlan 1

         where x : 1 - The represented vlan has snoop enabled
         0 - The represented vlan does not have snooping enabled."
    ::= { igmpSnoopCfg 16 }

igmpSnoopNewCfgVlanBmap OBJECT-TYPE
    SYNTAX OCTET STRING
    MAX-ACCESS read-write
    STATUS current
    DESCRIPTION
        "The snooping vlans present in the vlan map list.
         The snooping vlans are presented in a bitmap format.

         in receiving order:

         OCTET 1  OCTET 2  .....
         xxxxxxxx xxxxxxxx .....
         ||    || |_ Vlan 9
         ||    ||
         ||    ||___ Vlan 8
         ||    |____ Vlan 7
         ||      .    .   .
         ||_________ Vlan 2
         |__________ Vlan 1

         where x : 1 - The represented vlan has snoop enabled
         0 - The represented vlan does not have snooping enabled."
    ::= { igmpSnoopCfg 17 }


igmpSnoopCurCfgSrcIp OBJECT-TYPE
    SYNTAX IpAddress 
    MAX-ACCESS read-only
    STATUS current
    DESCRIPTION
    "The source ip for GSQ proxy in current config." 
    ::= { igmpSnoopCfg 26 }

igmpSnoopNewCfgSrcIp OBJECT-TYPE
    SYNTAX IpAddress 
    MAX-ACCESS read-write
    STATUS current
    DESCRIPTION
    "The source ip for GSQ proxy in new config." 
    ::= { igmpSnoopCfg 27 }


igmpSnoopSetToDefault OBJECT-TYPE
    SYNTAX INTEGER {
        none(1),
        setDefault(2)
      }
    MAX-ACCESS  read-write
    STATUS  current
    DESCRIPTION
        "When setting the value setDefault(2), the IGMP Snooping configuration 
         is set to the default values. When reading, none(1) is always
         returned."
    ::= { igmpSnoopCfg 33}


igmpStaticMrtrCfg OBJECT IDENTIFIER ::= { igmpCfg 10 }
igmpFilterCfg     OBJECT IDENTIFIER ::= { igmpCfg 11 }

igmpRelayCfg      OBJECT IDENTIFIER ::= { igmpCfg 12 }
igmpAdvCfg        OBJECT IDENTIFIER ::= { igmpCfg 13 }
igmpV3SnoopCfg      OBJECT IDENTIFIER ::= { igmpCfg 14 }

igmpV3SnoopCurCfgSources OBJECT-TYPE
    SYNTAX  Integer32 
    MAX-ACCESS  read-only
    STATUS  current
    DESCRIPTION
        "Number of sources to snoop in a group record in current config."
    ::= { igmpV3SnoopCfg 1 }

igmpV3SnoopNewCfgSources OBJECT-TYPE
    SYNTAX  Integer32 
    MAX-ACCESS  read-write
    STATUS  current
    DESCRIPTION
        "Number of sources to snoop in a group record in new config."
    ::= { igmpV3SnoopCfg 2 }

igmpV3SnoopCurCfgEnaDis OBJECT-TYPE
    SYNTAX INTEGER {
        enabled(1),
        disabled(2)
        }
    MAX-ACCESS  read-only
    STATUS  current
    DESCRIPTION
        "The current status of IGMP V3 Snooping."
    ::= { igmpV3SnoopCfg 3 }

igmpV3SnoopNewCfgEnaDis OBJECT-TYPE
    SYNTAX INTEGER {
        enable(1),
        disable(2)
        }
    MAX-ACCESS  read-write
    STATUS  current
    DESCRIPTION
        "Set Enable/Disable of IGMP V3 Snooping."
    ::= { igmpV3SnoopCfg 4 }

igmpV3SnoopCurCfgExcludeEnaDis OBJECT-TYPE
    SYNTAX INTEGER {
        enabled(1),
        disabled(2)
        }
    MAX-ACCESS  read-only
    STATUS  current
    DESCRIPTION
        "The current status of IGMP V3 EXCLUDE filter-mode Snooping."
    ::= { igmpV3SnoopCfg 5 }

igmpV3SnoopNewCfgExcludeEnaDis OBJECT-TYPE
    SYNTAX INTEGER {
        enable(1),
        disable(2)
        }
    MAX-ACCESS  read-write
    STATUS  current
    DESCRIPTION
        "Set Enable/Disable of IGMP V3 EXCLUDE filter-mode Snooping."
    ::= { igmpV3SnoopCfg 6 }

igmpV3SnoopCurCfgV1V2EnaDis OBJECT-TYPE
    SYNTAX INTEGER {
        enabled(1),
        disabled(2)
        }
    MAX-ACCESS  read-only
    STATUS  current
    DESCRIPTION
        "The current status of IGMP V1/V2 Report Snooping."
    ::= { igmpV3SnoopCfg 7 }

igmpV3SnoopNewCfgV1V2EnaDis OBJECT-TYPE
    SYNTAX INTEGER {
        enable(1),
        disable(2)
        }
    MAX-ACCESS  read-write
    STATUS  current
    DESCRIPTION
        "Set Enable/Disable of IGMP V1/V2 Report Snooping."
    ::= { igmpV3SnoopCfg 8 }


-- IGMP Static Mrtr Support
igmpStaticMrtrCurCfgTable OBJECT-TYPE
    SYNTAX  SEQUENCE OF IgmpStaticMrtrCurCfgTableEntry
    MAX-ACCESS  not-accessible
    STATUS  current
    DESCRIPTION
        "The IGMP Static Multicast Router table in the current configuration block."
    ::= { igmpStaticMrtrCfg 1 }

igmpStaticMrtrCurCfgTableEntry OBJECT-TYPE
    SYNTAX  IgmpStaticMrtrCurCfgTableEntry
    MAX-ACCESS  not-accessible
    STATUS  current
    DESCRIPTION
        "A row in the Static Multicast Router table."
    INDEX   { igmpStaticMrtrCurCfgIndx }
    ::= { igmpStaticMrtrCurCfgTable 1 }

IgmpStaticMrtrCurCfgTableEntry ::= SEQUENCE {
    igmpStaticMrtrCurCfgIndx         INTEGER,
    igmpStaticMrtrCurCfgPortId       PortNumber,
    igmpStaticMrtrCurCfgVlanId       INTEGER,
    igmpStaticMrtrCurCfgVersion      INTEGER
    }

igmpStaticMrtrCurCfgIndx OBJECT-TYPE
    SYNTAX  INTEGER
    MAX-ACCESS  read-only
    STATUS  current
    DESCRIPTION
        "The IGMP Multicast Router table port index."
    ::= { igmpStaticMrtrCurCfgTableEntry 1 }

igmpStaticMrtrCurCfgPortId OBJECT-TYPE
    SYNTAX  PortNumber
    MAX-ACCESS  read-only
    STATUS  current
    DESCRIPTION
        "The IGMP Multicast Router port in the current configuration block."
    ::= { igmpStaticMrtrCurCfgTableEntry 2 }

igmpStaticMrtrCurCfgVlanId OBJECT-TYPE
    SYNTAX  INTEGER
    MAX-ACCESS  read-only
    STATUS  current
    DESCRIPTION
        "The IGMP Multicast Router port in the current configuration block."
    ::= { igmpStaticMrtrCurCfgTableEntry 3 }

igmpStaticMrtrCurCfgVersion OBJECT-TYPE
    SYNTAX  INTEGER {
        version1(1),
        version2(2),
        version3(3)
        }
    MAX-ACCESS  read-only
    STATUS  current
    DESCRIPTION
        "The IGMP version of the IGMP Static Multicast Router."
    ::= { igmpStaticMrtrCurCfgTableEntry 4 }

igmpStaticMrtrNewCfgTable OBJECT-TYPE
    SYNTAX  SEQUENCE OF IgmpStaticMrtrNewCfgTableEntry
    MAX-ACCESS  not-accessible
    STATUS  current
    DESCRIPTION
        "The IGMP Static Multicast Router table in the new configuration block."
    ::= { igmpStaticMrtrCfg 2 }

igmpStaticMrtrNewCfgTableEntry OBJECT-TYPE
    SYNTAX  IgmpStaticMrtrNewCfgTableEntry
    MAX-ACCESS  not-accessible
    STATUS  current
    DESCRIPTION
        "A row in the Static Multicast Router table."
    INDEX   { igmpStaticMrtrNewCfgIndx }
    ::= { igmpStaticMrtrNewCfgTable 1 }

IgmpStaticMrtrNewCfgTableEntry ::= SEQUENCE {
    igmpStaticMrtrNewCfgIndx         INTEGER,
    igmpStaticMrtrNewCfgPortId       PortNumber,
    igmpStaticMrtrNewCfgVlanId       INTEGER,
    igmpStaticMrtrNewCfgVersion      INTEGER,
    igmpStaticMrtrNewCfgDelete       INTEGER
    }

igmpStaticMrtrNewCfgIndx OBJECT-TYPE
    SYNTAX  INTEGER
    MAX-ACCESS  read-only
    STATUS  current
    DESCRIPTION
        "The IGMP Multicast Router table port index."
    ::= { igmpStaticMrtrNewCfgTableEntry 1 }

igmpStaticMrtrNewCfgPortId OBJECT-TYPE
    SYNTAX  PortNumber
    MAX-ACCESS  read-write
    STATUS  current
    DESCRIPTION
        "The IGMP Multicast Router port in the new configuration block."
    ::= { igmpStaticMrtrNewCfgTableEntry 2 }

igmpStaticMrtrNewCfgVlanId OBJECT-TYPE
    SYNTAX  INTEGER
    MAX-ACCESS  read-write
    STATUS  current
    DESCRIPTION
        "The IGMP Multicast Router port in the new configuration block."
    ::= { igmpStaticMrtrNewCfgTableEntry 3 }

igmpStaticMrtrNewCfgVersion OBJECT-TYPE
    SYNTAX  INTEGER {
        version1(1),
        version2(2),
        version3(3)
        }
    MAX-ACCESS  read-write
    STATUS  current
    DESCRIPTION
        "The IGMP version of the IGMP Static Multicast Router."
    ::= { igmpStaticMrtrNewCfgTableEntry 4 }

igmpStaticMrtrNewCfgDelete OBJECT-TYPE
    SYNTAX  INTEGER {
        other(1),
        delete(2)
        }
    MAX-ACCESS  read-write
    STATUS  current
    DESCRIPTION
        "When set to the value of 2 (delete), the entire row is deleted.
         When read, other(1) is returned. Setting the value to anything
         other than 2(delete) has no effect on the state of the row."
    ::= { igmpStaticMrtrNewCfgTableEntry 5 }

igmpStaticMrtrNewCfgClear OBJECT-TYPE
    SYNTAX  INTEGER {
        other(1),
        clear(2)
        }
    MAX-ACCESS  read-write
    STATUS  current
    DESCRIPTION
        "When set to the value of 2 (clear), the entire table is deleted.
         When read, other(1) is returned. Setting the value to anything
         other than 2(clear) has no effect on the table."
    ::= { igmpStaticMrtrCfg 3 }


-- IGMP Filtering
igmpFltCurCfgTable OBJECT-TYPE
    SYNTAX  SEQUENCE OF IgmpFltCurCfgTableEntry
    MAX-ACCESS  not-accessible
    STATUS  current
    DESCRIPTION
        "The IGMP filtering table in the current configuration block."
    ::= { igmpFilterCfg 1 }

igmpFltCurCfgTableEntry OBJECT-TYPE
    SYNTAX  IgmpFltCurCfgTableEntry
    MAX-ACCESS  not-accessible
    STATUS  current
    DESCRIPTION
        "A row in the filtering table."
    INDEX   { igmpFltCurCfgIndx }
    ::= { igmpFltCurCfgTable 1 }

IgmpFltCurCfgTableEntry ::= SEQUENCE {
    igmpFltCurCfgIndx         INTEGER,
    igmpFltCurCfgMcastIp1     IpAddress,
    igmpFltCurCfgMcastIp2     IpAddress,
    igmpFltCurCfgAction       INTEGER,
    igmpFltCurCfgState        INTEGER
    }

igmpFltCurCfgIndx OBJECT-TYPE
    SYNTAX  INTEGER
    MAX-ACCESS  read-only
    STATUS  current
    DESCRIPTION
        "The IGMP filter table index."
    ::= { igmpFltCurCfgTableEntry 1 }

igmpFltCurCfgMcastIp1 OBJECT-TYPE
    SYNTAX  IpAddress
    MAX-ACCESS  read-only
    STATUS  current
    DESCRIPTION
        "Range1 Multicast IP address to be filtered."
    ::= { igmpFltCurCfgTableEntry 2 }

igmpFltCurCfgMcastIp2 OBJECT-TYPE
    SYNTAX  IpAddress
    MAX-ACCESS  read-only
    STATUS  current
    DESCRIPTION
        "Range2 Multicast IP address to be filtered."
    ::= { igmpFltCurCfgTableEntry 3 }

igmpFltCurCfgAction OBJECT-TYPE
    SYNTAX  INTEGER {
        allow(1),
        deny(2)
        }
    MAX-ACCESS  read-only
    STATUS  current
    DESCRIPTION
        "The action for the IGMP filtering rule."
    ::= { igmpFltCurCfgTableEntry 4 }

igmpFltCurCfgState OBJECT-TYPE
    SYNTAX  INTEGER {
        enabled(1),
        disabled(2)
        }
    MAX-ACCESS  read-only
    STATUS  current
    DESCRIPTION
        "The state of this IGMP filtering rule."
    ::= { igmpFltCurCfgTableEntry 5 }

igmpFltNewCfgTable OBJECT-TYPE
    SYNTAX  SEQUENCE OF IgmpFltNewCfgTableEntry
    MAX-ACCESS  not-accessible
    STATUS  current
    DESCRIPTION
        "The IGMP filtering table in the current configuration block."
    ::= { igmpFilterCfg 2 }

igmpFltNewCfgTableEntry OBJECT-TYPE
    SYNTAX  IgmpFltNewCfgTableEntry
    MAX-ACCESS  not-accessible
    STATUS  current
    DESCRIPTION
        "A row in the filtering table."
    INDEX   { igmpFltNewCfgIndx }
    ::= { igmpFltNewCfgTable 1 }

IgmpFltNewCfgTableEntry ::= SEQUENCE {
    igmpFltNewCfgIndx         INTEGER,
    igmpFltNewCfgMcastIp1     IpAddress,
    igmpFltNewCfgMcastIp2     IpAddress,
    igmpFltNewCfgAction       INTEGER,
    igmpFltNewCfgState        INTEGER,
    igmpFltNewCfgDelete       INTEGER
    }

igmpFltNewCfgIndx OBJECT-TYPE
    SYNTAX  INTEGER
    MAX-ACCESS  read-only 
    STATUS  current
    DESCRIPTION
        "The IGMP filter table index."
    ::= { igmpFltNewCfgTableEntry 1 }

igmpFltNewCfgMcastIp1 OBJECT-TYPE
    SYNTAX  IpAddress
    MAX-ACCESS  read-write
    STATUS  current
    DESCRIPTION
        "Range1 Multicast source IP address to be filtered."
    ::= { igmpFltNewCfgTableEntry 2 }

igmpFltNewCfgMcastIp2 OBJECT-TYPE
    SYNTAX  IpAddress
    MAX-ACCESS  read-write
    STATUS  current
    DESCRIPTION
        "Range2 Multicast source IP address to be filtered."
    ::= { igmpFltNewCfgTableEntry 3 }

igmpFltNewCfgAction OBJECT-TYPE
    SYNTAX  INTEGER {
        allow(1),
        deny(2)
        }
    MAX-ACCESS  read-write
    STATUS  current
    DESCRIPTION
        "The action for the IGMP filtering rule."
    ::= { igmpFltNewCfgTableEntry 4 }

igmpFltNewCfgState OBJECT-TYPE
    SYNTAX  INTEGER {
        enabled(1),
        disabled(2)
        }
    MAX-ACCESS  read-write
    STATUS  current
    DESCRIPTION
        "The state of this IGMP filtering rule."
    ::= { igmpFltNewCfgTableEntry 5 }

igmpFltNewCfgDelete OBJECT-TYPE
    SYNTAX  INTEGER {
        other(1),
        delete(2)
        }
    MAX-ACCESS  read-write
    STATUS  current
    DESCRIPTION
        "When set to the value of 2 (delete), the entire row is deleted. 
         When read, other(1) is returned. Setting the value to anything 
         other than 2(delete) has no effect on the state of the row."
    ::= { igmpFltNewCfgTableEntry 6 }

-- IGMP Filtering Port Table

igmpFltCurCfgPortTable OBJECT-TYPE
    SYNTAX  SEQUENCE OF IgmpFltCurCfgPortTableEntry
    MAX-ACCESS  not-accessible
    STATUS  current
    DESCRIPTION
        "The IGMP filtering port table in the current configuration block."
    ::= { igmpFilterCfg 3 }

igmpFltCurCfgPortTableEntry OBJECT-TYPE
    SYNTAX  IgmpFltCurCfgPortTableEntry
    MAX-ACCESS  not-accessible
    STATUS  current
    DESCRIPTION
        "A row in the IGMP filtering port table."
    INDEX   { igmpFltCurCfgPortIndx }
    ::= { igmpFltCurCfgPortTable 1 }

IgmpFltCurCfgPortTableEntry ::= SEQUENCE {
    igmpFltCurCfgPortIndx         PortNumber,
    igmpFltCurCfgPortState        INTEGER,
    igmpFltCurCfgPortFiltBmap     OCTET STRING
    }

igmpFltCurCfgPortIndx OBJECT-TYPE
    SYNTAX  PortNumber
    MAX-ACCESS  read-only
    STATUS  current
    DESCRIPTION
        "The port index."
    ::= { igmpFltCurCfgPortTableEntry 1 }

igmpFltCurCfgPortState OBJECT-TYPE
    SYNTAX  INTEGER {
        enabled(1),
        disabled(2)
        }
    MAX-ACCESS  read-only
    STATUS  current
    DESCRIPTION
        "Enable or disable IGMP filtering."
    ::= { igmpFltCurCfgPortTableEntry 2 }

igmpFltCurCfgPortFiltBmap OBJECT-TYPE
    SYNTAX  OCTET STRING (SIZE(0..256))
    MAX-ACCESS  read-only
    STATUS  current
    DESCRIPTION
    "The IGMP filtering rules applied to the port.  The filtering rules are 
         presented in bitmap format.

     in receiving order:

         OCTET 1  OCTET 2  .....
             xxxxxxxx xxxxxxxx ..... 
             ||    || |_ filter 9
             ||    ||  
             ||    ||___ filter 8
             ||    |____ filter 7
             ||      .    .   .
             ||_________ filter 2
             |__________ filter 1 (as index to igmpFltCurCfgTable)

         where x : 1 - The represented IGMP filter rule applied to the port
           0 - The represented IGMP filter rule not applied to the port "
    ::= { igmpFltCurCfgPortTableEntry 3 }

igmpFltNewCfgPortTable OBJECT-TYPE
    SYNTAX  SEQUENCE OF IgmpFltNewCfgPortTableEntry
    MAX-ACCESS  not-accessible
    STATUS  current
    DESCRIPTION
        "The IGMP filtering port table in the new configuration block."
    ::= { igmpFilterCfg 4 }

igmpFltNewCfgPortTableEntry OBJECT-TYPE
    SYNTAX  IgmpFltNewCfgPortTableEntry
    MAX-ACCESS  not-accessible
    STATUS  current
    DESCRIPTION
        "A row in the IGMP filtering port table."
    INDEX   { igmpFltNewCfgPortIndx }
    ::= { igmpFltNewCfgPortTable 1 }

IgmpFltNewCfgPortTableEntry ::= SEQUENCE {
    igmpFltNewCfgPortIndx         PortNumber,
    igmpFltNewCfgPortState        INTEGER,
    igmpFltNewCfgPortFiltBmap     OCTET STRING,
    igmpFltNewCfgPortAddFiltRule  INTEGER,
    igmpFltNewCfgPortRemFiltRule  INTEGER
    }

igmpFltNewCfgPortIndx OBJECT-TYPE
    SYNTAX  PortNumber
    MAX-ACCESS  read-only
    STATUS  current
    DESCRIPTION
        "The port index."
    ::= { igmpFltNewCfgPortTableEntry 1 }

igmpFltNewCfgPortState OBJECT-TYPE
    SYNTAX  INTEGER {
        enabled(1),
        disabled(2)
        }
    MAX-ACCESS  read-write
    STATUS  current
    DESCRIPTION
        "Enable or disable IGMP filtering."
    ::= { igmpFltNewCfgPortTableEntry 2 }

igmpFltNewCfgPortFiltBmap OBJECT-TYPE
    SYNTAX  OCTET STRING (SIZE(0..256))
    MAX-ACCESS  read-only
    STATUS  current
    DESCRIPTION
        "The IGMP filtering rules applied to the port.  The filtering rules
         are presented in bitmap format.

         in receiving order:

         OCTET 1  OCTET 2  .....
             xxxxxxxx xxxxxxxx ..... 
             ||    || |_ filter 9
             ||    ||  
             ||    ||___ filter 8
             ||    |____ filter 7
             ||      .    .   .
             ||_________ filter 2
             |__________ filter 1 (as index to fltNewCfgTable)

         where x : 1 - The represented filter rule applied to the port
           0 - The represented filter rule not applied to the port "
    ::= { igmpFltNewCfgPortTableEntry 3 }

igmpFltNewCfgPortAddFiltRule OBJECT-TYPE
    SYNTAX  INTEGER
    MAX-ACCESS  read-write
    STATUS  current
    DESCRIPTION
        "This is an action object to add filtering rule to a port. The value 
         specified with this object is the index to the fltNewCfgTable for 
         which filtering rule to be added to the port. The range of the 
         valid index is between 1 and igmpFltCurCfgTableMaxSize. When read, the 
         value '0' is returned always."
    ::= { igmpFltNewCfgPortTableEntry 4 }

igmpFltNewCfgPortRemFiltRule OBJECT-TYPE
    SYNTAX  INTEGER
    MAX-ACCESS  read-write
    STATUS  current
    DESCRIPTION
        "This is an action object to remove filtering rule from a port. The 
         value specified with this object is the index to the fltNewCfgTable 
         for which filtering rule to be removed from the port. The range of 
         the valid index is between 1 and igmpFltCurCfgTableMaxSize.  When read, 
         the value '0' is returned always."
    ::= { igmpFltNewCfgPortTableEntry 5 }

igmpFltCurCfgEnaDis OBJECT-TYPE
    SYNTAX INTEGER { 
        enable(1),
        disable(2)
    }
    MAX-ACCESS  read-only
    STATUS  current
    DESCRIPTION
        "Enable/Disable of IGMP Filtering."
    ::= { igmpFilterCfg 5 }

igmpFltNewCfgEnaDis OBJECT-TYPE
    SYNTAX INTEGER { 
        enable(1),
        disable(2)
    }
    MAX-ACCESS  read-write
    STATUS  current
    DESCRIPTION
        "Enable/Disable of IGMP Filtering."
    ::= { igmpFilterCfg 6 }

--
-- IGMP Relay Configuration
--
igmpRelayCurCfgEnaDis OBJECT-TYPE
    SYNTAX INTEGER { 
        enabled(1),
        disabled(2)
    }
    MAX-ACCESS  read-only
    STATUS  current
    DESCRIPTION
        "The current status of IGMP Relay."
    ::= { igmpRelayCfg 1 }

igmpRelayNewCfgEnaDis OBJECT-TYPE
    SYNTAX INTEGER { 
        enable(1),
        disable(2)
    }
    MAX-ACCESS  read-write
    STATUS  current
    DESCRIPTION
        "Enable/Disable of IGMP Relay."
    ::= { igmpRelayCfg 2 }

igmpRelayNewCfgAddVlan OBJECT-TYPE
    SYNTAX  Integer32 
    MAX-ACCESS  read-write
    STATUS  current
    DESCRIPTION
        "The VLAN to be added to relay vlan list. When read,
         0 is returned."
    ::= { igmpRelayCfg 3 }

igmpRelayNewCfgRemVlan OBJECT-TYPE
    SYNTAX  Integer32 
    MAX-ACCESS  read-write
    STATUS  current
    DESCRIPTION
        "The VLAN to be removed from relay vlan list. When read,
         0 is returned."
    ::= { igmpRelayCfg 4 }

igmpRelayNewCfgClearVlan OBJECT-TYPE
    SYNTAX  INTEGER {
        clear(1),
        ok(2)
        }
    MAX-ACCESS  read-write
    STATUS  current
    DESCRIPTION
        "Removing ALL Relay Vlans."
    ::= { igmpRelayCfg 5 }

igmpRelayCurCfgVlanBmap OBJECT-TYPE
    SYNTAX OCTET STRING
    MAX-ACCESS read-only
    STATUS current
    DESCRIPTION
        "The relay vlans present in the vlan map list.
         The relay vlans are presented in a bitmap format.

         in receiving order:

         OCTET 1  OCTET 2  .....
         xxxxxxxx xxxxxxxx .....
         ||    || |_ Vlan 9
         ||    ||
         ||    ||___ Vlan 8
         ||    |____ Vlan 7
         ||      .    .   .
         ||_________ Vlan 2
         |__________ Vlan 1

         where x : 1 - The represented vlan has relay enabled
         0 - The represented vlan does not have relay enabled."
    ::= { igmpRelayCfg 6 }

igmpRelayNewCfgVlanBmap OBJECT-TYPE
    SYNTAX OCTET STRING
    MAX-ACCESS read-write
    STATUS current
    DESCRIPTION
        "The relay vlans present in the vlan map list.
         The relay vlans are presented in a bitmap format.

         in receiving order:

         OCTET 1  OCTET 2  .....
         xxxxxxxx xxxxxxxx .....
         ||    || |_ Vlan 9
         ||    ||
         ||    ||___ Vlan 8
         ||    |____ Vlan 7
         ||      .    .   .
         ||_________ Vlan 2
         |__________ Vlan 1

         where x : 1 - The represented vlan has relay enabled
         0 - The represented vlan does not have relay enabled."
    ::= { igmpRelayCfg 7 }

igmpRelayCurCfgReport OBJECT-TYPE
    SYNTAX  INTEGER(0..150)
    MAX-ACCESS  read-only
    STATUS  current
    DESCRIPTION
        "The Unsolicited Report Interval."
    ::= { igmpRelayCfg 8 }

igmpRelayNewCfgReport OBJECT-TYPE
    SYNTAX  INTEGER(0..150)
    MAX-ACCESS  read-write
    STATUS  current
    DESCRIPTION
        "Set Unsolicited Report Interval."
    ::= { igmpRelayCfg 9 }

igmpRelayMrtrCurCfgTable OBJECT-TYPE
    SYNTAX  SEQUENCE OF IgmpRelayMrtrCurCfgTableEntry
    MAX-ACCESS  not-accessible
    STATUS  current
    DESCRIPTION
        "The IGMP relay multicast router table in the
        current configuration block."
    ::= { igmpRelayCfg 10 }

igmpRelayMrtrCurCfgTableEntry OBJECT-TYPE
    SYNTAX  IgmpRelayMrtrCurCfgTableEntry
    MAX-ACCESS  not-accessible
    STATUS  current
    DESCRIPTION
        "A row in the IGMP relay multicast router table."
    INDEX   { igmpRelayMrtrCurCfgIndx }
    ::= { igmpRelayMrtrCurCfgTable 1 }

IgmpRelayMrtrCurCfgTableEntry ::= SEQUENCE {
    igmpRelayMrtrCurCfgIndx             INTEGER,
    igmpRelayMrtrCurCfgAddr             IpAddress,
    igmpRelayMrtrCurCfgEnaDis           INTEGER,
    igmpRelayMrtrCurCfgInterval         INTEGER,
    igmpRelayMrtrCurCfgRetry            INTEGER,
    igmpRelayMrtrCurCfgRestr            INTEGER,
    igmpRelayMrtrCurCfgVersion          INTEGER
    }

igmpRelayMrtrCurCfgIndx OBJECT-TYPE
    SYNTAX  INTEGER(1..2)
    MAX-ACCESS  read-only
    STATUS  current
    DESCRIPTION
        "The IGMP relay multicast router table index."
    ::= { igmpRelayMrtrCurCfgTableEntry 1 }

igmpRelayMrtrCurCfgAddr OBJECT-TYPE
    SYNTAX  IpAddress
    MAX-ACCESS  read-only
    STATUS  current
    DESCRIPTION
        "The IP address of the multicast router."
    ::= { igmpRelayMrtrCurCfgTableEntry 2 }

igmpRelayMrtrCurCfgEnaDis OBJECT-TYPE
    SYNTAX  INTEGER{ 
        enabled(1),
        disabled(2)
        }
    MAX-ACCESS  read-only
    STATUS  current
    DESCRIPTION
        "The status of the multicast router."
    ::= { igmpRelayMrtrCurCfgTableEntry 3 }

igmpRelayMrtrCurCfgInterval OBJECT-TYPE
    SYNTAX  INTEGER(1..60)
    MAX-ACCESS  read-only
    STATUS  current
    DESCRIPTION
        "The interval between ping attempts."
    ::= { igmpRelayMrtrCurCfgTableEntry 4 }

igmpRelayMrtrCurCfgRetry OBJECT-TYPE
    SYNTAX  INTEGER(1..120)
    MAX-ACCESS  read-only
    STATUS  current
    DESCRIPTION
        "The number of failed attempts to declare router DOWN."
    ::= { igmpRelayMrtrCurCfgTableEntry 5 }

igmpRelayMrtrCurCfgRestr OBJECT-TYPE
    SYNTAX  INTEGER(1..128)
    MAX-ACCESS  read-only
    STATUS  current
    DESCRIPTION
        "The number of successful attempts to declare router UP."
    ::= { igmpRelayMrtrCurCfgTableEntry 6 }

igmpRelayMrtrCurCfgVersion OBJECT-TYPE
    SYNTAX  INTEGER{
       igmpv1(1),
       igmpv2(2)
      }
    MAX-ACCESS  read-only
    STATUS  current
    DESCRIPTION
        "The IGMP version."
    ::= { igmpRelayMrtrCurCfgTableEntry 7 }

igmpRelayMrtrNewCfgTable OBJECT-TYPE
    SYNTAX  SEQUENCE OF IgmpRelayMrtrNewCfgTableEntry
    MAX-ACCESS  not-accessible
    STATUS  current
    DESCRIPTION
        "The IGMP relay multicast router table in the
        new configuration block."
    ::= { igmpRelayCfg 11 }

igmpRelayMrtrNewCfgTableEntry OBJECT-TYPE
    SYNTAX  IgmpRelayMrtrNewCfgTableEntry
    MAX-ACCESS  not-accessible
    STATUS  current
    DESCRIPTION
        "A row in the IGMP relay multicast router table."
    INDEX   { igmpRelayMrtrNewCfgIndx }
    ::= { igmpRelayMrtrNewCfgTable 1 }

IgmpRelayMrtrNewCfgTableEntry ::= SEQUENCE {
    igmpRelayMrtrNewCfgIndx             INTEGER,
    igmpRelayMrtrNewCfgAddr             IpAddress,
    igmpRelayMrtrNewCfgEnaDis           INTEGER,
    igmpRelayMrtrNewCfgInterval         INTEGER,
    igmpRelayMrtrNewCfgRetry            INTEGER,
    igmpRelayMrtrNewCfgRestr            INTEGER,
    igmpRelayMrtrNewCfgVersion          INTEGER,
    igmpRelayMrtrNewCfgRemove           INTEGER
    }

igmpRelayMrtrNewCfgIndx OBJECT-TYPE
    SYNTAX  INTEGER(1..2)
    MAX-ACCESS  read-only
    STATUS  current
    DESCRIPTION
        "The IGMP relay multicast router table index."
    ::= { igmpRelayMrtrNewCfgTableEntry 1 }

igmpRelayMrtrNewCfgAddr OBJECT-TYPE
    SYNTAX  IpAddress
    MAX-ACCESS  read-write
    STATUS  current
    DESCRIPTION
        "The IP address of the multicast router."
    ::= { igmpRelayMrtrNewCfgTableEntry 2 }

igmpRelayMrtrNewCfgEnaDis OBJECT-TYPE
    SYNTAX  INTEGER{ 
        enable(1),
        disable(2)
        }
    MAX-ACCESS  read-write
    STATUS  current
    DESCRIPTION
        "The status of the multicast router."
    ::= { igmpRelayMrtrNewCfgTableEntry 3 }

igmpRelayMrtrNewCfgInterval OBJECT-TYPE
    SYNTAX  INTEGER(1..60)
    MAX-ACCESS  read-write
    STATUS  current
    DESCRIPTION
        "The interval between ping attempts."
    ::= { igmpRelayMrtrNewCfgTableEntry 4 }

igmpRelayMrtrNewCfgRetry OBJECT-TYPE
    SYNTAX  INTEGER(1..120)
    MAX-ACCESS  read-write
    STATUS  current
    DESCRIPTION
        "The number of failed attempts to declare router DOWN."
    ::= { igmpRelayMrtrNewCfgTableEntry 5 }

igmpRelayMrtrNewCfgRestr OBJECT-TYPE
    SYNTAX  INTEGER(1..128)
    MAX-ACCESS  read-write
    STATUS  current
    DESCRIPTION
        "The number of successful attempts to declare router UP."
    ::= { igmpRelayMrtrNewCfgTableEntry 6 }

igmpRelayMrtrNewCfgVersion OBJECT-TYPE
    SYNTAX  INTEGER{
       igmpv1(1),
       igmpv2(2)
      }
    MAX-ACCESS  read-write
    STATUS  current
    DESCRIPTION
        "The IGMP version."
    ::= { igmpRelayMrtrNewCfgTableEntry 7 }

igmpRelayMrtrNewCfgRemove OBJECT-TYPE
    SYNTAX INTEGER {
        clear(1),
        ok(2)
        }
    MAX-ACCESS  read-write
    STATUS  current
    DESCRIPTION
        "Delete the IGMP Relay multicast router."
    ::= { igmpRelayMrtrNewCfgTableEntry 8 }

--
-- IGMP Configuration  Advanced Menu
--
igmpAdvCurCfgQInterval OBJECT-TYPE
    SYNTAX  INTEGER(1..600)
    MAX-ACCESS  read-only
    STATUS  current
    DESCRIPTION
        "The IGMP Query Interval of current config."
    ::= { igmpAdvCfg 1 }

igmpAdvNewCfgQInterval OBJECT-TYPE
    SYNTAX  INTEGER(1..600)
    MAX-ACCESS  read-write
    STATUS  current
    DESCRIPTION
        "The IGMP Query Interval of new config."
    ::= { igmpAdvCfg 2 }

igmpAdvCurCfgRobust OBJECT-TYPE
    SYNTAX  INTEGER(1..10) 
    MAX-ACCESS  read-only
    STATUS  current
    DESCRIPTION
        "The value of expected packet loss on subnet in current config."
    ::= { igmpAdvCfg 3 }

igmpAdvNewCfgRobust OBJECT-TYPE
    SYNTAX   INTEGER(1..10)
    MAX-ACCESS  read-write
    STATUS  current
    DESCRIPTION
        "Set the value of expected packet loss on subnet."
    ::= { igmpAdvCfg 4 }

igmpAdvCurCfgTimeout OBJECT-TYPE
    SYNTAX  INTEGER(1..255)
    MAX-ACCESS  read-only
    STATUS  current
    DESCRIPTION
        "The IGMP Report timeout."
    ::= { igmpAdvCfg 5 }

igmpAdvNewCfgTimeout OBJECT-TYPE
    SYNTAX  INTEGER(1..255)
    MAX-ACCESS  read-write
    STATUS  current
    DESCRIPTION
        "Set IGMP Report timeout."
    ::= { igmpAdvCfg 6 }

igmpAdvNewCfgVlanFastlvAdd OBJECT-TYPE
    SYNTAX  Integer32 
    MAX-ACCESS  read-write
    STATUS  current
    DESCRIPTION
        "The VLAN to be added to quick-leave vlan list. When read,
         0 is returned."
    ::= { igmpAdvCfg 7 }

igmpAdvNewCfgVlanFastlvRem OBJECT-TYPE
    SYNTAX  Integer32 
    MAX-ACCESS  read-write
    STATUS  current
    DESCRIPTION
        "The VLAN to be removed from quick-leave vlan list. When read,
         0 is returned."
    ::= { igmpAdvCfg 8 }

igmpAdvCurCfgVlanFastlvBmap OBJECT-TYPE
    SYNTAX OCTET STRING
    MAX-ACCESS read-only
    STATUS current
    DESCRIPTION
        "The fast-leave enabled vlans present in the vlan map list.
         The fast-leave enabled vlans are presented in a bitmap format.

         in receiving order:

         OCTET 1  OCTET 2  .....
         xxxxxxxx xxxxxxxx .....
         ||    || |_ Vlan 9
         ||    ||
         ||    ||___ Vlan 8
         ||    |____ Vlan 7
         ||      .    .   .
         ||_________ Vlan 2
         |__________ Vlan 1

         where x : 1 - The represented vlan has fast-leave enabled
         0 - The represented vlan does not have fast-leave enabled."
    ::= { igmpAdvCfg 9 }

igmpAdvNewCfgVlanFastlvBmap OBJECT-TYPE
    SYNTAX OCTET STRING
    MAX-ACCESS read-write
    STATUS current
    DESCRIPTION
        "The fast-leave enabled vlans present in the vlan map list.
         The fast-leave enabled vlans are presented in a bitmap format.

         in receiving order:

         OCTET 1  OCTET 2  .....
         xxxxxxxx xxxxxxxx .....
         ||    || |_ Vlan 9
         ||    ||
         ||    ||___ Vlan 8
         ||    |____ Vlan 7
         ||      .    .   .
         ||_________ Vlan 2
         |__________ Vlan 1

         where x : 1 - The represented vlan has fast-leave enabled
         0 - The represented vlan does not have fast-leave enabled."
    ::= { igmpAdvCfg 10 }



igmpAdvCurCfgRtrAlert OBJECT-TYPE
    SYNTAX  INTEGER{
        enabled(1),
        disabled(2)
        }
    MAX-ACCESS  read-only
    STATUS  current
    DESCRIPTION
        "Enable/disable sending IGMP messages with Router Alert option."
    ::= { igmpAdvCfg 15 }

igmpAdvNewCfgRtrAlert OBJECT-TYPE
    SYNTAX  INTEGER{
        enabled(1),
        disabled(2)
        }
    MAX-ACCESS  read-write
    STATUS  current
    DESCRIPTION
        "Enable/disable sending IGMP messages with Router Alert option."
    ::= { igmpAdvCfg 16 }


igmpCurQurCfgTable OBJECT-TYPE
    SYNTAX  SEQUENCE OF IgmpCurQurCfgEntry
    MAX-ACCESS  not-accessible
    STATUS  current
    DESCRIPTION
        "The table of IGMP querier configuration."
    ::= { igmpCfg 15 }

igmpCurQurCfgEntry OBJECT-TYPE
    SYNTAX  IgmpCurQurCfgEntry
    MAX-ACCESS  not-accessible
    STATUS  current
    DESCRIPTION
        "A row in the IGMP querier configuration table"
    INDEX   { igmpCurQurCfgVlanIndex }
    ::= { igmpCurQurCfgTable 1 }

IgmpCurQurCfgEntry ::= SEQUENCE {
    igmpCurQurCfgVlanIndex             INTEGER,
    igmpCurQuerierState                INTEGER,
    igmpCurCfgQuerier                  INTEGER,
    igmpCurCfgQueryInterval            INTEGER,
    igmpCurCfgQurSrcIp                 IpAddress,
    igmpCurCfgElectionType             INTEGER,
    igmpCurCfgQurRobustness            INTEGER,
    igmpCurCfgQurStartupCnt            INTEGER,
    igmpCurCfgQurStartupInt            INTEGER,
    igmpCurCfgQurMaxRespTime           INTEGER,
    igmpCurCfgOtherQurAddress          DisplayString,
    igmpCurCfgOtherQurPresentInt       DisplayString,
    igmpCurCfgVlanOperVersion          INTEGER,
    igmpCurVlanOperVersion             INTEGER, 
    igmpCurVlanOlderVerTimer           DisplayString
    }

igmpCurQurCfgVlanIndex OBJECT-TYPE
    SYNTAX  INTEGER(1..4094)
    MAX-ACCESS  read-only
    STATUS current
    DESCRIPTION
        "The vlan number for which the IGMP querier information is related."
    ::= { igmpCurQurCfgEntry 1}

igmpCurQuerierState OBJECT-TYPE
    SYNTAX  INTEGER { 
    querier(1),
    nonQuerier(2),
    checkingMembership(3)
    }
    MAX-ACCESS  read-only
    STATUS current
    DESCRIPTION
        "Indicates whether the switch is running as a querier in the VLAN.
         Based on the querier election, if elected as a querier, it will
         send  query messages. If the switch receives the query message with
         lower IP/MAC any other querier in the VLAN, It will move to non querier
         state. If a leave is received then querier moves to checking membership state."
    ::= { igmpCurQurCfgEntry 2}

igmpCurCfgQuerier OBJECT-TYPE
    SYNTAX  INTEGER { 
    enabled(1),
    disabled(2)
    }
    MAX-ACCESS  read-only
    STATUS current
    DESCRIPTION
       "The snooping switch can be configured to send IGMP queries.
        querier  are not present in the VLAN and it set to
        'enabled' the switch will generate general query messages.
        The query messages will be suppressed if the switch receives
        the query message from any other querier with lower IP/MAC in the VLAN."
    ::= { igmpCurQurCfgEntry 3}

igmpCurCfgQueryInterval OBJECT-TYPE
    SYNTAX  INTEGER(1..608)
    MAX-ACCESS  read-only
    STATUS  current
    DESCRIPTION
        "This is the interval (in seconds) for which the switch
         sends general queries when it is configured as a querier for
         the VLAN."
    ::= { igmpCurQurCfgEntry 4 }

igmpCurCfgQurSrcIp OBJECT-TYPE
    SYNTAX  IpAddress
    MAX-ACCESS  read-only
    STATUS  current
    DESCRIPTION
        "The source ip for GSQ proxy in this vlan. This Src Ip will be used in
         querier election mechanism. It will be the source address in queries sent bye
         the switch."
    ::= { igmpCurQurCfgEntry 5 }

igmpCurCfgElectionType OBJECT-TYPE
    SYNTAX  INTEGER { 
    ipv4(1),
    macaddr(2)
    }
    MAX-ACCESS  read-only
    STATUS current
    DESCRIPTION
        "The querier selection type specify the criteria to be used to elect
         querier for this VLAN. When a switch is configured as a querier,
         this will define the election criteria . e.g. MAC or source IP-address."
    ::= { igmpCurQurCfgEntry 6 }

igmpCurCfgQurRobustness OBJECT-TYPE
    SYNTAX  INTEGER(1..10)
    MAX-ACCESS  read-only
    STATUS  current
    DESCRIPTION
        "The Robustness Variable allows tuning for the Other
         Querier Present Interval."
    ::= { igmpCurQurCfgEntry 7 }

igmpCurCfgQurStartupCnt OBJECT-TYPE
    SYNTAX  INTEGER(1..10)
    MAX-ACCESS  read-only
    STATUS  current
    DESCRIPTION
        "Represents the number of Queries sent out on startup of
         querier election, separated by the Startup Query Interval."
    ::= { igmpCurQurCfgEntry 8 }

igmpCurCfgQurStartupInt OBJECT-TYPE
    SYNTAX  INTEGER(1..608)
    MAX-ACCESS  read-only
    STATUS  current
    DESCRIPTION
        "This variable represents the interval(in seconds) between General
          Queries sent by a Querier on startup. By default: 1/4 the Query Interval."
    ::= { igmpCurQurCfgEntry 9 }

igmpCurCfgQurMaxRespTime OBJECT-TYPE
    SYNTAX  INTEGER(1..256)
    MAX-ACCESS  read-only
    STATUS  current
    DESCRIPTION
        "The maximum query response interval advertised in
          IGMP queries on this VLAN."
    ::= { igmpCurQurCfgEntry 10 }

igmpCurCfgOtherQurAddress OBJECT-TYPE  
   SYNTAX DisplayString (SIZE(0..128))
    MAX-ACCESS read-only
    STATUS current
    DESCRIPTION
    "The  IP/MAC Address of the  Querier, which has won the Querier election,
    when bosSnoopVlanCfgQuerier is enabled on this vlan."
    ::= { igmpCurQurCfgEntry 11 }
 

igmpCurCfgOtherQurPresentInt OBJECT-TYPE  
   SYNTAX DisplayString (SIZE(0..128))
    MAX-ACCESS read-only
    STATUS current
    DESCRIPTION
    "The Other Querier Present Interval is the length of time that must
    pass before switch decides that there is no longer another 
    multicast router which should be the querier.  This value
    is ((the Robustness Variable) times (the Query Interval)) plus
    (one half of one Query Response Interval)."
        ::= { igmpCurQurCfgEntry 12 }

igmpCurCfgVlanOperVersion OBJECT-TYPE
    SYNTAX  INTEGER { 
    igmpV1(1),
    igmpV2(2),
    igmpV3(3)
    }
    MAX-ACCESS  read-only
    STATUS current
    DESCRIPTION
        "Indicates the operating version of the IGMP snooping switch for
         a specific VLAN. The default operating mode on a specific VLAN
         is IGMP version 3 i.e, V3(3). The 'bosIgsVlanCfgOperVersion'
         should be configured on the basis of the version of the router
         present in the VLAN."
    ::= { igmpCurQurCfgEntry 13 }

igmpCurVlanOperVersion OBJECT-TYPE
    SYNTAX  INTEGER { 
    igmpV1(1),
    igmpV2(2),
    igmpV3(3)
    }
    MAX-ACCESS  read-only
    STATUS current
    DESCRIPTION
        "Indicates the operating version of the IGMP snooping switch for
         specific VLAN. The default operating mode on a specific VLAN
         IGMP version 3 i.e, V3(3)."
    ::= { igmpCurQurCfgEntry 14 }

igmpCurVlanOlderVerTimer OBJECT-TYPE  
    SYNTAX DisplayString (SIZE(0..128))
    MAX-ACCESS read-only
    STATUS current
    DESCRIPTION
    "Indicates the remaining time of lowest operating version of the vlan.
    For interoperability with multicast routers/switches/Hosts, running older 
    versions of IGMP, systems maintain a IGMP Version variable for each Vlan.
    In order to switch gracefully between versions of IGMP, hosts keep both an
    IGMPv1 Querier Present timer and an IGMPv2 Querier Present timer per Vlan.
    According to RFC 3376 this value is ((the Robustness Variable) times 
    (the Query Interval)) plus (one Query Response Interval)."
    ::= { igmpCurQurCfgEntry 15 }



igmpNewQurCfgTable OBJECT-TYPE
    SYNTAX  SEQUENCE OF IgmpNewQurCfgEntry
    MAX-ACCESS  not-accessible
    STATUS  current
    DESCRIPTION
        "The table of IGMP querier configuration."
    ::= { igmpCfg 16 }

igmpNewQurCfgEntry OBJECT-TYPE
    SYNTAX  IgmpNewQurCfgEntry
    MAX-ACCESS  not-accessible
    STATUS  current
    DESCRIPTION
        "A row in the IGMP querier configuration table"
    INDEX   { igmpNewQurCfgVlanIndex }
    ::= { igmpNewQurCfgTable 1 }


IgmpNewQurCfgEntry ::= SEQUENCE {
    igmpNewQurCfgVlanIndex             INTEGER,
    igmpNewQuerierState                INTEGER,
    igmpNewCfgQuerier                  INTEGER,
    igmpNewCfgQueryInterval            INTEGER,
    igmpNewCfgQurSrcIp                 IpAddress,
    igmpNewCfgElectionType             INTEGER,
    igmpNewCfgQurRobustness            INTEGER,
    igmpNewCfgQurStartupCnt            INTEGER,
    igmpNewCfgQurStartupInt            INTEGER,
    igmpNewCfgQurMaxRespTime           INTEGER,
    igmpNewCfgOtherQurAddress          DisplayString,
    igmpNewCfgOtherQurPresentInt       DisplayString,
    igmpNewCfgVlanOperVersion          INTEGER,
    igmpNewVlanOperVersion             INTEGER, 
    igmpNewVlanOlderVerTimer           DisplayString,
    igmpNewCfgQuerierDefault           INTEGER
    }

igmpNewQurCfgVlanIndex OBJECT-TYPE
    SYNTAX  INTEGER(1..4094)
    MAX-ACCESS  read-only
    STATUS current
    DESCRIPTION
        "The vlan number for which the IGMP querier information is related."
    ::= { igmpNewQurCfgEntry 1}

igmpNewQuerierState OBJECT-TYPE
    SYNTAX  INTEGER { 
    querier(1),
    nonQuerier(2),
    checkingMembership(3)
    }
    MAX-ACCESS  read-only
    STATUS current
    DESCRIPTION
        "Indicates whether the switch is running as a querier in the VLAN.
         Based on the querier election, if elected as a querier, it will
         send  query messages. If the switch receives the query message with
         lower IP/MAC any other querier in the VLAN, It will move to non querier
         state. If a leave is received then querier moves to checking membership state."
    ::= { igmpNewQurCfgEntry 2}

igmpNewCfgQuerier OBJECT-TYPE
    SYNTAX  INTEGER { 
    enabled(1),
    disabled(2)
    }
    MAX-ACCESS  read-write
    STATUS current
    DESCRIPTION
       "The snooping switch can be configured to send IGMP queries.
        querier  are not present in the VLAN and it set to
        'enabled' the switch will generate general query messages.
        The query messages will be suppressed if the switch receives
        the query message from any other querier with lower IP/MAC in the VLAN."
    ::= { igmpNewQurCfgEntry 3}

igmpNewCfgQueryInterval OBJECT-TYPE
    SYNTAX  INTEGER(1..608)
    MAX-ACCESS  read-write
    STATUS  current
    DESCRIPTION
        "This is the interval (in seconds) for which the switch
         sends general queries when it is configured as a querier for
         the VLAN."
    ::= { igmpNewQurCfgEntry 4 }

igmpNewCfgQurSrcIp OBJECT-TYPE
    SYNTAX  IpAddress
    MAX-ACCESS  read-write
    STATUS  current
    DESCRIPTION
        "The source ip for GSQ proxy in this vlan. This Src Ip will be used in
         querier election mechanism. It will be the source address in queries sent bye
         the switch."
    ::= { igmpNewQurCfgEntry 5 }

igmpNewCfgElectionType OBJECT-TYPE
    SYNTAX  INTEGER { 
    ipv4(1),
    macaddr(2)
    }
    MAX-ACCESS  read-write
    STATUS current
    DESCRIPTION
        "The querier selection type specify the criteria to be used to elect
         querier for this VLAN. When a switch is configured as a querier,
         this will define the election criteria . e.g. MAC or source IP-address."
    ::= { igmpNewQurCfgEntry 6 }

igmpNewCfgQurRobustness OBJECT-TYPE
    SYNTAX  INTEGER(1..10)
    MAX-ACCESS  read-write
    STATUS  current
    DESCRIPTION
        "The Robustness Variable allows tuning for the Other
         Querier Present Interval."
    ::= { igmpNewQurCfgEntry 7 }

igmpNewCfgQurStartupCnt OBJECT-TYPE
    SYNTAX  INTEGER(1..10)
    MAX-ACCESS  read-write
    STATUS  current
    DESCRIPTION
        "Represents the number of Queries sent out on startup of
         querier election, separated by the Startup Query Interval."
    ::= { igmpNewQurCfgEntry 8 }

igmpNewCfgQurStartupInt OBJECT-TYPE
    SYNTAX  INTEGER(1..608)
    MAX-ACCESS  read-write
    STATUS  current
    DESCRIPTION
        "This variable represents the interval(in seconds) between General
          Queries sent by a Querier on startup. By default: 1/4 the Query Interval."
    ::= { igmpNewQurCfgEntry 9 }

igmpNewCfgQurMaxRespTime OBJECT-TYPE
    SYNTAX  INTEGER(1..256)
    MAX-ACCESS  read-write
    STATUS  current
    DESCRIPTION
        "The maximum query response interval advertised in
          IGMP queries on this VLAN."
    ::= { igmpNewQurCfgEntry 10 }

igmpNewCfgOtherQurAddress OBJECT-TYPE  
   SYNTAX DisplayString (SIZE(0..128))
    MAX-ACCESS read-only
    STATUS current
    DESCRIPTION
    "The  IP/MAC Address of the  Querier, which has won the Querier election,
    when bosSnoopVlanCfgQuerier is enabled on this vlan."
    ::= { igmpNewQurCfgEntry 11 }
 

igmpNewCfgOtherQurPresentInt OBJECT-TYPE  
   SYNTAX DisplayString (SIZE(0..128))
    MAX-ACCESS read-only
    STATUS current
    DESCRIPTION
    "The Other Querier Present Interval is the length of time that must
    pass before switch decides that there is no longer another 
    multicast router which should be the querier.  This value
    is ((the Robustness Variable) times (the Query Interval)) plus
    (one half of one Query Response Interval)."
    ::= { igmpNewQurCfgEntry 12 }

igmpNewCfgVlanOperVersion OBJECT-TYPE
    SYNTAX  INTEGER { 
    igmpV1(1),
    igmpV2(2),
    igmpV3(3)
    }
    MAX-ACCESS  read-write
    STATUS current
    DESCRIPTION
        "Indicates the operating version of the IGMP snooping switch for
         a specific VLAN. The default operating mode on a specific VLAN
         is IGMP version 3 i.e, V3(3). The 'igmpNewCfgVlanOperVersion'
         should be configured on the basis of the version of the mrouter
         present in the VLAN."
    ::= { igmpNewQurCfgEntry 13 }

igmpNewVlanOperVersion OBJECT-TYPE
    SYNTAX  INTEGER { 
    igmpV1(1),
    igmpV2(2),
    igmpV3(3)
    }
    MAX-ACCESS  read-only
    STATUS current
    DESCRIPTION
        "Indicates the operating version of the IGMP snooping switch for
         specific VLAN. The default operating mode on a specific VLAN
         IGMP version 3 i.e, V3(3)."
    ::= { igmpNewQurCfgEntry 14 }

igmpNewVlanOlderVerTimer OBJECT-TYPE  
    SYNTAX DisplayString (SIZE(0..128))
    MAX-ACCESS read-only
    STATUS current
    DESCRIPTION
    "Indicates the remaining time of lowest operating version of the vlan.
    For interoperability with multicast routers/switches/Hosts, running older 
    versions of IGMP, systems maintain a IGMP Version variable for each Vlan.
    In order to switch gracefully between versions of IGMP, hosts keep both an
    IGMPv1 Querier Present timer and an IGMPv2 Querier Present timer per Vlan.
    According to RFC 3376 this value is ((the Robustness Variable) times 
    (the Query Interval)) plus (one Query Response Interval)."
    ::= { igmpNewQurCfgEntry 15 }

igmpNewCfgQuerierDefault OBJECT-TYPE
    SYNTAX INTEGER {
        other(1),
        default(2)
    }
    MAX-ACCESS read-write
    STATUS     current
    DESCRIPTION
      "Action to set the default IGMP Querier settings on a Vlan.
       Returns other(1) when read."
    ::= { igmpNewQurCfgEntry 16 }

igmpCurCfgQuerierOnOff OBJECT-TYPE
    SYNTAX INTEGER { 
        on(1),
        off(2)
    }
    MAX-ACCESS  read-only
    STATUS  current
    DESCRIPTION
        "The current status of IGMP Querier."
    ::= { igmpCfg 17}

igmpNewCfgQuerierOnOff OBJECT-TYPE
    SYNTAX INTEGER { 
        on(1),
        off(2)
    }
    MAX-ACCESS  read-write
    STATUS  current
    DESCRIPTION
        "Globally turn IGMP Querier On/Off."
    ::= { igmpCfg 18}



--
-- IPMC Static Route Configuration
--
ipmcStaticRouteCfg  OBJECT IDENTIFIER ::= { layer3Configs 20 }

ipmcStaticRouteTableMaxSize OBJECT-TYPE
    SYNTAX  Integer32
    MAX-ACCESS  read-only
    STATUS  current
    DESCRIPTION
        "The maximum number of rows in the IPMC Static Route table."
    ::= { ipmcStaticRouteCfg 1 }

ipmcCurCfgStaticRouteTable OBJECT-TYPE
    SYNTAX  SEQUENCE OF IpmcCurCfgStaticRouteEntry
    MAX-ACCESS  not-accessible
    STATUS  current
    DESCRIPTION
        "The table of static IPMC routes in the current configuration block."
    ::= { ipmcStaticRouteCfg 2 }

ipmcCurCfgStaticRouteEntry OBJECT-TYPE
    SYNTAX  IpmcCurCfgStaticRouteEntry
    MAX-ACCESS  not-accessible
    STATUS  current
    DESCRIPTION
        "A row in the static IPMC route table"
    INDEX   { ipmcCurCfgStaticRouteIndx }
    ::= { ipmcCurCfgStaticRouteTable 1 }

IpmcCurCfgStaticRouteEntry ::= SEQUENCE {
    ipmcCurCfgStaticRouteIndx             Integer32,
    ipmcCurCfgStaticRouteDestIp           IpAddress,
    ipmcCurCfgStaticRouteVlanId           Integer32,
    ipmcCurCfgStaticRouteHostBmap         OCTET STRING,
    ipmcCurCfgStaticRoutePMrtrBmap        OCTET STRING,
    ipmcCurCfgStaticRouteBMrtrBmap        OCTET STRING,
    ipmcCurCfgStaticRouteVrid             Integer32,
    ipmcCurCfgStaticRouteAdminkeys        DisplayString,
    ipmcCurCfgStaticRouteTrunks           OCTET STRING
    }

ipmcCurCfgStaticRouteIndx OBJECT-TYPE
    SYNTAX  Integer32
    MAX-ACCESS  read-only
    STATUS  current
    DESCRIPTION
        "The index of the IPMC static routing table."
    ::= { ipmcCurCfgStaticRouteEntry 1}

ipmcCurCfgStaticRouteDestIp OBJECT-TYPE
    SYNTAX  IpAddress
    MAX-ACCESS  read-only
    STATUS  current
    DESCRIPTION
        "The destination IPMC address of this IPMC route."
    ::= { ipmcCurCfgStaticRouteEntry 2}

ipmcCurCfgStaticRouteVlanId OBJECT-TYPE 
    SYNTAX  Integer32
    MAX-ACCESS  read-only 
    STATUS  current 
    DESCRIPTION 
        "The vlan id of this route."
    ::= { ipmcCurCfgStaticRouteEntry 3}

ipmcCurCfgStaticRouteHostBmap OBJECT-TYPE 
    SYNTAX  OCTET STRING
    MAX-ACCESS  read-only 
    STATUS  current 
    DESCRIPTION 
        "The Host ports that are added to this IPMC port bitmap.
         The selected ports are presented in a bitmap format
         in receiving order:

             OCTET 1  OCTET 2  .....
             xxxxxxxx xxxxxxxx .....
             ||    || |_ Port 9
             ||    ||
             ||    ||___ Port 8
             ||    |____ Port 7
             ||      .    .   .
             ||_________ Port 2
             |__________ Port 1

             where x : 1 - The represented Host Port is added
                       0 - The represented Host Port is not added"

    ::= { ipmcCurCfgStaticRouteEntry 4}

ipmcCurCfgStaticRoutePMrtrBmap OBJECT-TYPE 
    SYNTAX  OCTET STRING
    MAX-ACCESS  read-only 
    STATUS  current 
    DESCRIPTION 
        "The Primary Mrouter ports that are added to this IPMC port bitmap.
         The selected ports are presented in a bitmap format
         in receiving order:

             OCTET 1  OCTET 2  .....
             xxxxxxxx xxxxxxxx .....
             ||    || |_ Port 9
             ||    ||
             ||    ||___ Port 8
             ||    |____ Port 7
             ||      .    .   .
             ||_________ Port 2
             |__________ Port 1

             where x : 1 - The represented Primary Mrouter Port is added
                       0 - The represented Primary Mrouter Port is not added"

    ::= { ipmcCurCfgStaticRouteEntry 5}

ipmcCurCfgStaticRouteBMrtrBmap OBJECT-TYPE 
    SYNTAX  OCTET STRING
    MAX-ACCESS  read-only 
    STATUS  current 
    DESCRIPTION 
        "The Backup Mrouter ports that are added to this IPMC port bitmap.
         The selected ports are presented in a bitmap format
         in receiving order:

             OCTET 1  OCTET 2  .....
             xxxxxxxx xxxxxxxx .....
             ||    || |_ Port 9
             ||    ||
             ||    ||___ Port 8
             ||    |____ Port 7
             ||      .    .   .
             ||_________ Port 2
             |__________ Port 1

             where x : 1 - The represented Backup Mrouter Port is added
                       0 - The represented Backup Mrouter Port is not added"

    ::= { ipmcCurCfgStaticRouteEntry 6}

ipmcCurCfgStaticRouteVrid OBJECT-TYPE 
    SYNTAX  Integer32
    MAX-ACCESS  read-only 
    STATUS  current 
    DESCRIPTION 
        "The virtual router id of this route."
    ::= { ipmcCurCfgStaticRouteEntry 7}

ipmcCurCfgStaticRouteAdminkeys OBJECT-TYPE
    SYNTAX  DisplayString (SIZE(1..128))
    MAX-ACCESS  read-only
    STATUS  current
    DESCRIPTION
        "The LACP port adminkey of this route.
         Adminkeys on five positions alligned to right, separated by commas."
    ::= { ipmcCurCfgStaticRouteEntry 8}

ipmcCurCfgStaticRouteTrunks      OBJECT-TYPE
    SYNTAX  OCTET STRING
    MAX-ACCESS  read-only
    STATUS  current
    DESCRIPTION
        "The trunk list for this IPMC route. The trunks are presented in bitmap format.
         in receiving order:

              OCTET 1  OCTET 2  .....
             xxxxxxxx xxxxxxxx .....
             ||    || |_ trunk 8
             ||    ||
             ||    ||___ trunk 7
             ||    |____ trunk 6
             ||      .    .   .
             ||_________ trunk 1
             |__________ reserved

         where x : 1 - The represented trunk belongs to IPMC route
                   0 - The represented trunk does not belong to IPMC route"
    ::= { ipmcCurCfgStaticRouteEntry 9 }

ipmcNewCfgStaticRouteTable OBJECT-TYPE
    SYNTAX  SEQUENCE OF IpmcNewCfgStaticRouteEntry
    MAX-ACCESS  not-accessible
    STATUS  current
    DESCRIPTION
        "The table of IPMC static routes in the new
         configuration block.
         When creating a new route, Destination IP
         and Vlan id must be set first.
         The actual change in configuration occurs
         on using PortInfo leaf."
    ::= { ipmcStaticRouteCfg 3 }

ipmcNewCfgStaticRouteEntry OBJECT-TYPE
    SYNTAX  IpmcNewCfgStaticRouteEntry
    MAX-ACCESS  not-accessible
    STATUS  current
    DESCRIPTION
        "A row in the static IPMC route table"
    INDEX   { ipmcNewCfgStaticRouteIndx }
    ::= { ipmcNewCfgStaticRouteTable 1 }

IpmcNewCfgStaticRouteEntry ::= SEQUENCE {
    ipmcNewCfgStaticRouteIndx             Integer32,
    ipmcNewCfgStaticRouteDestIp           IpAddress,
    ipmcNewCfgStaticRouteVlanId           Integer32,
    ipmcNewCfgStaticRouteHostBmap         OCTET STRING,
    ipmcNewCfgStaticRoutePMrtrBmap        OCTET STRING,
    ipmcNewCfgStaticRouteBMrtrBmap        OCTET STRING,
    ipmcNewCfgStaticRouteAddPort             Integer32,
    ipmcNewCfgStaticRouteRemPort             Integer32,
    ipmcNewCfgStaticRouteTrunks           OCTET STRING,
    ipmcNewCfgStaticRouteAddTrunk         INTEGER,
    ipmcNewCfgStaticRouteRemTrunk         INTEGER,
    ipmcNewCfgStaticRouteAdminkeys        DisplayString,
    ipmcNewCfgStaticRouteAddAdminkey      INTEGER,
    ipmcNewCfgStaticRouteRemAdminkey      INTEGER,
    ipmcNewCfgStaticRoutePortInfo         INTEGER,
    ipmcNewCfgStaticRouteVrid             Integer32,
    ipmcNewCfgStaticRouteDelete           INTEGER
    }

ipmcNewCfgStaticRouteIndx OBJECT-TYPE
    SYNTAX  Integer32
    MAX-ACCESS  read-only
    STATUS  current
    DESCRIPTION
        "The index of the IPMC static routing table."
    ::= { ipmcNewCfgStaticRouteEntry 1}

ipmcNewCfgStaticRouteDestIp OBJECT-TYPE
    SYNTAX  IpAddress
    MAX-ACCESS  read-create
    STATUS  current
    DESCRIPTION
        "The destination IPMC address of this route.
         It must be set along Vlan id before creating
         new route."
    ::= { ipmcNewCfgStaticRouteEntry 2}

ipmcNewCfgStaticRouteVlanId OBJECT-TYPE 
    SYNTAX  Integer32
    MAX-ACCESS  read-create 
    STATUS  current 
    DESCRIPTION 
        "The vlan id of this route.
         It must be set along Destination IP before
         creating new route."
    ::= { ipmcNewCfgStaticRouteEntry 3}

ipmcNewCfgStaticRouteHostBmap OBJECT-TYPE 
    SYNTAX  OCTET STRING
    MAX-ACCESS  read-only 
    STATUS  current 
    DESCRIPTION 
        "The Host ports that are added to this IPMC port bitmap.
         The selected ports are presented in a bitmap format
         in receiving order:

             OCTET 1  OCTET 2  .....
             xxxxxxxx xxxxxxxx .....
             ||    || |_ Port 9
             ||    ||
             ||    ||___ Port 8
             ||    |____ Port 7
             ||      .    .   .
             ||_________ Port 2
             |__________ Port 1

             where x : 1 - The represented Host Port is added
                       0 - The represented Host Port is not added"

    ::= { ipmcNewCfgStaticRouteEntry 4}

ipmcNewCfgStaticRoutePMrtrBmap OBJECT-TYPE 
    SYNTAX  OCTET STRING
    MAX-ACCESS  read-only 
    STATUS  current 
    DESCRIPTION 
        "The Primary Mrouter ports that are added to this IPMC port bitmap.
         The selected ports are presented in a bitmap format
         in receiving order:

             OCTET 1  OCTET 2  .....
             xxxxxxxx xxxxxxxx .....
             ||    || |_ Port 9
             ||    ||
             ||    ||___ Port 8
             ||    |____ Port 7
             ||      .    .   .
             ||_________ Port 2
             |__________ Port 1

             where x : 1 - The represented Primary Mrouter Port is added
                       0 - The represented Primary Mrouter Port is not added"

    ::= { ipmcNewCfgStaticRouteEntry 5}

ipmcNewCfgStaticRouteBMrtrBmap OBJECT-TYPE 
    SYNTAX  OCTET STRING
    MAX-ACCESS  read-only 
    STATUS  current 
    DESCRIPTION 
        "The Backup Mrouter ports that are added to this IPMC port bitmap.
         The selected ports are presented in a bitmap format
         in receiving order:

             OCTET 1  OCTET 2  .....
             xxxxxxxx xxxxxxxx .....
             ||    || |_ Port 9
             ||    ||
             ||    ||___ Port 8
             ||    |____ Port 7
             ||      .    .   .
             ||_________ Port 2
             |__________ Port 1

             where x : 1 - The represented Backup Mrouter Port is added
                       0 - The represented Backup Mrouter Port is not added"

    ::= { ipmcNewCfgStaticRouteEntry 6}

ipmcNewCfgStaticRouteAddPort OBJECT-TYPE
    SYNTAX  Integer32
    MAX-ACCESS  read-create
    STATUS  current
    DESCRIPTION
        "The port to be added to this IPMC route.
         Next step is using ipmcNewCfgStaticRoutePortInfo leaf
         in order to make the actual change.
         When creating a new route, be sure to set Destination IP
         and Vlan Id before using this leaf."
    ::= { ipmcNewCfgStaticRouteEntry 7}

ipmcNewCfgStaticRouteRemPort OBJECT-TYPE
    SYNTAX  Integer32
    MAX-ACCESS  read-create
    STATUS  current
    DESCRIPTION
        "The port to be removed from this IPMC route.
         Not allowed to delete ports that are part of trunks."
    ::= { ipmcNewCfgStaticRouteEntry 17}

ipmcNewCfgStaticRouteTrunks      OBJECT-TYPE
    SYNTAX  OCTET STRING
    MAX-ACCESS  read-only
    STATUS  current
    DESCRIPTION
        "The trunk list for this IPMC route. The trunks are presented in bitmap format.
         in receiving order:

              OCTET 1  OCTET 2  .....
             xxxxxxxx xxxxxxxx .....
             ||    || |_ trunk 8
             ||    ||
             ||    ||___ trunk 7
             ||    |____ trunk 6
             ||      .    .   .
             ||_________ trunk 1
             |__________ reserved

         where x : 1 - The represented trunk belongs to ipmc
                   0 - The represented trunk does not belong to ipmc"
    ::= { ipmcNewCfgStaticRouteEntry 8 }

ipmcNewCfgStaticRouteAddTrunk OBJECT-TYPE
    SYNTAX  INTEGER
    MAX-ACCESS  read-create
    STATUS  current
    DESCRIPTION
        "The trunk group number to be added to this IPMC route.
         Next step is using ipmcNewCfgStaticRoutePortInfo leaf
         in order to make the actual change.
         A '0' value is returned when read.
         When creating a new route, be sure to set Destination IP
         and Vlan Id before using this leaf."
    ::= { ipmcNewCfgStaticRouteEntry 9 }

ipmcNewCfgStaticRouteRemTrunk OBJECT-TYPE
    SYNTAX  INTEGER
    MAX-ACCESS  read-create
    STATUS  current
    DESCRIPTION
        "The trunk group number to be removed from this IPMC route.
         Next step is using ipmcNewCfgStaticRoutePortInfo leaf
         in order to make the actual change.
         A '0' value is returned when read."
    ::= { ipmcNewCfgStaticRouteEntry 10 }

ipmcNewCfgStaticRouteAdminkeys OBJECT-TYPE
    SYNTAX  DisplayString (SIZE(1..128))
    MAX-ACCESS  read-only
    STATUS  current
    DESCRIPTION
        "The LACP port adminkeys list for to this IPMC route.
         Adminkeys on five positions alligned to right, separated by commas"
    ::= { ipmcNewCfgStaticRouteEntry 11 }

ipmcNewCfgStaticRouteAddAdminkey OBJECT-TYPE
    SYNTAX  INTEGER
    MAX-ACCESS  read-write
    STATUS  current
    DESCRIPTION
        "The LACP port adminkey to be added to this IPMC route.
         Next step is using ipmcNewCfgStaticRoutePortInfo leaf
         in order to make the actual change.
         A '0' value is returned when read.
         When creating a new route, be sure to set Destination IP
         and Vlan Id before using this leaf."
    ::= { ipmcNewCfgStaticRouteEntry 12 }

ipmcNewCfgStaticRouteRemAdminkey OBJECT-TYPE
    SYNTAX  INTEGER
    MAX-ACCESS  read-write
    STATUS  current
    DESCRIPTION
        "The LACP port adminkey to be removed from this IPMC route.
         Next step is using ipmcNewCfgStaticRoutePortInfo leaf
         in order to make the actual change.
         A '0' value is returned when read."
    ::= { ipmcNewCfgStaticRouteEntry 13 }

ipmcNewCfgStaticRoutePortInfo OBJECT-TYPE
    SYNTAX  INTEGER {
                host(1),
                primary(2),
                backup(3)
            }
    MAX-ACCESS  read-create
    STATUS  current
    DESCRIPTION
        "The Port/Trunk/Adminkey Information to be added to 
         this IPMC route (host/primary/backup). Use it only
         right after you set a new port/trunk/adminkey to
         specify its type.
         Warning: If snooping is enabled, primary/backup 
         routes will be converted to host."
    ::= { ipmcNewCfgStaticRouteEntry 14 }

ipmcNewCfgStaticRouteVrid OBJECT-TYPE 
    SYNTAX  Integer32
    MAX-ACCESS  read-create 
    STATUS  current 
    DESCRIPTION 
        "The virtual router id of this route."
    ::= { ipmcNewCfgStaticRouteEntry 15}

ipmcNewCfgStaticRouteDelete OBJECT-TYPE
    SYNTAX  INTEGER {
        delete(2),
        deletehost(3),
        deleteprimary(4),
        deletebackup(5),
        no(0)
    }
    MAX-ACCESS read-write
    STATUS current
    DESCRIPTION
        "Delete this route."
    ::= { ipmcNewCfgStaticRouteEntry 16}

ipmcStaticRouteClearAll OBJECT-TYPE
    SYNTAX INTEGER {
        ok(1),
        clear(2)
        }
    MAX-ACCESS  read-write
    STATUS  current
    DESCRIPTION
        "When set to clear(2),clears all static IPMC routes. Otherwhise nothing
is done."
    ::= { ipmcStaticRouteCfg 4 }


--
-- Static ARP Configuration
--
ipStaticArpTableMaxSize OBJECT-TYPE
    SYNTAX  Integer32
    MAX-ACCESS  read-only
    STATUS  current
    DESCRIPTION
        "The maximum number of rows in the Static ARP table."
    ::= { ipStaticArpCfg 1 }

ipCurCfgStaticArpTable OBJECT-TYPE
    SYNTAX  SEQUENCE OF IpCurCfgStaticArpEntry
    MAX-ACCESS  not-accessible
    STATUS  current
    DESCRIPTION
        "The table of static ARPs in the current configuration block."
    ::= { ipStaticArpCfg 2 }

ipCurCfgStaticArpEntry OBJECT-TYPE
    SYNTAX  IpCurCfgStaticArpEntry
    MAX-ACCESS  not-accessible
    STATUS  current
    DESCRIPTION
        "A row in the static ARP table"
    INDEX   { ipCurCfgStaticArpIndx }
    ::= { ipCurCfgStaticArpTable 1 }

IpCurCfgStaticArpEntry ::= SEQUENCE {
    ipCurCfgStaticArpIndx         Integer32,
    ipCurCfgStaticArpIp           IpAddress,
    ipCurCfgStaticArpMAC          DisplayString,
    ipCurCfgStaticArpVlan         Integer32,
    ipCurCfgStaticArpPort         PortNumber
    }

ipCurCfgStaticArpIndx OBJECT-TYPE
    SYNTAX  Integer32
    MAX-ACCESS  read-only
    STATUS  current
    DESCRIPTION
        "The index of the static ARP table."
    ::= { ipCurCfgStaticArpEntry 1}

ipCurCfgStaticArpIp OBJECT-TYPE
    SYNTAX  IpAddress
    MAX-ACCESS  read-only
    STATUS  current
    DESCRIPTION
        "The IP address for the ARP entry."
    ::= { ipCurCfgStaticArpEntry 2}

ipCurCfgStaticArpMAC OBJECT-TYPE
    SYNTAX  DisplayString
    MAX-ACCESS  read-only
    STATUS  current
    DESCRIPTION
        "The MAC address for the ARP entry."
    ::= { ipCurCfgStaticArpEntry 3 }

ipCurCfgStaticArpVlan OBJECT-TYPE 
    SYNTAX  Integer32
    MAX-ACCESS  read-only 
    STATUS  current 
    DESCRIPTION 
        "The VLAN for the ARP entry."
    ::= { ipCurCfgStaticArpEntry 4}

ipCurCfgStaticArpPort OBJECT-TYPE 
    SYNTAX  PortNumber
    MAX-ACCESS  read-only 
    STATUS  current 
    DESCRIPTION 
        "The port for the ARP entry."
    ::= { ipCurCfgStaticArpEntry 5}


ipNewCfgStaticArpTable OBJECT-TYPE
    SYNTAX  SEQUENCE OF IpNewCfgStaticArpEntry
    MAX-ACCESS  not-accessible
    STATUS  current
    DESCRIPTION
        "The table of static ARPs in the new configuration block."
    ::= { ipStaticArpCfg 3 }

ipNewCfgStaticArpEntry OBJECT-TYPE
    SYNTAX  IpNewCfgStaticArpEntry
    MAX-ACCESS  not-accessible
    STATUS  current
    DESCRIPTION
        "A row in the static ARP table"
    INDEX   { ipNewCfgStaticArpIndx }
    ::= { ipNewCfgStaticArpTable 1 }

IpNewCfgStaticArpEntry ::= SEQUENCE {
    ipNewCfgStaticArpIndx         Integer32,
    ipNewCfgStaticArpIp           IpAddress,
    ipNewCfgStaticArpMAC          DisplayString,
    ipNewCfgStaticArpVlan         Integer32,
    ipNewCfgStaticArpPort         PortNumber,
    ipNewCfgStaticArpAction       INTEGER
    }

ipNewCfgStaticArpIndx OBJECT-TYPE
    SYNTAX  Integer32
    MAX-ACCESS  read-only
    STATUS  current
    DESCRIPTION
        "The index of the static ARP table."
    ::= { ipNewCfgStaticArpEntry 1}

ipNewCfgStaticArpIp OBJECT-TYPE
    SYNTAX  IpAddress
    MAX-ACCESS  read-create
    STATUS  current
    DESCRIPTION
        "The IP address for the ARP entry."
    ::= { ipNewCfgStaticArpEntry 2}

ipNewCfgStaticArpMAC OBJECT-TYPE
    SYNTAX  DisplayString
    MAX-ACCESS  read-create
    STATUS  current
    DESCRIPTION
        "The MAC address for the ARP entry."
    ::= { ipNewCfgStaticArpEntry 3 }

ipNewCfgStaticArpVlan OBJECT-TYPE 
    SYNTAX  Integer32
    MAX-ACCESS  read-create 
    STATUS  current 
    DESCRIPTION 
        "The VLAN for the ARP entry."
    ::= { ipNewCfgStaticArpEntry 4}

ipNewCfgStaticArpPort OBJECT-TYPE 
    SYNTAX  PortNumber
    MAX-ACCESS  read-create 
    STATUS  current 
    DESCRIPTION 
        "The port for the ARP entry."
    ::= { ipNewCfgStaticArpEntry 5}

ipNewCfgStaticArpAction OBJECT-TYPE
    SYNTAX  INTEGER {
        other(1),
        delete(2)
       }  
    MAX-ACCESS  read-create
    STATUS  current
    DESCRIPTION
        "When set to the value of 2 (delete), the entire row is deleted. 
         When read, other is returned. Setting the value to anything other 
         than 2(delete) has no effect on the state of the row."
    ::= { ipNewCfgStaticArpEntry 6 }


ipStaticArpClearAll OBJECT-TYPE
    SYNTAX INTEGER {
        ok(1),
        clear(2)
        }
    MAX-ACCESS  read-write
    STATUS  current
    DESCRIPTION
        "When set to clear(2), clears all static ARP entries. Otherwise
         nothing is done."
    ::= { ipStaticArpCfg 4 }


--
-- Static NBR Configuration
--
ipStaticNbrTableMaxSize OBJECT-TYPE
    SYNTAX  Integer32
    MAX-ACCESS  read-only
    STATUS  current
    DESCRIPTION
        "The maximum number of rows in the Static NBR Cache table."
    ::= { ipStaticNbrCfg 1 }

ipCurCfgStaticNbrTable OBJECT-TYPE
    SYNTAX  SEQUENCE OF IpCurCfgStaticNbrEntry
    MAX-ACCESS  not-accessible
    STATUS  current
    DESCRIPTION
        "The table of static NBR Cache entries in the current configuration block."
    ::= { ipStaticNbrCfg 2 }

ipCurCfgStaticNbrEntry OBJECT-TYPE
    SYNTAX  IpCurCfgStaticNbrEntry
    MAX-ACCESS  not-accessible
    STATUS  current
    DESCRIPTION
        "A row in the static NBR Cache table"
    INDEX   { ipCurCfgStaticNbrIndx }
    ::= { ipCurCfgStaticNbrTable 1 }

IpCurCfgStaticNbrEntry ::= SEQUENCE {
    ipCurCfgStaticNbrIndx         Integer32,
    ipCurCfgStaticNbrIp           DisplayString,
    ipCurCfgStaticNbrMAC          DisplayString,
    ipCurCfgStaticNbrVlan         Integer32,
    ipCurCfgStaticNbrPort         PortNumber
    }

ipCurCfgStaticNbrIndx OBJECT-TYPE
    SYNTAX  Integer32
    MAX-ACCESS  read-only
    STATUS  current
    DESCRIPTION
        "The index of the static NBR Cache table."
    ::= { ipCurCfgStaticNbrEntry 1}

ipCurCfgStaticNbrIp OBJECT-TYPE
    SYNTAX  DisplayString 
    MAX-ACCESS  read-only
    STATUS  current
    DESCRIPTION
        "The IP address for the NBR Cache entry."
    ::= { ipCurCfgStaticNbrEntry 2}

ipCurCfgStaticNbrMAC OBJECT-TYPE
    SYNTAX  DisplayString
    MAX-ACCESS  read-only
    STATUS  current
    DESCRIPTION
        "The MAC address for the NBR Cache entry."
    ::= { ipCurCfgStaticNbrEntry 3 }

ipCurCfgStaticNbrVlan OBJECT-TYPE 
    SYNTAX  Integer32
    MAX-ACCESS  read-only 
    STATUS  current 
    DESCRIPTION 
        "The VLAN for the NBR Cache entry."
    ::= { ipCurCfgStaticNbrEntry 4}

ipCurCfgStaticNbrPort OBJECT-TYPE 
    SYNTAX  PortNumber
    MAX-ACCESS  read-only 
    STATUS  current 
    DESCRIPTION 
        "The port for the NBR Cache entry."
    ::= { ipCurCfgStaticNbrEntry 5}


ipNewCfgStaticNbrTable OBJECT-TYPE
    SYNTAX  SEQUENCE OF IpNewCfgStaticNbrEntry
    MAX-ACCESS  not-accessible
    STATUS  current
    DESCRIPTION
        "The table of static NBR Cache entries in the new configuration block."
    ::= { ipStaticNbrCfg 3 }

ipNewCfgStaticNbrEntry OBJECT-TYPE
    SYNTAX  IpNewCfgStaticNbrEntry
    MAX-ACCESS  not-accessible
    STATUS  current
    DESCRIPTION
        "A row in the static NBR Cache table"
    INDEX   { ipNewCfgStaticNbrIndx }
    ::= { ipNewCfgStaticNbrTable 1 }

IpNewCfgStaticNbrEntry ::= SEQUENCE {
    ipNewCfgStaticNbrIndx         Integer32,
    ipNewCfgStaticNbrIp           DisplayString,
    ipNewCfgStaticNbrMAC          DisplayString,
    ipNewCfgStaticNbrVlan         Integer32,
    ipNewCfgStaticNbrPort         PortNumber,
    ipNewCfgStaticNbrAction       INTEGER
    }

ipNewCfgStaticNbrIndx OBJECT-TYPE
    SYNTAX  Integer32
    MAX-ACCESS  read-only
    STATUS  current
    DESCRIPTION
        "The index of the static NBR Cache table."
    ::= { ipNewCfgStaticNbrEntry 1}

ipNewCfgStaticNbrIp OBJECT-TYPE
    SYNTAX  DisplayString  (SIZE(0..40))
    MAX-ACCESS  read-create
    STATUS  current
    DESCRIPTION
        "The IP address for the NBR Cache entry."
    ::= { ipNewCfgStaticNbrEntry 2}

ipNewCfgStaticNbrMAC OBJECT-TYPE
    SYNTAX  DisplayString
    MAX-ACCESS  read-create
    STATUS  current
    DESCRIPTION
        "The MAC address for the NBR Cache entry."
    ::= { ipNewCfgStaticNbrEntry 3 }

ipNewCfgStaticNbrVlan OBJECT-TYPE 
    SYNTAX  Integer32
    MAX-ACCESS  read-create 
    STATUS  current 
    DESCRIPTION 
        "The VLAN for the NBR Cache entry."
    ::= { ipNewCfgStaticNbrEntry 4}

ipNewCfgStaticNbrPort OBJECT-TYPE 
    SYNTAX  PortNumber
    MAX-ACCESS  read-create 
    STATUS  current 
    DESCRIPTION 
        "The port for the NBR Cache entry."
    ::= { ipNewCfgStaticNbrEntry 5}

ipNewCfgStaticNbrAction OBJECT-TYPE
    SYNTAX  INTEGER {
        other(1),
        delete(2)
       }  
    MAX-ACCESS  read-create
    STATUS  current
    DESCRIPTION
        "When set to the value of 2 (delete), the entire row is deleted. 
         When read, other is returned. Setting the value to anything other 
         than 2(delete) has no effect on the state of the row."
    ::= { ipNewCfgStaticNbrEntry 6 }


ipStaticNbrClearAll OBJECT-TYPE
    SYNTAX INTEGER {
        ok(1),
        clear(2)
        }       
    MAX-ACCESS  read-write
    STATUS  current
    DESCRIPTION
        "When set to clear(2),clears all static NBR Cache entries. Otherwhise nothing is done."
    ::= { ipStaticNbrCfg 4 }

--
-- IP Static Route6 Configuration
--
ipStaticRoute6TableMaxSize OBJECT-TYPE
    SYNTAX  Integer32
    MAX-ACCESS  read-only
    STATUS  current
    DESCRIPTION
        "The maximum number of rows in the Static Route6 table."
    ::= { ipStaticRoute6Cfg 1 }


ipCurCfgStaticRoute6Table OBJECT-TYPE
    SYNTAX  SEQUENCE OF IpCurCfgStaticRoute6Entry
    MAX-ACCESS  not-accessible
    STATUS  current
    DESCRIPTION
        "The table of static IP6 routes in the current configuration block."
    ::= { ipStaticRoute6Cfg 2 }

ipCurCfgStaticRoute6Entry OBJECT-TYPE
    SYNTAX  IpCurCfgStaticRoute6Entry
    MAX-ACCESS  not-accessible
    STATUS  current
    DESCRIPTION
        "A row in the static IP6 route table"
    INDEX   { ipCurCfgStaticRoute6Indx }
    ::= { ipCurCfgStaticRoute6Table 1 }

IpCurCfgStaticRoute6Entry ::= SEQUENCE {
    ipCurCfgStaticRoute6Indx         Integer32,
    ipCurCfgStaticRoute6DestIp       DisplayString,
    ipCurCfgStaticRoute6Mask         INTEGER,
    ipCurCfgStaticRoute6Gateway      DisplayString,
    ipCurCfgStaticRoute6Interface    Integer32
    }

ipCurCfgStaticRoute6Indx OBJECT-TYPE
    SYNTAX  Integer32
    MAX-ACCESS  read-only
    STATUS  current
    DESCRIPTION
        "The index of the static IP6 routing table."
    ::= { ipCurCfgStaticRoute6Entry 1}

ipCurCfgStaticRoute6DestIp OBJECT-TYPE
    SYNTAX  DisplayString
    MAX-ACCESS  read-only
    STATUS  current
    DESCRIPTION
        "The destination IP6 address of this route."
    ::= { ipCurCfgStaticRoute6Entry 2}

ipCurCfgStaticRoute6Mask OBJECT-TYPE 
    SYNTAX  INTEGER (0..128)
    MAX-ACCESS  read-only 
    STATUS  current 
    DESCRIPTION 
        "The destination IP6 prefix len of this route."
    ::= { ipCurCfgStaticRoute6Entry 3}

ipCurCfgStaticRoute6Gateway OBJECT-TYPE 
    SYNTAX  DisplayString
    MAX-ACCESS  read-only 
    STATUS  current 
    DESCRIPTION 
        "The IP6 address of the gateway for this route."
    ::= { ipCurCfgStaticRoute6Entry 4}

ipCurCfgStaticRoute6Interface OBJECT-TYPE
    SYNTAX  Integer32
    MAX-ACCESS  read-only 
    STATUS  current 
    DESCRIPTION 
        "The IP6 interface of this route.  The IP6 address of the specified 
         interface shall be used as source IP when performs routing."
    ::= { ipCurCfgStaticRoute6Entry 5}

ipNewCfgStaticRoute6Table OBJECT-TYPE
    SYNTAX  SEQUENCE OF IpNewCfgStaticRoute6Entry
    MAX-ACCESS  not-accessible
    STATUS  current
    DESCRIPTION
        "The table of static IP6 routes in the new configuration block."
    ::= { ipStaticRoute6Cfg 3 }

ipStaticRoute6ClearAllByDestIp OBJECT-TYPE
    SYNTAX  DisplayString
    MAX-ACCESS  read-write
    STATUS  current
    DESCRIPTION
        "Clears all static IP6 routes with the specified destination IP6 address."
    ::= { ipStaticRoute6Cfg 4}

ipStaticRoute6ClearAllByGatewayIp OBJECT-TYPE
    SYNTAX  DisplayString
    MAX-ACCESS  read-write
    STATUS  current
    DESCRIPTION
        "Clears all static IP6 routes with the specified gateway IP address."
    ::= { ipStaticRoute6Cfg 5}

ipStaticRoute6ClearAllByInterface OBJECT-TYPE
    SYNTAX  INTEGER
    MAX-ACCESS  read-write
    STATUS  current
    DESCRIPTION
        "Clears all IP6 routes on the specified inteface number."
    ::= { ipStaticRoute6Cfg 6}

ipStaticRoute6ClearAll OBJECT-TYPE
    SYNTAX INTEGER {
    ok(1),
    clear(2)
    }
    MAX-ACCESS  read-write
    STATUS  current
    DESCRIPTION
        "When set to clear(2), clears all IP6 static routes. Otherwise
         nothing is done."
    ::= { ipStaticRoute6Cfg 7}

ipNewCfgStaticRoute6Entry OBJECT-TYPE
    SYNTAX  IpNewCfgStaticRoute6Entry
    MAX-ACCESS  not-accessible
    STATUS  current
    DESCRIPTION
        "A row in the static IP6 route table"
    INDEX   { ipNewCfgStaticRoute6Indx }
    ::= { ipNewCfgStaticRoute6Table 1 }

IpNewCfgStaticRoute6Entry ::= SEQUENCE {
    ipNewCfgStaticRoute6Indx         Integer32,
    ipNewCfgStaticRoute6DestIp       DisplayString,
    ipNewCfgStaticRoute6Mask         INTEGER,
    ipNewCfgStaticRoute6Gateway      DisplayString,
    ipNewCfgStaticRoute6Action       INTEGER,
    ipNewCfgStaticRoute6Interface    Integer32
    }

ipNewCfgStaticRoute6Indx OBJECT-TYPE
    SYNTAX  Integer32
    MAX-ACCESS  read-only
    STATUS  current
    DESCRIPTION
        "The index of the static IP6 routing table."
    ::= { ipNewCfgStaticRoute6Entry 1}

ipNewCfgStaticRoute6DestIp OBJECT-TYPE
    SYNTAX  DisplayString  (SIZE(0..40))
    MAX-ACCESS  read-create
    STATUS  current
    DESCRIPTION
        "The destination IP6 address of this route.
         Address should be 16-byte hexadecimal colon notation.
         Valid IPv6 address should be in any of the following forms
           xxxx:xxxx:xxxx:xxxx:xxxx:xxxx:xxxx:xxxx or
           xxxx::xxxx:xxxx:xxxx:xxxx"
    ::= { ipNewCfgStaticRoute6Entry 2}

ipNewCfgStaticRoute6Mask OBJECT-TYPE 
    SYNTAX  INTEGER (0..128)
    MAX-ACCESS  read-create 
    STATUS  current 
    DESCRIPTION 
        "The prefix length of this route."
    ::= { ipNewCfgStaticRoute6Entry 3}

ipNewCfgStaticRoute6Gateway OBJECT-TYPE 
    SYNTAX  DisplayString  (SIZE(0..40))
    MAX-ACCESS  read-create 
    STATUS  current 
    DESCRIPTION 
        "The IP6 address of the gateway for this route.
         Address should be 16-byte hexadecimal colon notation.
         Valid IPv6 address should be in any of the following forms
           xxxx:xxxx:xxxx:xxxx:xxxx:xxxx:xxxx:xxxx or
           xxxx::xxxx:xxxx:xxxx:xxxx"
    ::= { ipNewCfgStaticRoute6Entry 4}

ipNewCfgStaticRoute6Action OBJECT-TYPE
    SYNTAX  INTEGER {
        other(1),
        delete(2)
       }  
    MAX-ACCESS  read-create
    STATUS  current
    DESCRIPTION
        "Set the value '2' to delete the entire route entry. 
         Value 1 (other) is returned when read."
    ::= { ipNewCfgStaticRoute6Entry 5 }

ipNewCfgStaticRoute6Interface OBJECT-TYPE
    SYNTAX  Integer32
    MAX-ACCESS  read-create
    STATUS  current
    DESCRIPTION
        "The IP6 interface of this route.  The IP6 address of the specified
         interface shall be used as source IP when performs routing."
    ::= { ipNewCfgStaticRoute6Entry 6 }


--
-- IPv6 Default Gateway Configuration
--

ipGatewayIpv6TableMax OBJECT-TYPE
    SYNTAX  Integer32
    MAX-ACCESS  read-only
    STATUS  current
    DESCRIPTION
        "The maximum number of rows in the IPv6 gateway table."
    ::= { ipGatewayIpv6Cfg 1 }

ipCurCfgGwIpv6Table OBJECT-TYPE
    SYNTAX  SEQUENCE OF IpCurCfgGwIpv6Entry
    MAX-ACCESS  not-accessible
    STATUS  current
    DESCRIPTION
        "The table of IPv6 gateways in the Current configuration Block."
    ::= { ipGatewayIpv6Cfg 2 }

ipCurCfgGwIpv6Entry OBJECT-TYPE
    SYNTAX  IpCurCfgGwIpv6Entry
    MAX-ACCESS  not-accessible
    STATUS  current
    DESCRIPTION
        "A row in the Ipv6 gateway table"
    INDEX   { ipCurCfgGwIpv6Index }
    ::= { ipCurCfgGwIpv6Table 1 }

IpCurCfgGwIpv6Entry ::= SEQUENCE {
    ipCurCfgGwIpv6Index    Integer32,
    ipCurCfgGwIpv6Addr     DisplayString,
    ipCurCfgGwIpv6State    INTEGER
    }

ipCurCfgGwIpv6Index OBJECT-TYPE
    SYNTAX  Integer32
    MAX-ACCESS  read-only
    STATUS  current
    DESCRIPTION
        "The IPv6 gateway number for which the information is related."
    ::= { ipCurCfgGwIpv6Entry 1}

ipCurCfgGwIpv6Addr OBJECT-TYPE
    SYNTAX   DisplayString (SIZE(0..40))
    MAX-ACCESS  read-only
    STATUS  current
    DESCRIPTION
        "The IPv6 address of the gateway. Address should be 4-byte
         hexadecimal colon notation.
         Valid IPv6 address should be in any of the following forms
           xxxx:xxxx:xxxx:xxxx:xxxx:xxxx:xxxx:xxxx or
           xxxx::xxxx:xxxx:xxxx:xxxx or 
        fe80:xxxx:xxxx:xxxx:xxxx:xxxx:xxxx:xxxx%interface"
    ::= { ipCurCfgGwIpv6Entry 2 }
    
ipCurCfgGwIpv6State OBJECT-TYPE
    SYNTAX  INTEGER {
        enabled(2),
        disabled(3)
        }
    MAX-ACCESS  read-only
    STATUS  current
    DESCRIPTION
        "The state of the default IPv6 gateway."
    ::= { ipCurCfgGwIpv6Entry 3 }

ipNewCfgGwIpv6Table OBJECT-TYPE
    SYNTAX  SEQUENCE OF IpNewCfgGwIpv6Entry
    MAX-ACCESS  not-accessible
    STATUS  current
    DESCRIPTION
        "The table of IPv6 gateways in the new configuration block."
    ::= { ipGatewayIpv6Cfg 3 }

ipNewCfgGwIpv6Entry OBJECT-TYPE
    SYNTAX  IpNewCfgGwIpv6Entry
    MAX-ACCESS  not-accessible
    STATUS  current
    DESCRIPTION
        "A row in the Ipv6 gateway table"
    INDEX   { ipNewCfgGwIpv6Index }
    ::= { ipNewCfgGwIpv6Table 1 }

IpNewCfgGwIpv6Entry ::= SEQUENCE {
    ipNewCfgGwIpv6Index    Integer32,
    ipNewCfgGwIpv6Addr     DisplayString,
    ipNewCfgGwIpv6State    INTEGER,
    ipNewCfgGwIpv6Delete   INTEGER
    }

ipNewCfgGwIpv6Index OBJECT-TYPE
    SYNTAX  Integer32
    MAX-ACCESS  read-only
    STATUS  current
    DESCRIPTION
        "The IPv6 gateway number for which the information is related."
    ::= { ipNewCfgGwIpv6Entry 1}

ipNewCfgGwIpv6Addr OBJECT-TYPE
    SYNTAX   DisplayString (SIZE(0..40))
    MAX-ACCESS  read-create
    STATUS  current
    DESCRIPTION
        "The IPv6 address of the gateway. Address should be 4-byte
         hexadecimal colon notation.
         Valid IPv6 address should be in any of the following forms
           xxxx:xxxx:xxxx:xxxx:xxxx:xxxx:xxxx:xxxx or
           xxxx::xxxx:xxxx:xxxx:xxxx"
    ::= { ipNewCfgGwIpv6Entry 2 }
    
ipNewCfgGwIpv6State OBJECT-TYPE
    SYNTAX  INTEGER {
        enabled(2),
        disabled(3)
        }
    MAX-ACCESS  read-create
    STATUS  current
    DESCRIPTION
        "The state of the default IPv6 gateway."
    ::= { ipNewCfgGwIpv6Entry 3 }

ipNewCfgGwIpv6Delete  OBJECT-TYPE
    SYNTAX  INTEGER {
        other(1),
        delete(2)
       }
    MAX-ACCESS  read-create
    STATUS  current
    DESCRIPTION
        "When set to the value of 2 (delete), the default gw is deleted.
         When read, other is returned. Setting the value to anything other
         than 2(delete) has no effect on the state of the default IPv6 gw."
    ::= { ipNewCfgGwIpv6Entry 4 }

--
-- Prefix policy table Configuration
--
pptTableMaxSize OBJECT-TYPE
    SYNTAX  Integer32
    MAX-ACCESS  read-only
    STATUS  current
    DESCRIPTION
        "The maximum number of rows in the Prefix policy table."
    ::= { pptCfg 1 }

pptCurCfgTable OBJECT-TYPE
    SYNTAX  SEQUENCE OF PPTCurCfgEntry
    MAX-ACCESS  not-accessible
    STATUS  current
    DESCRIPTION
        "The table of prefix policy table entries in the current configuration block."
    ::= { pptCfg 2 }

pptCurCfgEntry OBJECT-TYPE
    SYNTAX  PPTCurCfgEntry
    MAX-ACCESS  not-accessible
    STATUS  current
    DESCRIPTION
        "A row in the prefix policy table"
    INDEX   { pptCurCfgIndx }
    ::= { pptCurCfgTable 1 }

PPTCurCfgEntry ::= SEQUENCE {
    pptCurCfgIndx         Integer32,
    pptCurCfgPrefix       DisplayString,
    pptCurCfgPrefixLen    Integer32,
    pptCurCfgPrecedence   Integer32,
    pptCurCfgLabel        Integer32
    }

pptCurCfgIndx OBJECT-TYPE
    SYNTAX  Integer32
    MAX-ACCESS  read-only
    STATUS  current
    DESCRIPTION
        "The index of the prefix policy table."
    ::= { pptCurCfgEntry 1}

pptCurCfgPrefix OBJECT-TYPE
    SYNTAX  DisplayString 
    MAX-ACCESS  read-only
    STATUS  current
    DESCRIPTION
        "The prefix address for the prefix policy table entry."
    ::= { pptCurCfgEntry 2}

pptCurCfgPrefixLen OBJECT-TYPE 
    SYNTAX  Integer32
    MAX-ACCESS  read-only 
    STATUS  current 
    DESCRIPTION 
        "The prefix length for the prefix policy table entry."
    ::= { pptCurCfgEntry 3}

pptCurCfgPrecedence OBJECT-TYPE 
    SYNTAX  Integer32
    MAX-ACCESS  read-only 
    STATUS  current 
    DESCRIPTION 
        "The precedence for the prefix policy table entry."
    ::= { pptCurCfgEntry 4}

pptCurCfgLabel OBJECT-TYPE 
    SYNTAX  Integer32
    MAX-ACCESS  read-only 
    STATUS  current 
    DESCRIPTION 
        "The label for the prefix policy table entry."
    ::= { pptCurCfgEntry 5}

pptNewCfgTable OBJECT-TYPE
    SYNTAX  SEQUENCE OF PPTNewCfgEntry
    MAX-ACCESS  not-accessible
    STATUS  current
    DESCRIPTION
        "The table of prefix policy table entries in the new configuration block."
    ::= { pptCfg 3 }

pptNewCfgEntry OBJECT-TYPE
    SYNTAX  PPTNewCfgEntry
    MAX-ACCESS  not-accessible
    STATUS  current
    DESCRIPTION
        "A row in the prefix policy table"
    INDEX   { pptNewCfgIndx }
    ::= { pptNewCfgTable 1 }

PPTNewCfgEntry ::= SEQUENCE {
    pptNewCfgIndx         Integer32,
    pptNewCfgPrefix       DisplayString,
    pptNewCfgPrefixLen    Integer32,
    pptNewCfgPrecedence   Integer32,
    pptNewCfgLabel        Integer32,
    pptNewCfgAction       INTEGER
    }

pptNewCfgIndx OBJECT-TYPE
    SYNTAX  Integer32
    MAX-ACCESS  read-only
    STATUS  current
    DESCRIPTION
        "The index of the prefix policy table."
    ::= { pptNewCfgEntry 1}

pptNewCfgPrefix OBJECT-TYPE
    SYNTAX  DisplayString  (SIZE(0..40))
    MAX-ACCESS  read-create
    STATUS  current
    DESCRIPTION
        "The prefix address for the prefix policy table entry."
    ::= { pptNewCfgEntry 2}

pptNewCfgPrefixLen OBJECT-TYPE 
    SYNTAX  Integer32
    MAX-ACCESS  read-create 
    STATUS  current 
    DESCRIPTION 
        "The prefix length the prefix policy table entry."
    ::= { pptNewCfgEntry 3}

pptNewCfgPrecedence OBJECT-TYPE 
    SYNTAX  Integer32
    MAX-ACCESS  read-create 
    STATUS  current 
    DESCRIPTION 
        "The precedence for the prefix policy table entry."
    ::= { pptNewCfgEntry 4}

pptNewCfgLabel OBJECT-TYPE 
    SYNTAX  Integer32
    MAX-ACCESS  read-create 
    STATUS  current 
    DESCRIPTION 
        "The label for the prefix policy table entry."
    ::= { pptNewCfgEntry 5}

pptNewCfgAction OBJECT-TYPE
    SYNTAX  INTEGER {
        other(1),
        delete(2)
       }  
    MAX-ACCESS  read-create
    STATUS  current
    DESCRIPTION
        "When set to the value of 2 (delete), the entire row is deleted. 
         When read, other is returned. Setting the value to anything other 
         than 2(delete) has no effect on the state of the row."
    ::= { pptNewCfgEntry 6 }


mldCurCfgState OBJECT-TYPE
    SYNTAX INTEGER {
        on(1),
        off(2)
      }
    MAX-ACCESS read-only
    STATUS current
    DESCRIPTION    "MLD global state."
    ::= { mldCfg 1 }

mldNewCfgState OBJECT-TYPE
    SYNTAX INTEGER {
        on(1),
        off(2)
      }
    MAX-ACCESS read-write
    STATUS current
    DESCRIPTION    "MLD global state."
    ::= { mldCfg 2 }
    
mldCurInterfaceTable OBJECT-TYPE
    SYNTAX SEQUENCE OF MldCurInterfaceEntry
    MAX-ACCESS not-accessible
    STATUS current
    DESCRIPTION
      "The (conceptual) table listing the interfaces on which
         MLD is enabled."
    ::= { mldCfg 3 }
 
mldCurInterfaceEntry OBJECT-TYPE
    SYNTAX     MldCurInterfaceEntry
    MAX-ACCESS not-accessible
    STATUS     current
    DESCRIPTION
      "An entry (conceptual row) representing an interface on
         which MLD is enabled."
    INDEX      { mldCurInterfaceIfIndex }
    ::= { mldCurInterfaceTable 1 }

MldCurInterfaceEntry ::= SEQUENCE {
    mldCurInterfaceIfIndex                  Integer32,
    mldCurInterfaceQueryInterval            INTEGER,
    mldCurInterfaceVersion                  INTEGER,
    mldCurInterfaceQueryMaxResponseIntvl    INTEGER,
    mldCurInterfaceRobustness               INTEGER,
    mldCurInterfaceLastListenQueryIntvl  	INTEGER,
    mldCurInterfaceDMrtrEna                 INTEGER,
    mldCurInterfaceState                    INTEGER
}

mldCurInterfaceIfIndex OBJECT-TYPE
    SYNTAX     Integer32
    MAX-ACCESS read-only
    STATUS     current
    DESCRIPTION
      "The internetwork-layer interface value of the interface
       for which MLD is enabled."
    ::= { mldCurInterfaceEntry 1 }
       
mldCurInterfaceQueryInterval OBJECT-TYPE
    SYNTAX     INTEGER
    UNITS      "seconds"
    MAX-ACCESS read-only
    STATUS     current
    DESCRIPTION
      "The frequency at which MLD Host-Query packets are
       transmitted on this interface."
    DEFVAL     { 125 }
    ::= { mldCurInterfaceEntry 2 }

mldCurInterfaceVersion OBJECT-TYPE
    SYNTAX     INTEGER {
	mldv1(1),
	mldv2(2)
    }
    MAX-ACCESS read-only
    STATUS     current
    DESCRIPTION
      "The version of MLD which is running on this interface.
       This object is a place holder to allow for new versions
       of MLD to be introduced.  Version 1 of MLD is defined
       in RFC 2710."
    DEFVAL     { 1 }
    ::= { mldCurInterfaceEntry 3 }

mldCurInterfaceQueryMaxResponseIntvl OBJECT-TYPE
    SYNTAX     INTEGER
    UNITS      "seconds"
    MAX-ACCESS read-only
    STATUS     current
    DESCRIPTION
      "The maximum query response time advertised in MLD
       queries on this interface."
    DEFVAL     { 1000 }
    ::= { mldCurInterfaceEntry 4 }

mldCurInterfaceRobustness OBJECT-TYPE
    SYNTAX     INTEGER
    MAX-ACCESS read-only
    STATUS     current
    DESCRIPTION
      "The Robustness Variable allows tuning for the expected
       packet loss on a subnet.  If a subnet is expected to be
       lossy, the Robustness Variable may be increased.  MLD is
       robust to (Robustness Variable-1) packet losses.  The
       discussion of the Robustness Variable is in Section 7.1
       of RFC 2710."
    DEFVAL     { 2 }
    ::= { mldCurInterfaceEntry 5 }

mldCurInterfaceLastListenQueryIntvl OBJECT-TYPE
    SYNTAX     INTEGER
    UNITS      "seconds"
    MAX-ACCESS read-only
    STATUS     current
    DESCRIPTION
      "The Last Member Query Interval is the Max Response
       Delay inserted into Group-Specific Queries sent in
       response to Leave Group messages, and is also the amount
       of time between Group-Specific Query messages.  This
       value may be tuned to modify the leave latency of the
       network.  A reduced value results in reduced time to
       detect the loss of the last member of a group."
    DEFVAL     { 1 }
    ::= { mldCurInterfaceEntry 6 }

mldCurInterfaceDMrtrEna OBJECT-TYPE
    SYNTAX     INTEGER {
	disabled(0),
	enabled(1)
    }
    MAX-ACCESS read-only
    STATUS     current
    DESCRIPTION
      "Dynamic MRouter learning."
    DEFVAL	{ 0 }
    ::= { mldCurInterfaceEntry 7 }

mldCurInterfaceState OBJECT-TYPE
    SYNTAX     INTEGER {
	disabled(0),
	enabled(1)
    }
    MAX-ACCESS read-only
    STATUS     current
    DESCRIPTION
      "State of the MLD interface."
    DEFVAL	{ 0 }
    ::= { mldCurInterfaceEntry 8 }

mldNewInterfaceTable OBJECT-TYPE
    SYNTAX SEQUENCE OF MldNewInterfaceEntry
    MAX-ACCESS not-accessible
    STATUS current
    DESCRIPTION
      "The (conceptual) table listing the interfaces on which
      MLD is enabled."
    ::= { mldCfg 4 }
 
mldNewInterfaceEntry OBJECT-TYPE
    SYNTAX     MldNewInterfaceEntry
    MAX-ACCESS not-accessible
    STATUS     current
    DESCRIPTION
      "An entry (conceptual row) representing an interface on
         which MLD is enabled."
    INDEX      { mldNewInterfaceIfIndex }
    ::= { mldNewInterfaceTable 1 }

MldNewInterfaceEntry ::= SEQUENCE {
    mldNewInterfaceIfIndex                  Integer32,
    mldNewInterfaceQueryInterval            INTEGER,
    mldNewInterfaceVersion                  INTEGER,
    mldNewInterfaceQueryMaxResponseIntvl    INTEGER,
    mldNewInterfaceRobustness               INTEGER,
    mldNewInterfaceLastListenQueryIntvl  	INTEGER,
    mldNewInterfaceDMrtrEna                 INTEGER,
    mldNewInterfaceState                    INTEGER,
    mldNewInterfaceDefault                  INTEGER
}

mldNewInterfaceIfIndex OBJECT-TYPE
    SYNTAX     Integer32
    MAX-ACCESS read-only
    STATUS     current
    DESCRIPTION
      "The internetwork-layer interface value of the interface
       for which MLD is enabled."
    ::= { mldNewInterfaceEntry 1 }
       
mldNewInterfaceQueryInterval OBJECT-TYPE
    SYNTAX     INTEGER(2..65535)
    UNITS      "seconds"
    MAX-ACCESS read-write
    STATUS     current
    DESCRIPTION
      "The frequency at which MLD Host-Query packets are
       transmitted on this interface."
    DEFVAL     { 125 }
    ::= { mldNewInterfaceEntry 2 }

mldNewInterfaceVersion OBJECT-TYPE
    SYNTAX     INTEGER {
	mldv1(1),
	mldv2(2)
    }
    MAX-ACCESS read-write
    STATUS     current
    DESCRIPTION
      "The version of MLD which is running on this interface.
       This object is a place holder to allow for new versions
       of MLD to be introduced.  Version 1 of MLD is defined
       in RFC 2710."
    DEFVAL     { 1 }
    ::= { mldNewInterfaceEntry 3 }

mldNewInterfaceQueryMaxResponseIntvl OBJECT-TYPE
    SYNTAX     INTEGER(1000..65535)
    UNITS      "seconds"
    MAX-ACCESS read-write
    STATUS     current
    DESCRIPTION
      "The maximum query response time advertised in MLD
       queries on this interface."
    DEFVAL     { 10000 }
    ::= { mldNewInterfaceEntry 4 }

mldNewInterfaceRobustness OBJECT-TYPE
    SYNTAX     INTEGER(1..10)
    MAX-ACCESS read-write
    STATUS     current
    DESCRIPTION
      "The Robustness Variable allows tuning for the expected
       packet loss on a subnet.  If a subnet is expected to be
       lossy, the Robustness Variable may be increased.  MLD is
       robust to (Robustness Variable-1) packet losses.  The
       discussion of the Robustness Variable is in Section 7.1
       of RFC 2710."
    DEFVAL     { 2 }
    ::= { mldNewInterfaceEntry 5 }

mldNewInterfaceLastListenQueryIntvl OBJECT-TYPE
    SYNTAX     INTEGER(1..32)
    UNITS      "seconds"
    MAX-ACCESS read-write
    STATUS     current
    DESCRIPTION
      "The Last Member Query Interval is the Max Response
       Delay inserted into Group-Specific Queries sent in
       response to Leave Group messages, and is also the amount
       of time between Group-Specific Query messages.  This
       value may be tuned to modify the leave latency of the
       network.  A reduced value results in reduced time to
       detect the loss of the last member of a group."
    DEFVAL     { 1 }
    ::= { mldNewInterfaceEntry 6 }

mldNewInterfaceDMrtrEna OBJECT-TYPE
    SYNTAX     INTEGER {
        disabled(0),
        enabled(1)
    }
    MAX-ACCESS read-write
    STATUS     current
    DESCRIPTION
      "Dynamic MRouter learning."
    DEFVAL	{ 0 }
    ::= { mldNewInterfaceEntry 7 }

mldNewInterfaceState OBJECT-TYPE
    SYNTAX     INTEGER {
        disabled(0),
        enabled(1)
    }
    MAX-ACCESS read-write
    STATUS     current
    DESCRIPTION
      "State of the MLD interface."
    DEFVAL	{ 0 }
    ::= { mldNewInterfaceEntry 8 }

mldNewInterfaceDefault OBJECT-TYPE
    SYNTAX     INTEGER {
        other(1),
        default(2)
    }
    MAX-ACCESS read-write
    STATUS     current
    DESCRIPTION
      "Action to set the MLD interface configuration to default.
       Returns other(1) when read."
    ::= { mldNewInterfaceEntry 9 }

mldDefaultCfgState OBJECT-TYPE
    SYNTAX INTEGER {
        other(1),
        default(2)
      }
    MAX-ACCESS read-write
    STATUS current
    DESCRIPTION    "Action to set the global MLD configuration to default.
                    Returns other(1) when read."
    ::= { mldCfg 5 }
                                                                                

--
-- Neighbor Discovery Prefix Configuration
--
ndprefixTableMaxSize OBJECT-TYPE
    SYNTAX  Integer32
    MAX-ACCESS  read-only
    STATUS  current
    DESCRIPTION
        "The maximum number of rows in the NDPrefix table."
    ::= { ndprefixCfg 1 }

ndprefixCurCfgTable OBJECT-TYPE
    SYNTAX  SEQUENCE OF NDPREFIXCurCfgEntry
    MAX-ACCESS  not-accessible
    STATUS  current
    DESCRIPTION
        "The ndprefix table entries in the current configuration block."
    ::= { ndprefixCfg 2 }

ndprefixCurCfgEntry OBJECT-TYPE
    SYNTAX  NDPREFIXCurCfgEntry
    MAX-ACCESS  not-accessible
    STATUS  current
    DESCRIPTION
        "A row in the ndprefix table."
    INDEX   { ndprefixCurCfgIndx }
    ::= { ndprefixCurCfgTable 1 }

NDPREFIXCurCfgEntry ::= SEQUENCE {
    ndprefixCurCfgIndx                  INTEGER,
    ndprefixCurCfgPrefix                DisplayString,
    ndprefixCurCfgPrefixLen             INTEGER,
    ndprefixCurCfgInterfaceIndex        Integer32,
    ndprefixCurCfgProfileIndex          INTEGER,
    ndprefixCurCfgValidLifetime         Gauge32,
    ndprefixCurCfgValidLifetimeFlag     INTEGER,
    ndprefixCurCfgPreferredLifetime     Gauge32,
    ndprefixCurCfgPreferredLifetimeFlag INTEGER,
    ndprefixCurCfgOnlinkFlag            INTEGER,
    ndprefixCurCfgAutonomousFlag        INTEGER,
    ndprefixCurCfgState                 INTEGER
    }

ndprefixCurCfgIndx OBJECT-TYPE
    SYNTAX  INTEGER (1..128)
    MAX-ACCESS  read-only
    STATUS  current
    DESCRIPTION
        "The index of the ndprefix table."
    ::= { ndprefixCurCfgEntry 1}

ndprefixCurCfgPrefix OBJECT-TYPE
    SYNTAX  DisplayString 
    MAX-ACCESS  read-only
    STATUS  current
    DESCRIPTION
        "The prefix address for the prefix table entry."
    ::= { ndprefixCurCfgEntry 2}

ndprefixCurCfgPrefixLen OBJECT-TYPE 
    SYNTAX  INTEGER (0..128)
    MAX-ACCESS  read-only 
    STATUS  current 
    DESCRIPTION 
        "The prefix length for the prefix table entry."
    ::= { ndprefixCurCfgEntry 3}

ndprefixCurCfgInterfaceIndex OBJECT-TYPE
    SYNTAX  Integer32
    MAX-ACCESS  read-only
    STATUS  current
    DESCRIPTION
        "The interface index for the prefix table entry."
    ::= { ndprefixCurCfgEntry 4}

ndprefixCurCfgProfileIndex OBJECT-TYPE
    SYNTAX  INTEGER (0..127)
    MAX-ACCESS  read-only
    STATUS  current
    DESCRIPTION
        "The profile index for the prefix table entry
         Profile 0 is the default profile."
    ::= { ndprefixCurCfgEntry 5}

ndprefixCurCfgValidLifetime OBJECT-TYPE
    SYNTAX  Gauge32 (0..4294967295)
    MAX-ACCESS  read-only
    STATUS  current
    DESCRIPTION
        "The Valid lifetime for the prefix table entry."
    ::= { ndprefixCurCfgEntry 6}

ndprefixCurCfgValidLifetimeFlag OBJECT-TYPE
    SYNTAX  INTEGER {
        enabled(1),
        disabled(2)
    }
    MAX-ACCESS  read-only
    STATUS  current
    DESCRIPTION
        "The Valid lifetime fixed flag for the prefix table entry."
    ::= { ndprefixCurCfgEntry 7}

ndprefixCurCfgPreferredLifetime OBJECT-TYPE
    SYNTAX  Gauge32 (0..4294967295)
    MAX-ACCESS  read-only
    STATUS  current
    DESCRIPTION
        "The Preferred Lifetime for the prefix table entry."
    ::= { ndprefixCurCfgEntry 8}

ndprefixCurCfgPreferredLifetimeFlag OBJECT-TYPE
    SYNTAX  INTEGER {
        enabled(1),
        disabled(2)
    }
    MAX-ACCESS  read-only
    STATUS  current
    DESCRIPTION
        "The Preferred Lifetime fixed flag for the prefix table entry."
    ::= { ndprefixCurCfgEntry 9}

ndprefixCurCfgOnlinkFlag OBJECT-TYPE
    SYNTAX  INTEGER {
        enabled(1),
        disabled(2)
    }
    MAX-ACCESS  read-only
    STATUS  current
    DESCRIPTION
        "The Onlink flag for the prefix table entry."
    ::= { ndprefixCurCfgEntry 10}

ndprefixCurCfgAutonomousFlag OBJECT-TYPE
    SYNTAX  INTEGER {
        enabled(1),
        disabled(2)
    }
    MAX-ACCESS  read-only
    STATUS  current
    DESCRIPTION
        "The Autonomous flag for the prefix table entry."
    ::= { ndprefixCurCfgEntry 11}

ndprefixCurCfgState OBJECT-TYPE
    SYNTAX  INTEGER {
        enabled(1),
        disabled(2)
    }
    MAX-ACCESS  read-only
    STATUS  current
    DESCRIPTION
        "The state for the prefix table entry."
    ::= { ndprefixCurCfgEntry 12}

ndprefixNewCfgTable OBJECT-TYPE
    SYNTAX  SEQUENCE OF NDPREFIXNewCfgEntry
    MAX-ACCESS  not-accessible
    STATUS  current
    DESCRIPTION
        "The ndprefix table entries in the new configuration block."
    ::= { ndprefixCfg 3 }

ndprefixNewCfgEntry OBJECT-TYPE
    SYNTAX  NDPREFIXNewCfgEntry
    MAX-ACCESS  not-accessible
    STATUS  current
    DESCRIPTION
        "A row in the prefix table"
    INDEX   { ndprefixNewCfgIndx }
    ::= { ndprefixNewCfgTable 1 }

NDPREFIXNewCfgEntry ::= SEQUENCE {
    ndprefixNewCfgIndx                  Integer32,
    ndprefixNewCfgPrefix                DisplayString,
    ndprefixNewCfgPrefixLen             INTEGER,
    ndprefixNewCfgInterfaceIndex        Integer32,
    ndprefixNewCfgProfileIndex          INTEGER,
    ndprefixNewCfgValidLifetime         Gauge32,
    ndprefixNewCfgValidLifetimeFlag     INTEGER,
    ndprefixNewCfgPreferredLifetime     Gauge32,
    ndprefixNewCfgPreferredLifetimeFlag INTEGER,
    ndprefixNewCfgOnlinkFlag            INTEGER,
    ndprefixNewCfgAutonomousFlag        INTEGER,
    ndprefixNewCfgState                 INTEGER,
    ndprefixNewCfgAction                INTEGER
    }

ndprefixNewCfgIndx OBJECT-TYPE
    SYNTAX  Integer32
    MAX-ACCESS  read-only
    STATUS  current
    DESCRIPTION
        "The index of the prefix table."
    ::= { ndprefixNewCfgEntry 1}

ndprefixNewCfgPrefix OBJECT-TYPE
    SYNTAX  DisplayString
    MAX-ACCESS  read-create
    STATUS  current
    DESCRIPTION
        "The prefix address for the prefix table entry."
    ::= { ndprefixNewCfgEntry 2}

ndprefixNewCfgPrefixLen OBJECT-TYPE
    SYNTAX  INTEGER (0..128)
    MAX-ACCESS  read-create
    STATUS  current
    DESCRIPTION
        "The prefix length for the prefix table entry."
    ::= { ndprefixNewCfgEntry 3}

ndprefixNewCfgInterfaceIndex OBJECT-TYPE
    SYNTAX  Integer32
    MAX-ACCESS  read-create
    STATUS  current
    DESCRIPTION
        "The interface index for the prefix table entry."
    ::= { ndprefixNewCfgEntry 4}

ndprefixNewCfgProfileIndex OBJECT-TYPE
    SYNTAX  INTEGER (0..127)
    MAX-ACCESS  read-create
    STATUS  current
    DESCRIPTION
        "The profile index for the prefix table entry.
         Profile 0 is the default profile."
    ::= { ndprefixNewCfgEntry 5}

ndprefixNewCfgValidLifetime OBJECT-TYPE
    SYNTAX  Gauge32 (0..4294967295)
    MAX-ACCESS  read-create
    STATUS  current
    DESCRIPTION
        "The Valid lifetime for the prefix table entry."
    ::= { ndprefixNewCfgEntry 6}

ndprefixNewCfgValidLifetimeFlag OBJECT-TYPE
    SYNTAX  INTEGER {
        enabled(1),
        disabled(2)
    }
    MAX-ACCESS  read-create
    STATUS  current
    DESCRIPTION
        "The Valid lifetime fixed flag for the prefix table entry."
    ::= { ndprefixNewCfgEntry 7}

ndprefixNewCfgPreferredLifetime OBJECT-TYPE
    SYNTAX  Gauge32 (0..4294967295)
    MAX-ACCESS  read-create
    STATUS  current
    DESCRIPTION
        "The Preferred Lifetime for the prefix table entry."
    ::= { ndprefixNewCfgEntry 8}

ndprefixNewCfgPreferredLifetimeFlag OBJECT-TYPE
    SYNTAX  INTEGER {
        enabled(1),
        disabled(2)
    }
    MAX-ACCESS  read-create
    STATUS  current
    DESCRIPTION
        "The Preferred Lifetime fixed flag for the prefix table entry."
    ::= { ndprefixNewCfgEntry 9}

ndprefixNewCfgOnlinkFlag OBJECT-TYPE
    SYNTAX  INTEGER {
        enabled(1),
        disabled(2)
    }
    MAX-ACCESS  read-create
    STATUS  current
    DESCRIPTION
        "The Onlink flag for the prefix table entry."
    ::= { ndprefixNewCfgEntry 10}

ndprefixNewCfgAutonomousFlag OBJECT-TYPE
    SYNTAX  INTEGER {
        enabled(1),
        disabled(2)
    }
    MAX-ACCESS  read-create
    STATUS  current
    DESCRIPTION
        "The Autonomous flag for the prefix table entry."
    ::= { ndprefixNewCfgEntry 11}

ndprefixNewCfgState OBJECT-TYPE
    SYNTAX  INTEGER {
        enabled(1),
        disabled(2)
    }
    MAX-ACCESS  read-create
    STATUS  current
    DESCRIPTION
        "The state for the prefix table entry."
    ::= { ndprefixNewCfgEntry 12}

ndprefixNewCfgAction OBJECT-TYPE
    SYNTAX  INTEGER {
        other(1),
        delete(2),
        deleteall(3)
    }  
    MAX-ACCESS  read-create
    STATUS  current
    DESCRIPTION
        "When set to the value of 2 (delete), the entire row is deleted. 
         When set to the value of 3 (deleteall), all entries are deleted.
         When read, other is returned. Setting the value to anything other 
         than 2(delete) or 3(deleteall) has no effect on the state of the row."
    ::= { ndprefixNewCfgEntry 13}



-- Statistics


-- RIPv2 Statistics

ripStatInPackets OBJECT-TYPE
    SYNTAX  Counter32
    MAX-ACCESS  read-only
    STATUS  current
    DESCRIPTION
        "The total number of RIP packets received."
    ::= { rip2Stats 1 }

ripStatOutPackets OBJECT-TYPE
    SYNTAX  Counter32
    MAX-ACCESS  read-only
    STATUS  current
    DESCRIPTION
        "The total number of RIP packets transmitted."
    ::= { rip2Stats 2 }

ripStatInRequestPkts OBJECT-TYPE
    SYNTAX  Counter32
    MAX-ACCESS  read-only
    STATUS  current
    DESCRIPTION
        "The total number of RIP requests received."
    ::= { rip2Stats 3 }

ripStatInResponsePkts OBJECT-TYPE
    SYNTAX  Counter32
    MAX-ACCESS  read-only
    STATUS  current
    DESCRIPTION
        "The total number of RIP response received."
    ::= { rip2Stats 4 }

ripStatOutRequestPkts OBJECT-TYPE
    SYNTAX  Counter32
    MAX-ACCESS  read-only
    STATUS  current
    DESCRIPTION
        "The total number of RIP requests transmitted."
    ::= { rip2Stats 5 }

ripStatOutResponsePkts OBJECT-TYPE
    SYNTAX  Counter32
    MAX-ACCESS  read-only
    STATUS  current
    DESCRIPTION
        "The total number of RIP responses transmitted."
    ::= { rip2Stats 6 }

ripStatRouteTimeout OBJECT-TYPE
    SYNTAX  Counter32
    MAX-ACCESS  read-only
    STATUS  current
    DESCRIPTION
        "The total number of RIP route timeouts."
    ::= { rip2Stats 7 }

ripStatInBadSizePkts OBJECT-TYPE
    SYNTAX  Counter32
    MAX-ACCESS  read-only
    STATUS  current
    DESCRIPTION
        "The total number of bad size RIP packets received."
    ::= { rip2Stats 8 }

ripStatInBadVersion OBJECT-TYPE
    SYNTAX  Counter32
    MAX-ACCESS  read-only
    STATUS  current
    DESCRIPTION
        "The total number of RIP bad versions received."
    ::= { rip2Stats 9 }

ripStatInBadZeros OBJECT-TYPE
    SYNTAX  Counter32
    MAX-ACCESS  read-only
    STATUS  current
    DESCRIPTION
        "The total number of RIP bad zeros received."
    ::= { rip2Stats 10 }

ripStatInBadSourcePort OBJECT-TYPE
    SYNTAX  Counter32
    MAX-ACCESS  read-only
    STATUS  current
    DESCRIPTION
        "The total number of RIP bad source port received."
    ::= { rip2Stats 11 }

ripStatInBadSourceIP OBJECT-TYPE
    SYNTAX  Counter32
    MAX-ACCESS  read-only
    STATUS  current
    DESCRIPTION
        "The total number of RIP bad source IP received."
    ::= { rip2Stats 12 }

ripStatInSelfRcvPkts OBJECT-TYPE
    SYNTAX  Counter32
    MAX-ACCESS  read-only
    STATUS  current
    DESCRIPTION
        "The total number of RIP packets from self received."
    ::= { rip2Stats 13 }




-- IP statistics

ipStatsInReceives OBJECT-TYPE
    SYNTAX         Counter32
    MAX-ACCESS     read-only
    STATUS         current
    DESCRIPTION
        "ip InReceive"
    ::= { ipStats 1 }

ipStatsInHdrErrors OBJECT-TYPE
    SYNTAX          Counter32
    MAX-ACCESS      read-only
    STATUS          current
    DESCRIPTION
        "ip InHdrError"
    ::= { ipStats 2 }

ipStatsInAddrErrors OBJECT-TYPE
    SYNTAX          Counter32
    MAX-ACCESS      read-only
    STATUS          current
    DESCRIPTION
        "ip InAddrErrors"
    ::= { ipStats 3 }



ipStatsInUnknownProtos OBJECT-TYPE
    SYNTAX          Counter32
    MAX-ACCESS      read-only
    STATUS          current
    DESCRIPTION
        "ip InUnknownProtos"
    ::= { ipStats 5 }

ipStatsInDiscards OBJECT-TYPE
    SYNTAX          Counter32
    MAX-ACCESS      read-only
    STATUS          current
    DESCRIPTION
        "ip InDiscards"
    ::= { ipStats 6 }

ipStatsInDelivers OBJECT-TYPE
    SYNTAX          Counter32
    MAX-ACCESS      read-only
    STATUS          current
    DESCRIPTION
        "ip InDelivers"
    ::= { ipStats 7 }

ipStatsOutRequests OBJECT-TYPE
    SYNTAX          Counter32
    MAX-ACCESS      read-only
    STATUS          current
    DESCRIPTION
        "ip OutRequests"
    ::= { ipStats 8 }

ipStatsOutDiscards OBJECT-TYPE
    SYNTAX          Counter32
    MAX-ACCESS      read-only
    STATUS          current
    DESCRIPTION
        "ip OutDiscards"
    ::= { ipStats 9 }


ipStatsDefaultTTL OBJECT-TYPE
    SYNTAX          Counter32
    MAX-ACCESS      read-only
    STATUS          current
    DESCRIPTION
        "ip DefaultTTL"
    ::= { ipStats 19 }


--SNMP statistics

nsnmpInPkts OBJECT-TYPE
    SYNTAX         Counter32
    MAX-ACCESS     read-only
    STATUS         current
    DESCRIPTION
        "snmpInPkts"
    ::= { snmpStats 1 }

nsnmpInBadCommunityNames OBJECT-TYPE
    SYNTAX         Counter32
    MAX-ACCESS     read-only
    STATUS         current
    DESCRIPTION
        "snmpInBadCommunityNames"
    ::= { snmpStats 2 }

nsnmpInASNParseErrs OBJECT-TYPE
    SYNTAX         Counter32
    MAX-ACCESS     read-only
    STATUS         current
    DESCRIPTION
        "snmpInASNParseErrs"
    ::= { snmpStats 3 }

nsnmpOutPkts OBJECT-TYPE
    SYNTAX         Counter32
    MAX-ACCESS     read-only
    STATUS         current
    DESCRIPTION
        "snmpOutPkts"
    ::= { snmpStats 4 }

nsnmpInTooBigs OBJECT-TYPE
    SYNTAX         Counter32
    MAX-ACCESS     read-only
    STATUS         current
    DESCRIPTION
        "snmpInTooBigs"
    ::= { snmpStats 5 }

nsnmpInBadValues OBJECT-TYPE
    SYNTAX         Counter32
    MAX-ACCESS     read-only
    STATUS         current
    DESCRIPTION
        "snmpInBadValues"
    ::= { snmpStats 6 }

nsnmpInGenErrs OBJECT-TYPE
    SYNTAX         Counter32
    MAX-ACCESS     read-only
    STATUS         current
    DESCRIPTION
        "snmpInGenErrs"
    ::= { snmpStats 7 }

nsnmpInTotalSetVars OBJECT-TYPE
    SYNTAX         Counter32
    MAX-ACCESS     read-only
    STATUS         current
    DESCRIPTION
        "snmpInTotalSetVars"
    ::= { snmpStats 8 }

nsnmpInGetNexts OBJECT-TYPE
    SYNTAX         Counter32
    MAX-ACCESS     read-only
    STATUS         current
    DESCRIPTION
        "snmpInGetNexts"
    ::= { snmpStats 9 }

nsnmpInGetResponses OBJECT-TYPE
    SYNTAX         Counter32
    MAX-ACCESS     read-only
    STATUS         current
    DESCRIPTION
        "snmpInGetResponses"
    ::= { snmpStats 10 }

nsnmpOutTooBigs OBJECT-TYPE
    SYNTAX         Counter32
    MAX-ACCESS     read-only
    STATUS         current
    DESCRIPTION
        "snmpOutTooBigs"
    ::= { snmpStats 11 }

nsnmpOutBadValues OBJECT-TYPE
    SYNTAX         Counter32
    MAX-ACCESS     read-only
    STATUS         current
    DESCRIPTION
        "snmpOutBadValues"
    ::= { snmpStats 12 }

nsnmpOutGenErrs OBJECT-TYPE
    SYNTAX         Counter32
    MAX-ACCESS     read-only
    STATUS         current
    DESCRIPTION
        "snmpOutGenErrs"
    ::= { snmpStats 13 }

nsnmpOutGetNexts OBJECT-TYPE
    SYNTAX         Counter32
    MAX-ACCESS     read-only
    STATUS         current
    DESCRIPTION
        "snmpOutGetNexts"
    ::= { snmpStats 14 }

nsnmpOutGetResponses OBJECT-TYPE
    SYNTAX         Counter32
    MAX-ACCESS     read-only
    STATUS         current
    DESCRIPTION
        "snmpOutGetResponses"
    ::= { snmpStats 15 }

nsnmpSilentDrops OBJECT-TYPE
    SYNTAX         Counter32
    MAX-ACCESS     read-only
    STATUS         current
    DESCRIPTION
        "snmpSilentDrops"
    ::= { snmpStats 16 }

nsnmpInBadVersions OBJECT-TYPE
    SYNTAX         Counter32
    MAX-ACCESS     read-only
    STATUS         current
    DESCRIPTION
        "snmpInBadVersions"
    ::= { snmpStats 17 }

nsnmpInBadCommunityUses OBJECT-TYPE
    SYNTAX         Counter32
    MAX-ACCESS     read-only
    STATUS         current
    DESCRIPTION
        "snmpInBadCommunityUses"
    ::= { snmpStats 18 }

nsnmpEnableAuthTraps OBJECT-TYPE
    SYNTAX         Counter32
    MAX-ACCESS     read-only
    STATUS         current
    DESCRIPTION
        "snmpEnableAuthTraps"
    ::= { snmpStats 19 }

nsnmpInBadTypes OBJECT-TYPE
    SYNTAX         Counter32
    MAX-ACCESS     read-only
    STATUS         current
    DESCRIPTION
        "snmpInBadTypes"
    ::= { snmpStats 20 }

nsnmpInNoSuchNames OBJECT-TYPE
    SYNTAX         Counter32
    MAX-ACCESS     read-only
    STATUS         current
    DESCRIPTION
        "snmpInNoSuchNames"
    ::= { snmpStats 21 }

nsnmpInReadOnlys OBJECT-TYPE
    SYNTAX         Counter32
    MAX-ACCESS     read-only
    STATUS         current
    DESCRIPTION
        "snmpInReadOnlys"
    ::= { snmpStats 22 }

nsnmpInTotalReqVars OBJECT-TYPE
    SYNTAX         Counter32
    MAX-ACCESS     read-only
    STATUS         current
    DESCRIPTION
        "snmpInTotalReqVars"
    ::= { snmpStats 23 }

nsnmpInGetRequests OBJECT-TYPE
    SYNTAX         Counter32
    MAX-ACCESS     read-only
    STATUS         current
    DESCRIPTION
        "snmpInGetRequests"
    ::= { snmpStats 24 }

nsnmpInSetRequests OBJECT-TYPE
    SYNTAX         Counter32
    MAX-ACCESS     read-only
    STATUS         current
    DESCRIPTION
        "snmpInSetRequests"
    ::= { snmpStats 25 }

nsnmpInTraps OBJECT-TYPE
    SYNTAX         Counter32
    MAX-ACCESS     read-only
    STATUS         current
    DESCRIPTION
        "snmpInTraps"
    ::= { snmpStats 26 }

nsnmpOutNoSuchNames OBJECT-TYPE
    SYNTAX         Counter32
    MAX-ACCESS     read-only
    STATUS         current
    DESCRIPTION
        "snmpOutNoSuchNames"
    ::= { snmpStats 27 }

nsnmpOutReadOnlys OBJECT-TYPE
    SYNTAX         Counter32
    MAX-ACCESS     read-only
    STATUS         current
    DESCRIPTION
        "snmpOutReadOnlys"
    ::= { snmpStats 28 }

nsnmpOutGetRequests OBJECT-TYPE
    SYNTAX         Counter32
    MAX-ACCESS     read-only
    STATUS         current
    DESCRIPTION
        "snmpOutGetRequests"
    ::= { snmpStats 29 }

nsnmpOutSetRequests OBJECT-TYPE
    SYNTAX         Counter32
    MAX-ACCESS     read-only
    STATUS         current
    DESCRIPTION
        "snmpOutSetRequests"
    ::= { snmpStats 30 }

nsnmpOutTraps OBJECT-TYPE
    SYNTAX         Counter32
    MAX-ACCESS     read-only
    STATUS         current
    DESCRIPTION
        "snmpOutTraps"
    ::= { snmpStats 31 }

nsnmpProxyDrops OBJECT-TYPE
    SYNTAX         Counter32
    MAX-ACCESS     read-only
    STATUS         current
    DESCRIPTION
        "snmpProxyDrops"
    ::= { snmpStats 32 }


-- ICMP statistics

icmpStatsInMsgs OBJECT-TYPE
    SYNTAX         Counter32
    MAX-ACCESS     read-only
    STATUS         current
    DESCRIPTION
        "icmp InMsgs"
    ::= { icmpStats 1 }

icmpStatsInErrors OBJECT-TYPE
    SYNTAX         Counter32
    MAX-ACCESS     read-only
    STATUS         current
    DESCRIPTION
        "icmp InErrors"
    ::= { icmpStats 2 }

icmpStatsInDestUnreachs OBJECT-TYPE
    SYNTAX         Counter32
    MAX-ACCESS     read-only
    STATUS         current
    DESCRIPTION
        "icmp InDestUnreachs"
    ::= { icmpStats 3 }

icmpStatsInTimeExcds OBJECT-TYPE
    SYNTAX         Counter32
    MAX-ACCESS     read-only
    STATUS         current
    DESCRIPTION
        "icmp InTimeExcds"
    ::= { icmpStats 4 }

icmpStatsInParmProbs OBJECT-TYPE
    SYNTAX         Counter32
    MAX-ACCESS     read-only
    STATUS         current
    DESCRIPTION
        "icmp InParmProbs"
    ::= { icmpStats 5 }

icmpStatsInSrcQuenchs OBJECT-TYPE
    SYNTAX         Counter32
    MAX-ACCESS     read-only
    STATUS         current
    DESCRIPTION
        "icmp InSrcQuenchs"
    ::= { icmpStats 6 }

icmpStatsInRedirects OBJECT-TYPE
    SYNTAX         Counter32
    MAX-ACCESS     read-only
    STATUS         current
    DESCRIPTION
        "icmp InRedirects"
    ::= { icmpStats 7 }

icmpStatsInEchos OBJECT-TYPE
    SYNTAX         Counter32
    MAX-ACCESS     read-only
    STATUS         current
    DESCRIPTION
        "icmp InEchos"
    ::= { icmpStats 8 }

icmpStatsInEchoReps OBJECT-TYPE
    SYNTAX         Counter32
    MAX-ACCESS     read-only
    STATUS         current
    DESCRIPTION
        "icmp InEchoReps"
    ::= { icmpStats 9 }

icmpStatsInTimestamps OBJECT-TYPE
    SYNTAX         Counter32
    MAX-ACCESS     read-only
    STATUS         current
    DESCRIPTION
        "icmp InTimestamps"
    ::= { icmpStats 10 }

icmpStatsInTimestampReps OBJECT-TYPE
    SYNTAX         Counter32
    MAX-ACCESS     read-only
    STATUS         current
    DESCRIPTION
        "icmp InTimestampReps"
    ::= { icmpStats 11 }

icmpStatsInAddrMasks OBJECT-TYPE
    SYNTAX         Counter32
    MAX-ACCESS     read-only
    STATUS         current
    DESCRIPTION
        "icmp InAddrMasks"
    ::= { icmpStats 12 }

icmpStatsInAddrMaskReps OBJECT-TYPE
    SYNTAX         Counter32
    MAX-ACCESS     read-only
    STATUS         current
    DESCRIPTION
        "icmp InAddrMaskReps"
    ::= { icmpStats 13 }

icmpStatsOutMsgs OBJECT-TYPE
    SYNTAX         Counter32
    MAX-ACCESS     read-only
    STATUS         current
    DESCRIPTION
        "icmp OutMsgs"
    ::= { icmpStats 14 }

icmpStatsOutErrors OBJECT-TYPE
    SYNTAX         Counter32
    MAX-ACCESS     read-only
    STATUS         current
    DESCRIPTION
        "icmp OutErrors"
    ::= { icmpStats 15 }

icmpStatsOutDestUnreachs OBJECT-TYPE
    SYNTAX         Counter32
    MAX-ACCESS     read-only
    STATUS         current
    DESCRIPTION
        "icmp OutDestUnreachs"
    ::= { icmpStats 16 }

icmpStatsOutTimeExcds OBJECT-TYPE
    SYNTAX         Counter32
    MAX-ACCESS     read-only
    STATUS         current
    DESCRIPTION
        "icmp OutTimeExcds"
    ::= { icmpStats 17 }

icmpStatsOutParmProbs OBJECT-TYPE
    SYNTAX         Counter32
    MAX-ACCESS     read-only
    STATUS         current
    DESCRIPTION
        "icmp OutParmProbs"
    ::= { icmpStats 18 }

icmpStatsOutSrcQuenchs OBJECT-TYPE
    SYNTAX         Counter32
    MAX-ACCESS     read-only
    STATUS         current
    DESCRIPTION
        "icmp OutSrcQuenchs"
    ::= { icmpStats 19 }

icmpStatsOutRedirects OBJECT-TYPE
    SYNTAX         Counter32
    MAX-ACCESS     read-only
    STATUS         current
    DESCRIPTION
        "icmp OutRedirects"
    ::= { icmpStats 20 }

icmpStatsOutEchos OBJECT-TYPE
    SYNTAX         Counter32
    MAX-ACCESS     read-only
    STATUS         current
    DESCRIPTION
        "icmp OutEchos"
    ::= { icmpStats 21 }

icmpStatsOutEchoReps OBJECT-TYPE
    SYNTAX         Counter32
    MAX-ACCESS     read-only
    STATUS         current
    DESCRIPTION
        "icmp OutEchoReps"
    ::= { icmpStats 22 }

icmpStatsOutTimestamps OBJECT-TYPE
    SYNTAX         Counter32
    MAX-ACCESS     read-only
    STATUS         current
    DESCRIPTION
        "icmp OutTimestamps"
    ::= { icmpStats 23 }

icmpStatsOutTimestampReps OBJECT-TYPE
    SYNTAX         Counter32
    MAX-ACCESS     read-only
    STATUS         current
    DESCRIPTION
        "icmp OutTimestampReps"
    ::= { icmpStats 24 }

icmpStatsOutAddrMasks OBJECT-TYPE
    SYNTAX         Counter32
    MAX-ACCESS     read-only
    STATUS         current
    DESCRIPTION
        "icmp OutAddrMasks"
    ::= { icmpStats 25 }

icmpStatsOutAddrMaskReps OBJECT-TYPE
    SYNTAX         Counter32
    MAX-ACCESS     read-only
    STATUS         current
    DESCRIPTION
        "icmp OutAddrMaskReps"
    ::= { icmpStats 26 }

-- TCP statistics

tcpStatsRtoAlgorithm OBJECT-TYPE
    SYNTAX         Counter32
    MAX-ACCESS     read-only
    STATUS         current
    DESCRIPTION
        "tcp RtoAlgorithm"
    ::= { tcpStats 1 }

tcpStatsRtoMin OBJECT-TYPE
    SYNTAX         Counter32
    MAX-ACCESS     read-only
    STATUS         current
    DESCRIPTION
        "tcp RtoMin"
    ::= { tcpStats 2 }

tcpStatsRtoMax OBJECT-TYPE
    SYNTAX         Counter32
    MAX-ACCESS     read-only
    STATUS         current
    DESCRIPTION
        "tcp RtoMax"
    ::= { tcpStats 3 }

tcpStatsMaxConn OBJECT-TYPE
    SYNTAX         Counter32
    MAX-ACCESS     read-only
    STATUS         current
    DESCRIPTION
        "tcp MaxConn"
    ::= { tcpStats 4 }

tcpStatsActiveOpens OBJECT-TYPE
    SYNTAX         Counter32
    MAX-ACCESS     read-only
    STATUS         current
    DESCRIPTION
        "tcp ActiveOpens"
    ::= { tcpStats 5 }

tcpStatsPassiveOpens OBJECT-TYPE
    SYNTAX         Counter32
    MAX-ACCESS     read-only
    STATUS         current
    DESCRIPTION
        "tcp PassiveOpens"
    ::= { tcpStats 6 }

tcpStatsAttemptFails OBJECT-TYPE
    SYNTAX         Counter32
    MAX-ACCESS     read-only
    STATUS         current
    DESCRIPTION
        "tcp AttemptFails"
    ::= { tcpStats 7 }

tcpStatsEstabResets OBJECT-TYPE
    SYNTAX         Counter32
    MAX-ACCESS     read-only
    STATUS         current
    DESCRIPTION
        "tcp EstabResets"
    ::= { tcpStats 8 }

tcpStatsInSegs OBJECT-TYPE
    SYNTAX         Counter32
    MAX-ACCESS     read-only
    STATUS         current
    DESCRIPTION
        "tcp InSegs"
    ::= { tcpStats 9 }

tcpStatsOutSegs OBJECT-TYPE
    SYNTAX         Counter32
    MAX-ACCESS     read-only
    STATUS         current
    DESCRIPTION
        "tcp OutSegs"
    ::= { tcpStats 10 }

tcpStatsRetransSegs OBJECT-TYPE
    SYNTAX         Counter32
    MAX-ACCESS     read-only
    STATUS         current
    DESCRIPTION
        "tcp RetransSegs"
    ::= { tcpStats 11 }

tcpStatsInErrs OBJECT-TYPE
    SYNTAX         Counter32
    MAX-ACCESS     read-only
    STATUS         current
    DESCRIPTION
        "tcp InErrs"
    ::= { tcpStats 12 }

tcpStatsCurrEstab OBJECT-TYPE
    SYNTAX         Counter32
    MAX-ACCESS     read-only
    STATUS         current
    DESCRIPTION
        "tcp CurrEstab"
    ::= { tcpStats 13 }

tcpStatsCurrConn OBJECT-TYPE
    SYNTAX         Counter32
    MAX-ACCESS     read-only
    STATUS         current
    DESCRIPTION
        "tcp CurrConn"
    ::= { tcpStats 14 }

tcpStatsOutRsts OBJECT-TYPE
    SYNTAX         Counter32
    MAX-ACCESS     read-only
    STATUS         current
    DESCRIPTION
        "tcp OutRsts"
    ::= { tcpStats 15 }

-- UDP statistics

udpStatsInDatagrams OBJECT-TYPE
    SYNTAX         Counter32
    MAX-ACCESS     read-only
    STATUS         current
    DESCRIPTION
        "udp InDatagrams"
    ::= { udpStats 1 }

udpStatsOutDatagrams OBJECT-TYPE
    SYNTAX         Counter32
    MAX-ACCESS     read-only
    STATUS         current
    DESCRIPTION
        "udp OutDatagrams"
    ::= { udpStats 2 }

udpStatsInErrors OBJECT-TYPE
    SYNTAX         Counter32
    MAX-ACCESS     read-only
    STATUS         current
    DESCRIPTION
        "udp InErrors"
    ::= { udpStats 3 }

udpStatsNoPorts OBJECT-TYPE
    SYNTAX         Counter32
    MAX-ACCESS     read-only
    STATUS         current
    DESCRIPTION
        "udp NoPorts"
    ::= { udpStats 4 }


-- BOOTP statistics

bootpRelayStatsTable OBJECT-TYPE
    SYNTAX      SEQUENCE OF BootpRelayStatsTableEntry
    MAX-ACCESS  not-accessible
    STATUS      current
    DESCRIPTION
        "The BOOTP relay agent statistics."
    ::= { bootpStats 1 }

bootpRelayStatsTableEntry  OBJECT-TYPE
    SYNTAX      BootpRelayStatsTableEntry
    MAX-ACCESS  not-accessible
    STATUS      current
    DESCRIPTION
        "A row in the BOOTP relay agent statistics table."
    INDEX  { bootpRelayStatsIndex }
    ::= { bootpRelayStatsTable 1 }

BootpRelayStatsTableEntry ::= SEQUENCE {
    bootpRelayStatsIndex                    PortNumber,
    bootpRelayStatsRequestsReceived         Counter32,
    bootpRelayStatsRequestsRelayed          Counter32,
    bootpRelayStatsRequestsDroppedNoRelay   Counter32,
    bootpRelayStatsRequestsDroppedNoServer  Counter32,
    bootpRelayStatsRequestsDroppedError     Counter32,
    bootpRelayStatsRepliesReceived          Counter32,
    bootpRelayStatsRepliesRelayed           Counter32,
    bootpRelayStatsRepliesDroppedError      Counter32
    }

bootpRelayStatsIndex  OBJECT-TYPE
    SYNTAX      PortNumber
    MAX-ACCESS  read-only
    STATUS      current
    DESCRIPTION
        "The port number of the port associated with this BOOTP relay
         statistics entry."
    ::= { bootpRelayStatsTableEntry 1 }

bootpRelayStatsRequestsReceived  OBJECT-TYPE
    SYNTAX      Counter32
    MAX-ACCESS  read-only
    STATUS      current
    DESCRIPTION
        "The total number of BOOTP request packets received on the port."
    ::= { bootpRelayStatsTableEntry 2 }

bootpRelayStatsRequestsRelayed  OBJECT-TYPE
    SYNTAX      Counter32
    MAX-ACCESS  read-only
    STATUS      current
    DESCRIPTION
        "The number of request packets relayed to the BOOTP server. If
         there is more than one server, a request is relayed once for
         each server; hence, with two servers, this counter will be twice
         as many as the value of the bootpRelayStatsRequestsReceived
         object."
    ::= { bootpRelayStatsTableEntry 3 }


bootpRelayStatsRequestsDroppedNoRelay  OBJECT-TYPE
    SYNTAX      Counter32
    MAX-ACCESS  read-only
    STATUS      current
    DESCRIPTION
        "This counter increases each time a request could not be relayed
         because BOOTP relay is disabled or not allowed on the port."
    ::= { bootpRelayStatsTableEntry 5 }

bootpRelayStatsRequestsDroppedNoServer  OBJECT-TYPE
    SYNTAX      Counter32
    MAX-ACCESS  read-only
    STATUS      current
    DESCRIPTION
        "This counter increases each time a request is dropped because
         there is no configured server or the server is unreachable
         because there is no active IP interface that can be used for
         relaying the request to the server."
    ::= { bootpRelayStatsTableEntry 6 }

bootpRelayStatsRequestsDroppedError  OBJECT-TYPE
    SYNTAX      Counter32
    MAX-ACCESS  read-only
    STATUS      current
    DESCRIPTION
        "This counter increases each time a request is dropped due to
         various errors encountered while processing the request packet.
         Such errors include short packet length, invalid 'hops' value,
         and memory allocation errors."
    ::= { bootpRelayStatsTableEntry 7 }

bootpRelayStatsRepliesReceived  OBJECT-TYPE
    SYNTAX      Counter32
    MAX-ACCESS  read-only
    STATUS      current
    DESCRIPTION
        "This is the total number of BOOTP response packets received on
         the port associated with this object."
    ::= { bootpRelayStatsTableEntry 8 }

bootpRelayStatsRepliesRelayed  OBJECT-TYPE
    SYNTAX      Counter32
    MAX-ACCESS  read-only
    STATUS      current
    DESCRIPTION
        "This is the total number of response packets that were relayed
         to the client."
    ::= { bootpRelayStatsTableEntry 9 }

bootpRelayStatsRepliesDroppedError  OBJECT-TYPE
    SYNTAX      Counter32
    MAX-ACCESS  read-only
    STATUS      current
    DESCRIPTION
        "This counter increases each time a response packet is dropped
         due to various errors encountered while processing the packet.
         Errors include unknown relay agent addresses ('giaddr'), and
         memory allocation errors."
    ::= { bootpRelayStatsTableEntry 10 }


-- ARP Statistics Group

arpStatEntries OBJECT-TYPE
    SYNTAX  Gauge32 
    MAX-ACCESS  read-only
    STATUS  current
    DESCRIPTION
        "The current number of ARP entries."
    ::= { arpStats 1 }

arpStatHighWater OBJECT-TYPE
    SYNTAX  Gauge32 
    MAX-ACCESS  read-only
    STATUS  current
    DESCRIPTION
        "The highest number of ARP entries."
    ::= { arpStats 2 }

arpStatMaxEntries OBJECT-TYPE
    SYNTAX  Gauge32 
    MAX-ACCESS  read-only
    STATUS  current
    DESCRIPTION
        "The maximum number of ARP entries."
    ::= { arpStats 3 }

-- NBR Statistics

nbrStatEntries OBJECT-TYPE
    SYNTAX  Gauge32
    MAX-ACCESS  read-only
    STATUS  current
    DESCRIPTION
        "The current number of NBR entries."
    ::= { nbrStats 1 }

nbrStatHighWater OBJECT-TYPE
    SYNTAX  INTEGER
    MAX-ACCESS  read-only
    STATUS  current
    DESCRIPTION
        "The highest number of NBR entries."
    ::= { nbrStats 2 }

nbrStatMaxEntries OBJECT-TYPE
    SYNTAX  INTEGER
    MAX-ACCESS  read-only
    STATUS  current
    DESCRIPTION
        "The maximum number of NBR entries."
    ::= { nbrStats 3}

-- ROUTE Statistics Group

routeStatEntries OBJECT-TYPE
    SYNTAX  Gauge32 
    MAX-ACCESS  read-only
    STATUS  current
    DESCRIPTION
        "The current number of IP routes."
    ::= { routeStats 1 }

routeStatHighWater OBJECT-TYPE
    SYNTAX  Gauge32 
    MAX-ACCESS  read-only
    STATUS  current
    DESCRIPTION
        "The highest number of IP routes."
    ::= { routeStats 2 }

routeStatStaticEntries OBJECT-TYPE
    SYNTAX  Gauge32 
    MAX-ACCESS  read-only
    STATUS  current
    DESCRIPTION
        "Current static routes."
    ::= { routeStats 3 }

routeStatRipEntries OBJECT-TYPE
    SYNTAX  Gauge32 
    MAX-ACCESS  read-only
    STATUS  current
    DESCRIPTION
        "Current RIP routes."
    ::= { routeStats 4 }

routeStatOspfEntries OBJECT-TYPE
    SYNTAX  Gauge32 
    MAX-ACCESS  read-only
    STATUS  current
    DESCRIPTION
        "Current OSPF routes."
    ::= { routeStats 5 }

routeStatBgpEntries OBJECT-TYPE
    SYNTAX  Gauge32 
    MAX-ACCESS  read-only
    STATUS  current
    DESCRIPTION
        "Current BGP routes."
    ::= { routeStats 6 }

routeStatMaxEntries OBJECT-TYPE
    SYNTAX  Gauge32 
    MAX-ACCESS  read-only
    STATUS  current
    DESCRIPTION
        "The maximum number of IP routes."
    ::= { routeStats 7 }

routeStatEcmpMaxEntries OBJECT-TYPE
    SYNTAX  Gauge32 
    MAX-ACCESS  read-only
    STATUS  current
    DESCRIPTION
        "Maximum number of ECMP routes."
    ::= { routeStats 8 }

routeStatEcmpMaxStaticEntries OBJECT-TYPE
    SYNTAX  Gauge32 
    MAX-ACCESS  read-only
    STATUS  current
    DESCRIPTION
        "Maximum number of static ECMP routes."
    ::= { routeStats 9 }


routeStatEcmpPathsEntries OBJECT-TYPE
    SYNTAX  Gauge32 
    MAX-ACCESS  read-only
    STATUS  current
    DESCRIPTION
        "Number of routes with ECMP paths."
    ::= { routeStats 11 }

-- DNS Statistics

dnsStatInGoodDnsRequests OBJECT-TYPE 
    SYNTAX  Counter32 
    MAX-ACCESS  read-only
    STATUS  current 
    DESCRIPTION 
        "The total number of DNS request packets which are received."
    ::= { dnsStats 1 }

dnsStatInBadDnsRequests OBJECT-TYPE 
    SYNTAX  Counter32 
    MAX-ACCESS  read-only
    STATUS  current 
    DESCRIPTION 
        "The total number of DNS request packets received that were dropped."
    ::= { dnsStats 2 }

dnsStatOutDnsRequests OBJECT-TYPE 
    SYNTAX  Counter32 
    MAX-ACCESS  read-only
    STATUS  current 
    DESCRIPTION 
        "The total number of DNS request packets that have been transmitted."
    ::= { dnsStats 3 }

-- The VRRP Statistics

vrrpStatInAdvers OBJECT-TYPE 
    SYNTAX  Counter32 
    MAX-ACCESS  read-only
    STATUS  current 
    DESCRIPTION 
        "The number of good VRRP advertisements which are received."
    ::= { vrrpStats 1 }

vrrpStatOutAdvers OBJECT-TYPE 
    SYNTAX  Counter32 
    MAX-ACCESS  read-only
    STATUS  current 
    DESCRIPTION 
        "The number of good VRRP advertisements which are transmitted."
    ::= { vrrpStats 2 }

vrrpStatBadAdvers OBJECT-TYPE 
    SYNTAX  Counter32 
    MAX-ACCESS  read-only
    STATUS  current 
    DESCRIPTION 
        "The number of bad VRRP advertisements which are received."
    ::= { vrrpStats 3 }

vrrpStatBadVersion OBJECT-TYPE
    SYNTAX  Counter32
    MAX-ACCESS  read-only
    STATUS  current
    DESCRIPTION
        "The number of bad VRRP version adv which are received."
    ::= { vrrpStats 4 }

vrrpStatBadAddress OBJECT-TYPE
    SYNTAX  Counter32
    MAX-ACCESS  read-only
    STATUS  current
    DESCRIPTION
        "The number of bad VRRP addres adv which are received."
    ::= { vrrpStats 5 }

vrrpStatBadPassword OBJECT-TYPE
    SYNTAX  Counter32
    MAX-ACCESS  read-only
    STATUS  current
    DESCRIPTION
        "The number of bad VRRP advertisements which are received."
    ::= { vrrpStats 6 }

vrrpStatBadVrid OBJECT-TYPE
    SYNTAX  Counter32
    MAX-ACCESS  read-only
    STATUS  current
    DESCRIPTION
        "The number of bad VRRP version ID adv which are received."
    ::= { vrrpStats 7 }

vrrpStatBadData OBJECT-TYPE
    SYNTAX  Counter32
    MAX-ACCESS  read-only
    STATUS  current
    DESCRIPTION
        "The number of bad VRRP advertisements which are received."
    ::= { vrrpStats 8 }

vrrpStatBadInterval OBJECT-TYPE
    SYNTAX  Counter32
    MAX-ACCESS  read-only
    STATUS  current
    DESCRIPTION
        "The number of bad VRRP intervals which are received."
    ::= { vrrpStats 9 }

vrrpStatOutGratuitousARPs OBJECT-TYPE
    SYNTAX  Counter32
    MAX-ACCESS  read-only
    STATUS  current
    DESCRIPTION
        "The number of gratuitous ARP packets which are transmitted."
    ::= { vrrpStats 10 }


-- Clear Statistics  for ip and ip interface
ipClearStats OBJECT-TYPE
    SYNTAX  INTEGER { 
    ok(1),
    clear(2)
    }
    MAX-ACCESS  read-write
    STATUS  current  
    DESCRIPTION
        "Setting this to clear(2) results in clearing the IP statistics." 
    ::= { clearStats 1 }

vrrpClearStats OBJECT-TYPE 
    SYNTAX  INTEGER {
        ok(1),
        clear(2)
        }
    MAX-ACCESS  read-write
    STATUS  current 
    DESCRIPTION 
        "Setting this to clear(2) results in clearing the VRRP statistics."
    ::= { clearStats 2 }


ospfClearStats OBJECT-TYPE
    SYNTAX  INTEGER {
        clear(1),
        ok(2)
        }
    MAX-ACCESS  read-write
    STATUS  current
    DESCRIPTION
        "Setting this to clear(1) results in clearing the OSPF statistics."
    ::= { clearStats 4 }

tcpClearStats OBJECT-TYPE
    SYNTAX  INTEGER {
        clear(1),
        ok(2)
        }
    MAX-ACCESS  read-write
    STATUS  current
    DESCRIPTION
        "Setting this to clear(1) results in clearing the TCP statistics."
    ::= { clearStats 5 }

udpClearStats OBJECT-TYPE
    SYNTAX  INTEGER {
        clear(1),
        ok(2)
        }
    MAX-ACCESS  read-write
    STATUS  current
    DESCRIPTION
        "Setting this to clear(1) results in clearing the UDP statistics."
    ::= { clearStats 6 }

dnsClearStats OBJECT-TYPE
    SYNTAX  INTEGER {
        clear(1),
        ok(2)
        }
    MAX-ACCESS  read-write
    STATUS  current
    DESCRIPTION
        "Setting this to clear(1) results in clearing the DNS statistics."
    ::= { clearStats 7 }

arpClearStats OBJECT-TYPE
    SYNTAX  INTEGER {
        clear(1),
        ok(2)
        }
    MAX-ACCESS  read-write
    STATUS  current
    DESCRIPTION
        "Setting this to clear(1) results in clearing the ARP statistics."
    ::= { clearStats 8 }

icmpClearStats OBJECT-TYPE
    SYNTAX  INTEGER {
        clear(1),
        ok(2)
        }
    MAX-ACCESS  read-write
    STATUS  current
    DESCRIPTION
        "Setting this to clear(1) results in clearing the ICMP statistics."
    ::= { clearStats 9 }

routeClearStats OBJECT-TYPE
    SYNTAX  INTEGER {
        clear(1),
        ok(2)
        }
    MAX-ACCESS  read-write
    STATUS  current
    DESCRIPTION
        "Setting this to clear(1) results in clearing the Route statistics."
    ::= { clearStats 10 }

ipv6ClearStats OBJECT-TYPE
    SYNTAX  INTEGER {
        clear(1),
        ok(2)
        }
    MAX-ACCESS  read-write
    STATUS  current
    DESCRIPTION
        "Setting this to clear(1) results in clearing the IPv6 statistics."
    ::= { clearStats 13 }

ipv6ClearIcmpStats OBJECT-TYPE
    SYNTAX  INTEGER {
        clear(1),
        ok(2)
        }
    MAX-ACCESS  read-write
    STATUS  current
    DESCRIPTION
        "Setting this to clear(1) results in clearing the ICMP6 statistics."
    ::= { clearStats 14 }

ipv6ClearUdpStats OBJECT-TYPE
    SYNTAX  INTEGER {
        clear(1),
        ok(2)
        }
    MAX-ACCESS  read-write
    STATUS  current
    DESCRIPTION
        "Setting this to clear(1) results in clearing the UDP6 statistics."
    ::= { clearStats 15 }

ospf3ClearStats OBJECT-TYPE
    SYNTAX  INTEGER {
        clear(1),
        ok(2)
        }
    MAX-ACCESS  read-write
    STATUS  current
    DESCRIPTION
        "Setting this to clear(1) results in clearing the ospf3 statistics."
    ::= { clearStats 16 }
ripClearStats OBJECT-TYPE
    SYNTAX  INTEGER {
        clear(1),
        ok(2)
        }
    MAX-ACCESS  read-write
    STATUS  current
    DESCRIPTION
        "Setting this to clear(1) results in clearing the RIP statistics."
    ::= { clearStats 17 }

ipv6NbrClearStats OBJECT-TYPE
    SYNTAX  INTEGER {
        clear(1),
        ok(2)
        }
    MAX-ACCESS  read-write
    STATUS  current
    DESCRIPTION
        "Setting this to clear(1) results in clearing the IPv6 nbr statistics."
    ::= { clearStats 18 }


-- Ospf Statistics 

-- Ospf Statistics for all interfaces and OSPF areas 
ospfGeneralStats       OBJECT IDENTIFIER ::= { ospfStats  1 }
ospfCumRxTxStats       OBJECT IDENTIFIER ::= { ospfGeneralStats  1 }
ospfCumNbrChangeStats  OBJECT IDENTIFIER ::= { ospfGeneralStats  2 }
ospfCumIntfChangeStats OBJECT IDENTIFIER ::= { ospfGeneralStats  3 }
ospfTimersKickOffStats OBJECT IDENTIFIER ::= { ospfGeneralStats  4 }

-- Ospf Statistics / Area
ospfArea           OBJECT IDENTIFIER ::= { ospfStats  2 }

ospfAreaRxTxStats OBJECT-TYPE
    SYNTAX SEQUENCE OF OspfAreaRxTxStatsEntry
    MAX-ACCESS not-accessible
    STATUS current
    DESCRIPTION
      "The table of OSPF Area Rx/Tx Statistics."
    ::= { ospfArea 1 }

ospfAreaRxTxStatsEntry OBJECT-TYPE
    SYNTAX OspfAreaRxTxStatsEntry
    MAX-ACCESS not-accessible
    STATUS current
    DESCRIPTION
      "Rx Tx packet Statistics about a OSPF area."
    INDEX { ospfAreaRxTxIndex }
    ::= { ospfAreaRxTxStats 1 }
 
OspfAreaRxTxStatsEntry ::= SEQUENCE {
    ospfAreaRxTxIndex          Integer32,
    ospfAreaRxPkts             Counter32,
    ospfAreaTxPkts             Counter32,
    ospfAreaRxHello            Counter32,
    ospfAreaTxHello            Counter32,
    ospfAreaRxDatabase         Counter32,
    ospfAreaTxDatabase         Counter32,
    ospfAreaRxlsReqs           Counter32,
    ospfAreaTxlsReqs           Counter32,
    ospfAreaRxlsAcks           Counter32,
    ospfAreaTxlsAcks           Counter32,
    ospfAreaRxlsUpdates        Counter32,
    ospfAreaTxlsUpdates        Counter32
    }

ospfAreaRxTxIndex OBJECT-TYPE
    SYNTAX  Integer32
    MAX-ACCESS  read-only
    STATUS  current
    DESCRIPTION
        "The index of the ospf Area for which these statistics apply."
    ::= { ospfAreaRxTxStatsEntry 1 }

ospfAreaRxPkts OBJECT-TYPE
    SYNTAX  Counter32
    MAX-ACCESS  read-only
    STATUS  current
    DESCRIPTION
        "The total number of OSPF packets received in this OSPF area."
    ::= { ospfAreaRxTxStatsEntry 2 }
 
ospfAreaTxPkts OBJECT-TYPE
    SYNTAX  Counter32
    MAX-ACCESS  read-only
    STATUS  current
    DESCRIPTION
        "The total number of OSPF packets transmitted in this OSPF area."
    ::= { ospfAreaRxTxStatsEntry 3 }
 
ospfAreaRxHello OBJECT-TYPE
    SYNTAX  Counter32 
    MAX-ACCESS  read-only
    STATUS  current
    DESCRIPTION
        "The total number of Hello packets received in this OSPF area."
    ::= { ospfAreaRxTxStatsEntry 4 }

ospfAreaTxHello OBJECT-TYPE
    SYNTAX  Counter32
    MAX-ACCESS  read-only
    STATUS  current
    DESCRIPTION
        "The total number of Hello packets transmitted in this OSPF
         area."
    ::= { ospfAreaRxTxStatsEntry 5 }
 
ospfAreaRxDatabase OBJECT-TYPE
    SYNTAX  Counter32 
    MAX-ACCESS  read-only
    STATUS  current
    DESCRIPTION
        "The total number of Database Description packets transmitted 
         for this OSPF area."
    ::= { ospfAreaRxTxStatsEntry 6 }

ospfAreaTxDatabase OBJECT-TYPE
    SYNTAX  Counter32
    MAX-ACCESS  read-only
    STATUS  current
    DESCRIPTION
        "The total number of Database Description packets transmitted 
         for this OSPF area."
    ::= { ospfAreaRxTxStatsEntry 7 }
 
ospfAreaRxlsReqs OBJECT-TYPE
    SYNTAX  Counter32 
    MAX-ACCESS  read-only
    STATUS  current
    DESCRIPTION
        "The total number of Link State Request packets received for 
         this OSPF area."
    ::= { ospfAreaRxTxStatsEntry 8 }

ospfAreaTxlsReqs OBJECT-TYPE
    SYNTAX  Counter32 
    MAX-ACCESS  read-only
    STATUS  current
    DESCRIPTION
        "The total number of Link State Request packets transmitted for 
         this OSPF area."
    ::= { ospfAreaRxTxStatsEntry 9 }

ospfAreaRxlsAcks OBJECT-TYPE
    SYNTAX  Counter32
    MAX-ACCESS  read-only
    STATUS  current
    DESCRIPTION
        "The total number of Link State Acknowledgement packets received for 
         this OSPF area."
    ::= { ospfAreaRxTxStatsEntry 10 }
 
ospfAreaTxlsAcks OBJECT-TYPE
    SYNTAX  Counter32 
    MAX-ACCESS  read-only
    STATUS  current
    DESCRIPTION
        "The total number of Link State Acknowledgement packets transmitted
         for this OSPF area."
    ::= { ospfAreaRxTxStatsEntry 11 }

ospfAreaRxlsUpdates OBJECT-TYPE
    SYNTAX  Counter32
    MAX-ACCESS  read-only
    STATUS  current
    DESCRIPTION
        "The total number of Link State Update packets received for 
         this OSPF area."
    ::= { ospfAreaRxTxStatsEntry 12 }
 
ospfAreaTxlsUpdates OBJECT-TYPE
    SYNTAX  Counter32 
    MAX-ACCESS  read-only
    STATUS  current
    DESCRIPTION
        "The total number of Link State Update packets transmitted for 
         this OSPF area."
    ::= { ospfAreaRxTxStatsEntry 13 }


ospfAreaNbrChangeStats OBJECT-TYPE
    SYNTAX SEQUENCE OF OspfAreaNbrChangeStatsEntry
    MAX-ACCESS not-accessible
    STATUS current
    DESCRIPTION
      "The table of OSPF Area Neighbour Statistics."
    ::= { ospfArea 2 }

ospfAreaNbrChangeStatsEntry OBJECT-TYPE
    SYNTAX OspfAreaNbrChangeStatsEntry
    MAX-ACCESS not-accessible
    STATUS current
    DESCRIPTION
      "Area Neighbour Change Statistics about a OSPF area."
    INDEX { ospfAreaNbrIndex }
    ::= { ospfAreaNbrChangeStats 1 }
 
OspfAreaNbrChangeStatsEntry ::= SEQUENCE {
    ospfAreaNbrIndex            Integer32,
    ospfAreaNbrhello            Counter32,
    ospfAreaNbrStart            Counter32,
    ospfAreaNbrAdjointOk        Counter32,
    ospfAreaNbrNegotiationDone  Counter32,
    ospfAreaNbrExchangeDone     Counter32,
    ospfAreaNbrBadRequests      Counter32,
    ospfAreaNbrBadSequence      Counter32,
    ospfAreaNbrLoadingDone      Counter32,
    ospfAreaNbrN1way            Counter32,
    ospfAreaNbrRstAd            Counter32,
    ospfAreaNbrDown         Counter32,
    ospfAreaNbrN2way            Counter32
    }

ospfAreaNbrIndex OBJECT-TYPE
    SYNTAX  Integer32
    MAX-ACCESS  read-only
    STATUS  current
    DESCRIPTION
        "The index of the ospf Area for which these statistics apply."
    ::= { ospfAreaNbrChangeStatsEntry 1 }

ospfAreaNbrhello OBJECT-TYPE
    SYNTAX  Counter32
    MAX-ACCESS  read-only
    STATUS  current
    DESCRIPTION
        "The total number of Hello packets received from neighbours
         in this OSPF area."
    ::= { ospfAreaNbrChangeStatsEntry 2 }

ospfAreaNbrStart OBJECT-TYPE
    SYNTAX  Counter32
    MAX-ACCESS  read-only
    STATUS  current
    DESCRIPTION
        "The total number of neighbours in this state (i.e. an indication
         that  Hello packets should now be sent to the neighbour at intervals
         of HelloInterval seconds.) in this OSPF area."
    ::= { ospfAreaNbrChangeStatsEntry 3 }

ospfAreaNbrAdjointOk OBJECT-TYPE
    SYNTAX  Counter32
    MAX-ACCESS  read-only
    STATUS  current
    DESCRIPTION
        "The total number of decisions to be made (again) as to whether
         an adjacency should be established/maintained with the neighbour.
         for this OSPF area."
    ::= { ospfAreaNbrChangeStatsEntry 4 }

ospfAreaNbrNegotiationDone OBJECT-TYPE
    SYNTAX  Counter32
    MAX-ACCESS  read-only
    STATUS  current
    DESCRIPTION
        "The total number of neighbours in this state wherein the 
         Master/slave relationship has been negotiated, and sequence
         numbers have been exchanged, for this OSPF area."
    ::= { ospfAreaNbrChangeStatsEntry 5 }

ospfAreaNbrExchangeDone OBJECT-TYPE
    SYNTAX  Counter32
    MAX-ACCESS  read-only
    STATUS  current
    DESCRIPTION
        "The total number of neighbours in this state (i.e. in an
         adjacency's final state) having transimitted a full sequence 
         of Database Description packets, for this OSPF area."
    ::= { ospfAreaNbrChangeStatsEntry 6 }

ospfAreaNbrBadRequests OBJECT-TYPE
    SYNTAX  Counter32
    MAX-ACCESS  read-only
    STATUS  current
    DESCRIPTION
        "The sum total number of Link State Requests which have been received
         for a link state advertisement not contained in the database across
         this OSPF area."
    ::= { ospfAreaNbrChangeStatsEntry 7 }

ospfAreaNbrBadSequence OBJECT-TYPE
    SYNTAX  Counter32
    MAX-ACCESS  read-only
    STATUS  current
    DESCRIPTION
        "The total number of Database Description packets which have been
         received that either 
         a) has an unexpected DD sequence number
         b) Unexpectedly has the init bit set
         c) Has an options field differing from the last Options field
            received in a Database Description packet.
         Any of these conditions indicate that some error has occured during
         adjacency establishment for this OSPF area."
    ::= { ospfAreaNbrChangeStatsEntry 8 }

ospfAreaNbrLoadingDone OBJECT-TYPE
    SYNTAX  Counter32
    MAX-ACCESS  read-only
    STATUS  current
    DESCRIPTION
        "The total number of link state updates received for all 
         out-of-date portions of the database in this OSPF area."
    ::= { ospfAreaNbrChangeStatsEntry 9 }

ospfAreaNbrN1way OBJECT-TYPE
    SYNTAX  Counter32
    MAX-ACCESS  read-only
    STATUS  current
    DESCRIPTION
        "The total number of Hello packets received from neighbours, in
         which this router is not mentioned in this OSPF area."
    ::= { ospfAreaNbrChangeStatsEntry 10 }

ospfAreaNbrRstAd OBJECT-TYPE
    SYNTAX  Counter32
    MAX-ACCESS  read-only
    STATUS  current
    DESCRIPTION
        "The total number of times the Neighbour adjacency has been reset
         across this OPSF area."
    ::= { ospfAreaNbrChangeStatsEntry 11 }

ospfAreaNbrDown OBJECT-TYPE
    SYNTAX  Counter32
    MAX-ACCESS  read-only
    STATUS  current
    DESCRIPTION
        "The total number of Neighbouring routers down (i.e. in the initial
         state of a neighbour conversation.) in this OSPF area."
    ::= { ospfAreaNbrChangeStatsEntry 12 }

ospfAreaNbrN2way OBJECT-TYPE
    SYNTAX  Counter32
    MAX-ACCESS  read-only
    STATUS  current
    DESCRIPTION
        "The total number of Hello packets received from neighbours, in
         which this router is mentioned in this OSPF area."
    ::= { ospfAreaNbrChangeStatsEntry 13 }

ospfAreaChangeStats OBJECT-TYPE
    SYNTAX SEQUENCE OF OspfAreaChangeStatsEntry
    MAX-ACCESS not-accessible
    STATUS current
    DESCRIPTION
      "The table of OSPF Area Change Statistics."
    ::= { ospfArea 3 }

ospfAreaChangeStatsEntry OBJECT-TYPE
    SYNTAX OspfAreaChangeStatsEntry
    MAX-ACCESS not-accessible
    STATUS current
    DESCRIPTION
      "Area  Change Statistics about a OSPF area."
    INDEX { ospfAreaIntfIndex }
    ::= { ospfAreaChangeStats 1 }
 
OspfAreaChangeStatsEntry ::= SEQUENCE {
    ospfAreaIntfIndex       Integer32,
    ospfAreaIntfHello           Counter32,
    ospfAreaIntfDown            Counter32,
    ospfAreaIntfLoop        Counter32,
    ospfAreaIntfUnloop      Counter32,
    ospfAreaIntfWaitTimer       Counter32,
    ospfAreaIntfBackup          Counter32,
    ospfAreaIntfNbrChange       Counter32
    }

ospfAreaIntfIndex OBJECT-TYPE
    SYNTAX    Integer32
    MAX-ACCESS    read-only
    STATUS    current
    DESCRIPTION
        "The index of the OSPF Area for which these statistics apply."
    ::= { ospfAreaChangeStatsEntry 1 }

ospfAreaIntfHello OBJECT-TYPE
    SYNTAX    Counter32
    MAX-ACCESS    read-only
    STATUS    current
    DESCRIPTION
        "The total number of Hello packets sent on this OSPF area."
    ::= { ospfAreaChangeStatsEntry 2 }

ospfAreaIntfDown OBJECT-TYPE
    SYNTAX   Counter32
    MAX-ACCESS   read-only
    STATUS   current
    DESCRIPTION
        "The total number of interfaces down in this OSPF area."
    ::= { ospfAreaChangeStatsEntry 3 }

ospfAreaIntfLoop OBJECT-TYPE
    SYNTAX    Counter32
    MAX-ACCESS    read-only
    STATUS    current
    DESCRIPTION
        "The total number of interfaces no longer connected to 
         the attatched network in this OSPF area."
    ::= { ospfAreaChangeStatsEntry 4 }

ospfAreaIntfUnloop OBJECT-TYPE
    SYNTAX   Counter32
    MAX-ACCESS   read-only
    STATUS   current
    DESCRIPTION
        "The total number of interfaces connected to the attatched
     network in this OSPF area.."
    ::= { ospfAreaChangeStatsEntry 5 }


ospfAreaIntfWaitTimer OBJECT-TYPE
    SYNTAX        Counter32
    MAX-ACCESS        read-only
    STATUS        current
    DESCRIPTION
        "The total number of times the Wait Timer has been fired,
         (indicating the end of the waiting period that is required
          before electing a (Backup) Designated Router) for this 
          OSPF area."
    ::= { ospfAreaChangeStatsEntry 6 }

ospfAreaIntfBackup OBJECT-TYPE
    SYNTAX     Counter32
    MAX-ACCESS     read-only
    STATUS     current
    DESCRIPTION
        "The total number of Backup Designated Routers on the attatched
         network for this OSPF area."
    ::= { ospfAreaChangeStatsEntry 7 }


ospfAreaIntfNbrChange OBJECT-TYPE
    SYNTAX     Counter32
    MAX-ACCESS     read-only
    STATUS     current
    DESCRIPTION
        "The total number of changes in the set of bidirectional neighbours
         associated with the interface in this OSPF area."
    ::= { ospfAreaChangeStatsEntry 8 }

ospfAreaErrorStats OBJECT-TYPE
    SYNTAX SEQUENCE OF OspfAreaErrorStatsEntry
    MAX-ACCESS not-accessible
    STATUS current
    DESCRIPTION
      "The table of OSPF Area Error Statistics."
    ::= { ospfArea 4 }

ospfAreaErrorStatsEntry OBJECT-TYPE
    SYNTAX OspfAreaErrorStatsEntry
    MAX-ACCESS not-accessible
    STATUS current
    DESCRIPTION
      "Error Statistics for an OSPF area."
    INDEX { ospfAreaErrIndex }
    ::= { ospfAreaErrorStats 1 }
 
OspfAreaErrorStatsEntry ::= SEQUENCE {
    ospfAreaErrIndex        Integer32,
    ospfAreaErrAuthFailure      Counter32,
    ospfAreaErrNetmaskMismatch  Counter32,
    ospfAreaErrHelloMismatch    Counter32,
    ospfAreaErrDeadMismatch     Counter32,
    ospfAreaErrOptionsMismatch  Counter32,
    ospfAreaErrUnknownNbr       Counter32,
    ospfAreaErrAreaMismatch     Counter32,
    ospfAreaErrInvalidSelfOrigLsa Counter32
    }

ospfAreaErrIndex OBJECT-TYPE
    SYNTAX    Integer32
    MAX-ACCESS    read-only
    STATUS    current
    DESCRIPTION
        "The index of the OSPF Area for which these statistics apply."
    ::= { ospfAreaErrorStatsEntry 1 }

ospfAreaErrAuthFailure OBJECT-TYPE
    SYNTAX    Counter32
    MAX-ACCESS    read-only
    STATUS    current
    DESCRIPTION
        "The total number of packets received with a wrong password in 
         this area."
    ::= { ospfAreaErrorStatsEntry 2 }

ospfAreaErrNetmaskMismatch OBJECT-TYPE
    SYNTAX    Counter32
    MAX-ACCESS    read-only
    STATUS    current
    DESCRIPTION
        "The total number of packets received with a wrong netmask in 
         this area."
    ::= { ospfAreaErrorStatsEntry 3 }

ospfAreaErrHelloMismatch OBJECT-TYPE
    SYNTAX    Counter32
    MAX-ACCESS    read-only
    STATUS    current
    DESCRIPTION
        "The total number of packets received with a different hello interval
         in this area."
    ::= { ospfAreaErrorStatsEntry 4 }

ospfAreaErrDeadMismatch OBJECT-TYPE
    SYNTAX    Counter32
    MAX-ACCESS    read-only
    STATUS    current
    DESCRIPTION
        "The total number of packets received with a different dead interval
         in this area."
    ::= { ospfAreaErrorStatsEntry 5 }

ospfAreaErrOptionsMismatch OBJECT-TYPE
    SYNTAX    Counter32
    MAX-ACCESS    read-only
    STATUS    current
    DESCRIPTION
        "The total number of packets received with a different options
         in this area."
    ::= { ospfAreaErrorStatsEntry 6 }

ospfAreaErrUnknownNbr OBJECT-TYPE
    SYNTAX    Counter32
    MAX-ACCESS    read-only
    STATUS    current
    DESCRIPTION
        "The total number of packets received from an unknown neighbor
         in this area."
    ::= { ospfAreaErrorStatsEntry 7 }

ospfAreaErrAreaMismatch OBJECT-TYPE
    SYNTAX    Counter32
    MAX-ACCESS    read-only
    STATUS    current
    DESCRIPTION
        "The total number of packets received with a wrong  area."
    ::= { ospfAreaErrorStatsEntry 8 }

ospfAreaErrInvalidSelfOrigLsa OBJECT-TYPE
    SYNTAX     Counter32
    MAX-ACCESS     read-only
    STATUS     current
    DESCRIPTION
        "The total number of packets received with invalid self
         originated LSAs."
    ::= { ospfAreaErrorStatsEntry 9 }

-- Ospf Statistics / Interface
ospfInterface          OBJECT IDENTIFIER ::= { ospfStats  3 }

ospfIntfRxTxStats OBJECT-TYPE
    SYNTAX SEQUENCE OF OspfIntfRxTxStatsEntry
    MAX-ACCESS not-accessible
    STATUS current
    DESCRIPTION
      "The table of OSPF Interface Rx/Tx packet Statistics."
    ::= { ospfInterface 1 }

ospfIntfRxTxStatsEntry OBJECT-TYPE
    SYNTAX OspfIntfRxTxStatsEntry
    MAX-ACCESS not-accessible
    STATUS current
    DESCRIPTION
      "OSPF interface Rx/Tx packet statistics."
    INDEX { ospfIntfRxTxIndex }
    ::= { ospfIntfRxTxStats 1 }

OspfIntfRxTxStatsEntry ::= SEQUENCE {
    ospfIntfRxTxIndex          Integer32,
    ospfIntfRxPkts             Counter32,
    ospfIntfTxPkts             Counter32,
    ospfIntfRxHello            Counter32,
    ospfIntfTxHello            Counter32,
    ospfIntfRxDatabase         Counter32,
    ospfIntfTxDatabase         Counter32,
    ospfIntfRxlsReqs           Counter32,
    ospfIntfTxlsReqs           Counter32,
    ospfIntfRxlsAcks           Counter32,
    ospfIntfTxlsAcks           Counter32,
    ospfIntfRxlsUpdates        Counter32,
    ospfIntfTxlsUpdates        Counter32
    }

ospfIntfRxTxIndex OBJECT-TYPE
    SYNTAX  Integer32
    MAX-ACCESS  read-only
    STATUS  current
    DESCRIPTION
        "The OSPF interface for which these statistics apply."
    ::= { ospfIntfRxTxStatsEntry 1 }

ospfIntfRxPkts OBJECT-TYPE
    SYNTAX  Counter32
    MAX-ACCESS  read-only
    STATUS  current
    DESCRIPTION
        "The total number of OSPF packets received for this OSPF interface."
    ::= { ospfIntfRxTxStatsEntry 2 }
 
ospfIntfTxPkts OBJECT-TYPE
    SYNTAX  Counter32
    MAX-ACCESS  read-only
    STATUS  current
    DESCRIPTION
        "The total number of OSPF packets transmitted for this OSPF interface."
    ::= { ospfIntfRxTxStatsEntry 3 }
 
ospfIntfRxHello OBJECT-TYPE
    SYNTAX  Counter32 
    MAX-ACCESS  read-only
    STATUS  current
    DESCRIPTION
        "The total number of Hello packets received 
         for this OSPF interface."
    ::= { ospfIntfRxTxStatsEntry 4 }

ospfIntfTxHello OBJECT-TYPE
    SYNTAX  Counter32
    MAX-ACCESS  read-only
    STATUS  current
    DESCRIPTION
        "The total number of Hello packets transmitted 
         for this OSPF interface."
    ::= { ospfIntfRxTxStatsEntry 5 }
 
ospfIntfRxDatabase OBJECT-TYPE
    SYNTAX  Counter32 
    MAX-ACCESS  read-only
    STATUS  current
    DESCRIPTION
        "The total number of Database Description packets received 
         for this OSPF interface."
    ::= { ospfIntfRxTxStatsEntry 6 }

ospfIntfTxDatabase OBJECT-TYPE
    SYNTAX  Counter32
    MAX-ACCESS  read-only
    STATUS  current
    DESCRIPTION
        "The total number of Database Description packets transmitted 
         for this OSPF interface."
    ::= { ospfIntfRxTxStatsEntry 7 }
 
ospfIntfRxlsReqs OBJECT-TYPE
    SYNTAX  Counter32 
    MAX-ACCESS  read-only
    STATUS  current
    DESCRIPTION
        "The total number of Link State Request packets received
         for this OSPF interface."
    ::= { ospfIntfRxTxStatsEntry 8 }

ospfIntfTxlsReqs OBJECT-TYPE
    SYNTAX  Counter32 
    MAX-ACCESS  read-only
    STATUS  current
    DESCRIPTION
        "The total number of Link State Request packets transmitted
         for this OSPF interface."
    ::= { ospfIntfRxTxStatsEntry 9 }

ospfIntfRxlsAcks OBJECT-TYPE
    SYNTAX  Counter32
    MAX-ACCESS  read-only
    STATUS  current
    DESCRIPTION
        "The total number of Link State Acknowledgement packets received
         for this OSPF interface."
    ::= { ospfIntfRxTxStatsEntry 10 }
 
ospfIntfTxlsAcks OBJECT-TYPE
    SYNTAX  Counter32 
    MAX-ACCESS  read-only
    STATUS  current
    DESCRIPTION
        "The total number of Link State Acknowledgement packets transmitted
         for this OSPF interface."
    ::= { ospfIntfRxTxStatsEntry 11 }

ospfIntfRxlsUpdates OBJECT-TYPE
    SYNTAX  Counter32
    MAX-ACCESS  read-only
    STATUS  current
    DESCRIPTION
        "The total number of Link State Update packets received for 
         this OSPF interface."
    ::= { ospfIntfRxTxStatsEntry 12 }
 
ospfIntfTxlsUpdates OBJECT-TYPE
    SYNTAX  Counter32 
    MAX-ACCESS  read-only
    STATUS  current
    DESCRIPTION
        "The total number of Link State Update packets transmitted for 
         this OSPF interface."
    ::= { ospfIntfRxTxStatsEntry 13 }


ospfIntfNbrChangeStats OBJECT-TYPE
    SYNTAX SEQUENCE OF OspfIntfNbrChangeStatsEntry
    MAX-ACCESS not-accessible
    STATUS current
    DESCRIPTION
      "The table of OSPF Interface Neighbour change Statistics."
    ::= { ospfInterface 2 }

ospfIntfNbrChangeStatsEntry OBJECT-TYPE
    SYNTAX OspfIntfNbrChangeStatsEntry
    MAX-ACCESS not-accessible
    STATUS current
    DESCRIPTION
      "OSPF interface Neighbour Change statistics."
    INDEX { ospfIntfNbrIndex }
    ::= { ospfIntfNbrChangeStats 1 }

OspfIntfNbrChangeStatsEntry ::= SEQUENCE {
    ospfIntfNbrIndex        Integer32,
    ospfIntfNbrhello            Counter32,
    ospfIntfNbrStart            Counter32,
    ospfIntfNbrAdjointOk        Counter32,
    ospfIntfNbrNegotiationDone  Counter32,
    ospfIntfNbrExchangeDone     Counter32,
    ospfIntfNbrBadRequests      Counter32,
    ospfIntfNbrBadSequence      Counter32,
    ospfIntfNbrLoadingDone      Counter32,
    ospfIntfNbrN1way            Counter32,
    ospfIntfNbrRstAd            Counter32,
    ospfIntfNbrDown         Counter32,
    ospfIntfNbrN2way            Counter32
    }

ospfIntfNbrIndex OBJECT-TYPE
    SYNTAX  Integer32
    MAX-ACCESS  read-only
    STATUS  current
    DESCRIPTION
        "The index of the OSPF Interface for which these statistics apply."
    ::= { ospfIntfNbrChangeStatsEntry 1 }

ospfIntfNbrhello OBJECT-TYPE
    SYNTAX  Counter32
    MAX-ACCESS  read-only
    STATUS  current
    DESCRIPTION
        "The total number of Hello packets received from neighbours
         in this OSPF interface."
    ::= { ospfIntfNbrChangeStatsEntry 2 }

ospfIntfNbrStart OBJECT-TYPE
    SYNTAX  Counter32
    MAX-ACCESS  read-only
    STATUS  current
    DESCRIPTION
        "The total number of neighbours in this state (i.e. an indication
         that  Hello packets should now be sent to the neighbour at intervals
         of HelloInterval seconds.) in this OSPF interface."
    ::= { ospfIntfNbrChangeStatsEntry  3 }

ospfIntfNbrAdjointOk OBJECT-TYPE
    SYNTAX  Counter32
    MAX-ACCESS  read-only
    STATUS  current
    DESCRIPTION
        "The total number of decisions to be made (again) as to whether
         an adjacency should be established/maintained with the neighbour.
         for this OSPF interface."
    ::= { ospfIntfNbrChangeStatsEntry 4 }

ospfIntfNbrNegotiationDone OBJECT-TYPE
    SYNTAX  Counter32
    MAX-ACCESS  read-only
    STATUS  current
    DESCRIPTION
        "The total number of neighbours in this state wherein the 
         Master/slave relationship has been negotiated, and sequence
         numbers have been exchanged, for this OSPF interface."
    ::= { ospfIntfNbrChangeStatsEntry 5 }

ospfIntfNbrExchangeDone OBJECT-TYPE
    SYNTAX  Counter32
    MAX-ACCESS  read-only
    STATUS  current
    DESCRIPTION
        "The total number of neighbours in this state (i.e. in an
         adjacency's final state) having transimitted a full sequence 
         of Database Description packets, for this OSPF interface."
    ::= { ospfIntfNbrChangeStatsEntry 6 }

ospfIntfNbrBadRequests OBJECT-TYPE
    SYNTAX  Counter32
    MAX-ACCESS  read-only
    STATUS  current
    DESCRIPTION
        "The total number of Link State Requests which have been received
         for a link state advertisement not contained in the database for
         this interface."
    ::= { ospfIntfNbrChangeStatsEntry 7 }

ospfIntfNbrBadSequence OBJECT-TYPE
    SYNTAX  Counter32
    MAX-ACCESS  read-only
    STATUS  current
    DESCRIPTION
        "The total number of Database Description packets which have been
         received that either 
         a) has an unexpected DD sequence number
         b) Unexpectedly has the init bit set
         c) Has an options field differing from the last Options field
            received in a Database Description packet.
         Any of these conditions indicate that some error has occured during
         adjacency establishment for this interface."
    ::= { ospfIntfNbrChangeStatsEntry 8 }

ospfIntfNbrLoadingDone OBJECT-TYPE
    SYNTAX  Counter32
    MAX-ACCESS  read-only
    STATUS  current
    DESCRIPTION
        "The total number of link state updates received for all 
         out-of-date portions of the database for this OSPF interface."
    ::= { ospfIntfNbrChangeStatsEntry 9 }

ospfIntfNbrN1way OBJECT-TYPE
    SYNTAX  Counter32
    MAX-ACCESS  read-only
    STATUS  current
    DESCRIPTION
        "The total number of Hello packets received from neighbours, in
         which this router is not mentioned for this OSPF interface."
    ::= { ospfIntfNbrChangeStatsEntry 10 }

ospfIntfNbrRstAd OBJECT-TYPE
    SYNTAX  Counter32
    MAX-ACCESS  read-only
    STATUS  current
    DESCRIPTION
        "The sum total number of times the Neighbour adjacency has been reset
         on this interface."
    ::= { ospfIntfNbrChangeStatsEntry 11 }

ospfIntfNbrDown OBJECT-TYPE
    SYNTAX  Counter32
    MAX-ACCESS  read-only
    STATUS  current
    DESCRIPTION
        "The total number of Neighbouring routers down (i.e. in the initial
         state of a neighbour conversation.) for this interface."
    ::= { ospfIntfNbrChangeStatsEntry 12 }

ospfIntfNbrN2way OBJECT-TYPE
    SYNTAX  Counter32
    MAX-ACCESS  read-only
    STATUS  current
    DESCRIPTION
        "The total number of Hello packets received from neighbours, in
         which this router is mentioned for this OSPF interface."
    ::= { ospfIntfNbrChangeStatsEntry 13 }

ospfIntfChangeStats OBJECT-TYPE
    SYNTAX SEQUENCE OF OspfIntfChangeStatsEntry
    MAX-ACCESS not-accessible
    STATUS current
    DESCRIPTION
      "The table of OSPF Interface change Statistics."
    ::= { ospfInterface 3 }

ospfIntfChangeStatsEntry OBJECT-TYPE
    SYNTAX OspfIntfChangeStatsEntry
    MAX-ACCESS not-accessible
    STATUS current
    DESCRIPTION
      "OSPF interface Change statistics."
    INDEX { ospfIntfIndex }
    ::= { ospfIntfChangeStats 1 }

OspfIntfChangeStatsEntry ::= SEQUENCE {
    ospfIntfIndex               Integer32,
    ospfIntfHello               Counter32,
    ospfIntfDown            Counter32,
    ospfIntfLoop            Counter32,
    ospfIntfUnloop      Counter32,
    ospfIntfWaitTimer       Counter32,
    ospfIntfBackup          Counter32,
    ospfIntfNbrChange           Counter32
    }

ospfIntfIndex OBJECT-TYPE
    SYNTAX  Integer32
    MAX-ACCESS  read-only
    STATUS  current
    DESCRIPTION
        "The index of the OSPF Interface for which these statistics apply."
    ::= { ospfIntfChangeStatsEntry 1 }

ospfIntfHello OBJECT-TYPE
    SYNTAX    Counter32
    MAX-ACCESS    read-only
    STATUS    current
    DESCRIPTION
        "The total number of Hello packets sent by this interface."
    ::= { ospfIntfChangeStatsEntry 2 }

ospfIntfDown OBJECT-TYPE
    SYNTAX   Counter32
    MAX-ACCESS   read-only
    STATUS   current
    DESCRIPTION
        "The total number of times the interface was down."
    ::= { ospfIntfChangeStatsEntry 3 }

ospfIntfLoop OBJECT-TYPE
    SYNTAX    Counter32
    MAX-ACCESS    read-only
    STATUS    current
    DESCRIPTION
        "The total number of times the interface was no longer connected to 
         the attatched network."
    ::= { ospfIntfChangeStatsEntry 4 }

ospfIntfUnloop OBJECT-TYPE
    SYNTAX   Counter32
    MAX-ACCESS   read-only
    STATUS   current
    DESCRIPTION
        "The total number of times the interface, connected back to
         the attatched network."
    ::= { ospfIntfChangeStatsEntry 5 }

ospfIntfWaitTimer OBJECT-TYPE
    SYNTAX        Counter32
    MAX-ACCESS        read-only
    STATUS        current
    DESCRIPTION
        "The total number of times the Wait Timer has been fired,
         (indicating the end of the waiting period that is required
          before electing a (Backup) Designated Router) for this 
          OSPF interface."
    ::= { ospfIntfChangeStatsEntry 6 }

ospfIntfBackup OBJECT-TYPE
    SYNTAX     Counter32
    MAX-ACCESS     read-only
    STATUS     current
    DESCRIPTION
        "The total number of Backup Designated Routers on the attatched
         network for this OSPF interface."
    ::= { ospfIntfChangeStatsEntry 7 }

ospfIntfNbrChange OBJECT-TYPE
    SYNTAX     Counter32
    MAX-ACCESS     read-only
    STATUS     current
    DESCRIPTION
        "The total number of changes in the set of bidirectional neighbours
         associated with the interface for this OSPF interface."
    ::= { ospfIntfChangeStatsEntry 8 }

ospfIntfErrorStats OBJECT-TYPE
    SYNTAX SEQUENCE OF OspfIntfErrorStatsEntry
    MAX-ACCESS not-accessible
    STATUS current
    DESCRIPTION
      "The table of OSPF Interface Error Statistics."
    ::= { ospfInterface 4 }

ospfIntfErrorStatsEntry OBJECT-TYPE
    SYNTAX OspfIntfErrorStatsEntry
    MAX-ACCESS not-accessible
    STATUS current
    DESCRIPTION
      "Error Statistics for an OSPF area."
    INDEX { ospfIntfErrIndex }
    ::= { ospfIntfErrorStats 1 }
 
OspfIntfErrorStatsEntry ::= SEQUENCE {
    ospfIntfErrIndex        Integer32,
    ospfIntfErrAuthFailure      Counter32,
    ospfIntfErrNetmaskMismatch  Counter32,
    ospfIntfErrHelloMismatch    Counter32,
    ospfIntfErrDeadMismatch     Counter32,
    ospfIntfErrOptionsMismatch  Counter32,
    ospfIntfErrUnknownNbr       Counter32,
    ospfIntfErrAreaMismatch     Counter32,
    ospfIntfErrInvalidSelfOrigLSA Counter32
    }

ospfIntfErrIndex OBJECT-TYPE
    SYNTAX    Integer32
    MAX-ACCESS    read-only
    STATUS    current
    DESCRIPTION
        "The index of the OSPF Intf for which these statistics apply."
    ::= { ospfIntfErrorStatsEntry 1 }

ospfIntfErrAuthFailure OBJECT-TYPE
    SYNTAX    Counter32
    MAX-ACCESS    read-only
    STATUS    current
    DESCRIPTION
        "The total number of packets received with a wrong password in 
         this area."
    ::= { ospfIntfErrorStatsEntry 2 }

ospfIntfErrNetmaskMismatch OBJECT-TYPE
    SYNTAX    Counter32
    MAX-ACCESS    read-only
    STATUS    current
    DESCRIPTION
        "The total number of packets received with a wrong netmask in 
         this area."
    ::= { ospfIntfErrorStatsEntry 3 }

ospfIntfErrHelloMismatch OBJECT-TYPE
    SYNTAX    Counter32
    MAX-ACCESS    read-only
    STATUS    current
    DESCRIPTION
        "The total number of packets received with a different hello interval
         in this area."
    ::= { ospfIntfErrorStatsEntry 4 }

ospfIntfErrDeadMismatch OBJECT-TYPE
    SYNTAX    Counter32
    MAX-ACCESS    read-only
    STATUS    current
    DESCRIPTION
        "The total number of packets received with a different dead interval
         in this area."
    ::= { ospfIntfErrorStatsEntry 5 }

ospfIntfErrOptionsMismatch OBJECT-TYPE
    SYNTAX    Counter32
    MAX-ACCESS    read-only
    STATUS    current
    DESCRIPTION
        "The total number of packets received with a different options
         in this area."
    ::= { ospfIntfErrorStatsEntry 6 }

ospfIntfErrUnknownNbr OBJECT-TYPE
    SYNTAX    Counter32
    MAX-ACCESS    read-only
    STATUS    current
    DESCRIPTION
        "The total number of packets received from an unknown neighbor
         in this area."
    ::= { ospfIntfErrorStatsEntry 7 }

ospfIntfErrAreaMismatch OBJECT-TYPE
    SYNTAX    Counter32
    MAX-ACCESS    read-only
    STATUS    current
    DESCRIPTION
        "The total number of packets received with a wrong  area."
    ::= { ospfIntfErrorStatsEntry 8 }

ospfIntfErrInvalidSelfOrigLSA OBJECT-TYPE
    SYNTAX   Counter32
    MAX-ACCESS   read-only
    STATUS   current
    DESCRIPTION
        "The total number of packets received with invalid self-orig LSAs."
    ::= { ospfIntfErrorStatsEntry 9 }

-- Ospf General Statistics contains the cumulative stats for all
-- areas / interfaces
ospfCumRxPkts OBJECT-TYPE
    SYNTAX  Counter32
    MAX-ACCESS  read-only
    STATUS  current
    DESCRIPTION
        "The sum total of all OSPF packets received on all OSPF areas
         and interfaces."
    ::= { ospfCumRxTxStats 1 }
 
ospfCumTxPkts OBJECT-TYPE
    SYNTAX  Counter32
    MAX-ACCESS  read-only
    STATUS  current
    DESCRIPTION
        "The sum total of all OSPF packets transmitted on all OSPF areas
         and interfaces."
    ::= { ospfCumRxTxStats 2 }
 
ospfCumRxHello OBJECT-TYPE
    SYNTAX  Counter32 
    MAX-ACCESS  read-only
    STATUS  current
    DESCRIPTION
        "The sum total of all Hello packets received on all OSPF areas
         and interfaces."
    ::= { ospfCumRxTxStats 3 }

ospfCumTxHello OBJECT-TYPE
    SYNTAX  Counter32
    MAX-ACCESS  read-only
    STATUS  current
    DESCRIPTION
        "The sum total of all Hello packets transmitted on all OSPF areas
         and interfaces."
    ::= { ospfCumRxTxStats 4 }
 
ospfCumRxDatabase OBJECT-TYPE
    SYNTAX  Counter32 
    MAX-ACCESS  read-only
    STATUS  current
    DESCRIPTION
        "The sum total of all Database Description packets received on
         all OSPF areas and interfaces."
    ::= { ospfCumRxTxStats 5 }

ospfCumTxDatabase OBJECT-TYPE
    SYNTAX  Counter32
    MAX-ACCESS  read-only
    STATUS  current
    DESCRIPTION
        "The sum total of all Database Description packets transmitted on
         all OSPF areas and interfaces."
    ::= { ospfCumRxTxStats 6 }
 
ospfCumRxlsReqs OBJECT-TYPE
    SYNTAX  Counter32 
    MAX-ACCESS  read-only
    STATUS  current
    DESCRIPTION
        "The sum total of all Link State Request packets received on
         all OSPF areas and interfaces."
    ::= { ospfCumRxTxStats 7 }

ospfCumTxlsReqs OBJECT-TYPE
    SYNTAX  Counter32 
    MAX-ACCESS  read-only
    STATUS  current
    DESCRIPTION
        "The sum total of all Link State Request packets transmitted on
         all OSPF areas and interfaces."
    ::= { ospfCumRxTxStats 8 }

ospfCumRxlsAcks OBJECT-TYPE
    SYNTAX  Counter32
    MAX-ACCESS  read-only
    STATUS  current
    DESCRIPTION
        "The sum total of all Link State Acknowledgement packets received
         on all OSPF areas and interfaces."
    ::= { ospfCumRxTxStats 9 }
 
ospfCumTxlsAcks OBJECT-TYPE
    SYNTAX  Counter32 
    MAX-ACCESS  read-only
    STATUS  current
    DESCRIPTION
        "The sum total of all Link State Acknowledgement packets transmitted
         on all OSPF areas and interfaces."
    ::= { ospfCumRxTxStats 10 }

ospfCumRxlsUpdates OBJECT-TYPE
    SYNTAX  Counter32
    MAX-ACCESS  read-only
    STATUS  current
    DESCRIPTION
        "The sum total of all Link State Update packets received
         on all OSPF areas and interfaces."
    ::= { ospfCumRxTxStats 11 }
 
ospfCumTxlsUpdates OBJECT-TYPE
    SYNTAX  Counter32 
    MAX-ACCESS  read-only
    STATUS  current
    DESCRIPTION
        "The sum total of all Link State Update packets transmitted
         on all OSPF areas and interfaces."
    ::= { ospfCumRxTxStats 12 }

ospfCumNbrhello OBJECT-TYPE
    SYNTAX  Counter32
    MAX-ACCESS  read-only
    STATUS  current
    DESCRIPTION
        "The sum total of all Hello packets received from neighbours
         on all OSPF areas and interfaces."
    ::= { ospfCumNbrChangeStats 1 }

ospfCumNbrStart OBJECT-TYPE
    SYNTAX  Counter32
    MAX-ACCESS  read-only
    STATUS  current
    DESCRIPTION
        "The sum total number of neighbours in this state (i.e. an indication
         that  Hello packets should now be sent to the neighbour at intervals
         of HelloInterval seconds.) across all OSPF areas and interfaces."
    ::= { ospfCumNbrChangeStats 2 }

ospfCumNbrAdjointOk OBJECT-TYPE
    SYNTAX  Counter32
    MAX-ACCESS  read-only
    STATUS  current
    DESCRIPTION
        "The sum total number of decisions to be made (again) as to whether
         an adjacency should be established/maintained with the neighbour
         across all OSPF areas and interfaces."
    ::= { ospfCumNbrChangeStats 3 }

ospfCumNbrNegotiationDone OBJECT-TYPE
    SYNTAX  Counter32
    MAX-ACCESS  read-only
    STATUS  current
    DESCRIPTION
        "The sum total number of neighbours in this state wherein the 
         Master/slave relationship has been negotiated, and sequence
         numbers have been exchanged, across all OSPF areas and 
         interfaces."
    ::= { ospfCumNbrChangeStats 4 }

ospfCumNbrExchangeDone OBJECT-TYPE
    SYNTAX  Counter32
    MAX-ACCESS  read-only
    STATUS  current
    DESCRIPTION
        "The sum total number of neighbours in this state (i.e. in an
         adjacency's final state) having transimitted a full sequence 
         of Database Description packets, across all OSPF areas
         and interfaces."
    ::= { ospfCumNbrChangeStats 5 }

ospfCumNbrBadRequests OBJECT-TYPE
    SYNTAX  Counter32
    MAX-ACCESS  read-only
    STATUS  current
    DESCRIPTION
        "The sum total number of Link State Requests which have been received
         for a link state advertisement not contained in the database across
         all interfaces and OSPF areas."
    ::= { ospfCumNbrChangeStats 6 }

ospfCumNbrBadSequence OBJECT-TYPE
    SYNTAX  Counter32
    MAX-ACCESS  read-only
    STATUS  current
    DESCRIPTION
        "The sum total number of Database Description packets which have been
         received that either 
         a) has an unexpected DD sequence number
         b) Unexpectedly has the init bit set
         c) Has an options field differing from the last Options field
            received in a Database Description packet.
         Any of these conditions indicate that some error has occured during
         adjacency establishment for all OSPF areas and interfaces."
    ::= { ospfCumNbrChangeStats 7 }

ospfCumNbrLoadingDone OBJECT-TYPE
    SYNTAX  Counter32
    MAX-ACCESS  read-only
    STATUS  current
    DESCRIPTION
        "The sum total number of link state updates received for all 
         out-of-date portions of the database across all OSPF areas
         and interfaces."
    ::= { ospfCumNbrChangeStats 8 }

ospfCumNbrN1way OBJECT-TYPE
    SYNTAX  Counter32
    MAX-ACCESS  read-only
    STATUS  current
    DESCRIPTION
        "The sum total number of Hello packets received from neighbours, in
         which this router is not mentioned across all OSPF interfaces
         and areas."
    ::= { ospfCumNbrChangeStats 9 }

ospfCumNbrRstAd OBJECT-TYPE
    SYNTAX  Counter32
    MAX-ACCESS  read-only
    STATUS  current
    DESCRIPTION
        "The sum total number of times the Neighbour adjacency has been reset
         across all OPSF areas and interfaces."
    ::= { ospfCumNbrChangeStats 10 }

ospfCumNbrDown OBJECT-TYPE
    SYNTAX  Counter32
    MAX-ACCESS  read-only
    STATUS  current
    DESCRIPTION
        "The total number of Neighbouring routers down (i.e. in the initial
         state of a neighbour conversation.) across all OSPF areas and 
         interfaces."
    ::= { ospfCumNbrChangeStats 11 }

ospfCumNbrN2way OBJECT-TYPE
    SYNTAX  Counter32
    MAX-ACCESS  read-only
    STATUS  current
    DESCRIPTION
        "The sum total number of Hello packets received from neighbours, in
         which this router is mentioned across all OSPF interfaces
         and areas."
    ::= { ospfCumNbrChangeStats 12 }

ospfCumIntfHello OBJECT-TYPE
    SYNTAX    Counter32
    MAX-ACCESS    read-only
    STATUS    current
    DESCRIPTION
        "The sum total number of Hello packets sent on all interfaces 
         and areas"
    ::= { ospfCumIntfChangeStats 1 }

ospfCumIntfDown OBJECT-TYPE
    SYNTAX   Counter32
    MAX-ACCESS   read-only
    STATUS   current
    DESCRIPTION
        "The sum total number of interfaces down in all OSPF areas."
    ::= { ospfCumIntfChangeStats 2 }

ospfCumIntfLoop OBJECT-TYPE
    SYNTAX    Counter32
    MAX-ACCESS    read-only
    STATUS    current
    DESCRIPTION
        "The sum total of interfaces no longer connected to 
         the attatched network across all OSPF areas and interfaces."
    ::= { ospfCumIntfChangeStats 3 }

ospfCumIntfUnloop OBJECT-TYPE
    SYNTAX   Counter32
    MAX-ACCESS   read-only
    STATUS   current
    DESCRIPTION
        "The sum total number of interfaces, connected to
         the attatched network in all OSPF areas."
    ::= { ospfCumIntfChangeStats 4 }

ospfCumIntfWaitTimer OBJECT-TYPE
    SYNTAX        Counter32
    MAX-ACCESS        read-only
    STATUS        current
    DESCRIPTION
        "The sum total number of times the Wait Timer has been fired,
         (indicating the end of the waiting period that is required
          before electing a (Backup) Designated Router) across all 
          OSPF areas and interfaces."
    ::= { ospfCumIntfChangeStats 5 }

ospfCumIntfBackup OBJECT-TYPE
    SYNTAX     Counter32
    MAX-ACCESS     read-only
    STATUS     current
    DESCRIPTION
        "The sum total number of Backup Designated Routers on the attatched
         network for all OSPF areas and interfaces."
    ::= { ospfCumIntfChangeStats 6 }

ospfCumIntfNbrChange OBJECT-TYPE
    SYNTAX     Counter32
    MAX-ACCESS     read-only
    STATUS     current
    DESCRIPTION
        "The sum total number of changes in the set of bidirectional
         neighbours associated with any interface across all OSPF areas."
    ::= { ospfCumIntfChangeStats 7 }

ospfTmrsKckOffHello OBJECT-TYPE
    SYNTAX    Counter32
    MAX-ACCESS    read-only
    STATUS    current
    DESCRIPTION
        "The sum total number of times the Hello timer has been fired
         (which triggers the send of a Hello packet) across all OPSF 
         areas and interfaces."
    ::= { ospfTimersKickOffStats 1 }

ospfTmrsKckOffRetransmit OBJECT-TYPE
    SYNTAX   Counter32
    MAX-ACCESS   read-only
    STATUS   current
    DESCRIPTION
        "The sum total number of times the Retransmit timer has been
         fired across all OPSF areas and interfaces."
    ::= { ospfTimersKickOffStats 2 }

ospfTmrsKckOffLsaLock OBJECT-TYPE
    SYNTAX    Counter32
    MAX-ACCESS    read-only
    STATUS    current
    DESCRIPTION
        "The sum total number of times the Lsa Lock timer has been 
         fired across all OSPF areas and interfaces."
    ::= { ospfTimersKickOffStats 3 }

ospfTmrsKckOffLsaAck OBJECT-TYPE
    SYNTAX   Counter32
    MAX-ACCESS   read-only
    STATUS   current
    DESCRIPTION
        "The sum total number of times the Lsa Ack timer has been 
         fired across all ospf areas and interfaces."
    ::= { ospfTimersKickOffStats 4 }

ospfTmrsKckOffDbage OBJECT-TYPE
    SYNTAX        Counter32
    MAX-ACCESS        read-only
    STATUS        current
    DESCRIPTION
        "The total number of times the Dbage has been fired."
    ::= { ospfTimersKickOffStats 5 }

ospfTmrsKckOffSummary OBJECT-TYPE
    SYNTAX     Counter32
    MAX-ACCESS     read-only
    STATUS     current
    DESCRIPTION
        "The total number of times the Summary timer has been fired."
    ::= { ospfTimersKickOffStats 6 }

ospfTmrsKckOffAseExport OBJECT-TYPE
    SYNTAX     Counter32
    MAX-ACCESS     read-only
    STATUS     current
    DESCRIPTION
        "The total number of times the ASE Export timer has been fired."
    ::= { ospfTimersKickOffStats 7 }



-- IGMP Snooping statistics
igmpSnoopStats OBJECT-TYPE
  SYNTAX SEQUENCE OF IgmpSnoopStatsEntry
  MAX-ACCESS not-accessible
  STATUS current
   DESCRIPTION
      "Statistics for IGMP Snooping."
    ::= { igmpStats 1 }

igmpSnoopStatsEntry OBJECT-TYPE
    SYNTAX IgmpSnoopStatsEntry
    MAX-ACCESS not-accessible
    STATUS current
    DESCRIPTION
      "Statistics for IGMP Snooping."
    INDEX { igmpSnoopVlanIndex }
    ::= { igmpSnoopStats 1 }
 
IgmpSnoopStatsEntry ::= SEQUENCE {
    igmpSnoopVlanIndex      INTEGER,
    rxIgmpValidPkts             Counter32,
    rxIgmpInvalidPkts           Counter32,
    rxIgmpGenQueries            Counter32,
    rxIgmpGrpSpecificQueries    Counter32,
    rxIgmpLeaves                Counter32,
    rxIgmpDiscardPkts           Counter32,
    rxIgmpReports               Counter32,
    rxIgmpPimHellos             Counter32,
    txIgmpGenQueries            Counter32,
    txIgmpGrpSpecificQueries    Counter32,
    txIgmpReports               Counter32,
    igmpClearVlanStats          INTEGER,
    txIgmpLeaves                         Counter32,
    rxIgmpGroupSourceSpecificQueries     Counter32,
    rxIgmpV3CurrentStateRecords          Counter32,
    rxIgmpV3SourceListChangeRecords      Counter32,
    rxIgmpV3FilterChangeRecords          Counter32
    }

igmpSnoopVlanIndex OBJECT-TYPE
    SYNTAX    INTEGER
    MAX-ACCESS    read-only
    STATUS    current
    DESCRIPTION
        "The index of the VLAN for which these statistics apply."
    ::= { igmpSnoopStatsEntry 1 }

rxIgmpValidPkts OBJECT-TYPE
    SYNTAX    Counter32
    MAX-ACCESS    read-only
    STATUS    current
    DESCRIPTION
        "The total number of valid IGMP packets received 
         on this VLAN." 
    ::= { igmpSnoopStatsEntry 2 }

rxIgmpInvalidPkts OBJECT-TYPE
    SYNTAX    Counter32
    MAX-ACCESS    read-only
    STATUS    current
    DESCRIPTION
        "The total number of invalid IGMP packets received 
         on this VLAN." 
    ::= { igmpSnoopStatsEntry 3 }

rxIgmpGenQueries OBJECT-TYPE
    SYNTAX    Counter32
    MAX-ACCESS    read-only
    STATUS    current
    DESCRIPTION
        "The total number of IGMP General Query packets received
         on this VLAN." 
    ::= { igmpSnoopStatsEntry 4 }

rxIgmpGrpSpecificQueries OBJECT-TYPE
    SYNTAX    Counter32
    MAX-ACCESS    read-only
    STATUS    current
    DESCRIPTION
        "The total number of IGMP Group Specific Query packets received
         on this VLAN." 
    ::= { igmpSnoopStatsEntry 5 }

rxIgmpLeaves OBJECT-TYPE
    SYNTAX    Counter32
    MAX-ACCESS    read-only
    STATUS    current
    DESCRIPTION
        "The total number of IGMP Leave packets received
         on this VLAN." 
    ::= { igmpSnoopStatsEntry 6 }

rxIgmpReports OBJECT-TYPE
    SYNTAX    Counter32
    MAX-ACCESS    read-only
    STATUS    current
    DESCRIPTION
        "The total number of IGMP Report packets received
         on this VLAN." 
    ::= { igmpSnoopStatsEntry 7 }

txIgmpGrpSpecificQueries OBJECT-TYPE
    SYNTAX    Counter32
    MAX-ACCESS    read-only
    STATUS    current
    DESCRIPTION
        "The total number of IGMP Group Specific Query packets
         transmitted on this VLAN." 
    ::= { igmpSnoopStatsEntry 8 }

txIgmpReports OBJECT-TYPE
    SYNTAX    Counter32
    MAX-ACCESS    read-only
    STATUS    current
    DESCRIPTION
        "The total number of IGMP Report packets transmitted
         on this VLAN." 
    ::= { igmpSnoopStatsEntry 9 }

txIgmpLeaves OBJECT-TYPE
    SYNTAX    Counter32
    MAX-ACCESS    read-only
    STATUS    current
    DESCRIPTION
        "The total number of IGMP Leave packets transmitted
         on this VLAN." 
    ::= { igmpSnoopStatsEntry 10 }

rxIgmpGroupSourceSpecificQueries OBJECT-TYPE
    SYNTAX    Counter32
    MAX-ACCESS    read-only
    STATUS    current
    DESCRIPTION
        "The total number of IGMP Group Source Specific (GSSQ) Queries received
         on this VLAN." 
    ::= { igmpSnoopStatsEntry 11 }

rxIgmpV3CurrentStateRecords OBJECT-TYPE
    SYNTAX    Counter32
    MAX-ACCESS    read-only
    STATUS    current
    DESCRIPTION
        "The total number of IGMP Current State Records (CSRs) received
         on this VLAN." 
    ::= { igmpSnoopStatsEntry 12 }

rxIgmpV3SourceListChangeRecords OBJECT-TYPE
    SYNTAX    Counter32
    MAX-ACCESS    read-only
    STATUS    current
    DESCRIPTION
        "The total number of IGMP Source List Change Records (SLCRs) received
         on this VLAN." 
    ::= { igmpSnoopStatsEntry 13 }

rxIgmpV3FilterChangeRecords OBJECT-TYPE
    SYNTAX    Counter32
    MAX-ACCESS    read-only
    STATUS    current
    DESCRIPTION
        "The total number of IGMP Filter Mode Change Records (FMCRs) received
         on this VLAN." 
    ::= { igmpSnoopStatsEntry 14 }

txIgmpGenQueries OBJECT-TYPE
    SYNTAX    Counter32
    MAX-ACCESS    read-only
    STATUS    current
    DESCRIPTION
        "The total number of IGMP General Query packets send
         on this VLAN." 
    ::= { igmpSnoopStatsEntry 16 }

rxIgmpDiscardPkts OBJECT-TYPE
    SYNTAX    Counter32
    MAX-ACCESS    read-only
    STATUS    current
    DESCRIPTION
        "The total number of IGMP packets discarded
         on this VLAN." 
    ::= { igmpSnoopStatsEntry 17 }

rxIgmpPimHellos OBJECT-TYPE
    SYNTAX    Counter32
    MAX-ACCESS    read-only
    STATUS    current
    DESCRIPTION
        "The total number of Pim Hello packets received
         on this VLAN." 
    ::= { igmpSnoopStatsEntry 18 }

igmpClearVlanStats OBJECT-TYPE
    SYNTAX  INTEGER { 
    clear(1),
    ok(2)
    }
    MAX-ACCESS  read-write
    STATUS  current  
    DESCRIPTION
        "Setting this to clear(1) results in clearing the statistics for this
         snooping VLAN." 
    ::= { igmpSnoopStatsEntry 19 }

igmpClearAllStats OBJECT-TYPE
    SYNTAX  INTEGER { 
    clear(1),
    ok(2)
    }
    MAX-ACCESS  read-write
    STATUS  current  
    DESCRIPTION
        "Setting this to clear(1) results in clearing the IGMP statistics." 
    ::= { igmpStats 2 }

igmpStatsTotalIgmpGroups OBJECT-TYPE 
    SYNTAX  Counter32 
    MAX-ACCESS  read-only
    STATUS  current 
    DESCRIPTION 
        "The total number of IGMP groups."
    ::= { igmpStats 3 }

igmpStatsTotalIpmcGroups OBJECT-TYPE 
    SYNTAX  Counter32 
    MAX-ACCESS  read-only
    STATUS  current 
    DESCRIPTION 
        "The total number of IPMC groups."
    ::= { igmpStats 4 }





ipv6InReceives OBJECT-TYPE
    SYNTAX  Counter32
    MAX-ACCESS  read-only
    STATUS  current
    DESCRIPTION
        "The total number of input datagrams received from
         interfaces, including those received in error."
    ::= { ipv6Stats 1 }
    
ipv6InMcasts OBJECT-TYPE
    SYNTAX  Counter32
    MAX-ACCESS  read-only
    STATUS  current
    DESCRIPTION
        "The total number of multicast packets received from
         interfaces, including those received in error."
    ::= { ipv6Stats 2 }

ipv6InDelivers OBJECT-TYPE
    SYNTAX  Counter32
    MAX-ACCESS  read-only
    STATUS  current
    DESCRIPTION
        "Total datagrams given to upper layer - ICMP/UDP"
    ::= { ipv6Stats 3 }

ipv6InDiscards OBJECT-TYPE
    SYNTAX  Counter32
    MAX-ACCESS  read-only
    STATUS  current
    DESCRIPTION
        "Total datagrams discarded despite no errors"
    ::= { ipv6Stats 4 }

ipv6InHdrerrs OBJECT-TYPE
    SYNTAX  Counter32
    MAX-ACCESS  read-only
    STATUS  current
    DESCRIPTION
        "Total datagrams with error in IPv6/Option headers"
    ::= { ipv6Stats 5 }

ipv6InAddrerrs OBJECT-TYPE
    SYNTAX  Counter32
    MAX-ACCESS  read-only
    STATUS  current
    DESCRIPTION
        "Total datagrams with error in destination address"
    ::= { ipv6Stats 6 }

ipv6InUnkprots OBJECT-TYPE
    SYNTAX  Counter32
    MAX-ACCESS  read-only
    STATUS  current
    DESCRIPTION
        "Total datagrams with unknown/unsupported protocol"
    ::= { ipv6Stats 7 }

ipv6InTruncs OBJECT-TYPE
    SYNTAX  Counter32
    MAX-ACCESS  read-only
    STATUS  current
    DESCRIPTION
        "Total datagrams with insufficient data"
    ::= { ipv6Stats 8 }

ipv6OutMcasts OBJECT-TYPE
    SYNTAX  Counter32
    MAX-ACCESS  read-only
    STATUS  current
    DESCRIPTION
        "Total sent multicast pkts"
    ::= { ipv6Stats 10 }

ipv6ForwDgrams OBJECT-TYPE
    SYNTAX  Counter32
    MAX-ACCESS  read-only
    STATUS  current
    DESCRIPTION
        "Total datagrams attempted to be forwarded"
    ::= { ipv6Stats 11 }

ipv6TooBigerrs OBJECT-TYPE
    SYNTAX  Counter32
    MAX-ACCESS  read-only
    STATUS  current
    DESCRIPTION
        "Total datagrams which could not be forwarded
        as their size exceeds (Path) MTU"
    ::= { ipv6Stats 12 }

ipv6OutReqs OBJECT-TYPE
    SYNTAX  Counter32
    MAX-ACCESS  read-only
    STATUS  current
    DESCRIPTION
        "Total datagrams attempted to be sent"
    ::= { ipv6Stats 13 }

ipv6OutDiscards OBJECT-TYPE
    SYNTAX  Counter32
    MAX-ACCESS  read-only
    STATUS  current
    DESCRIPTION
        "Total outgoing Datagrams discarded despite no errors"
    ::= { ipv6Stats 14 }

ipv6OutNorts OBJECT-TYPE
    SYNTAX  Counter32
    MAX-ACCESS  read-only
    STATUS  current
    DESCRIPTION
        "Total datagrams discarded due to no routes"
    ::= { ipv6Stats 15 }

ipv6Reasmreqs OBJECT-TYPE
    SYNTAX  Counter32
    MAX-ACCESS  read-only
    STATUS  current
    DESCRIPTION
        "Total datagrams needing reassembly"
    ::= { ipv6Stats 16 }

ipv6Reasmoks OBJECT-TYPE
    SYNTAX  Counter32
    MAX-ACCESS  read-only
    STATUS  current
    DESCRIPTION
        "Total datagrams successfully reassembled"
    ::= { ipv6Stats 17 }

ipv6Reasmfails OBJECT-TYPE
    SYNTAX  Counter32
    MAX-ACCESS  read-only
    STATUS  current
    DESCRIPTION
        "Total datagrams for witch reassembly failured"
    ::= { ipv6Stats 18 }

ipv6Fragoks OBJECT-TYPE
    SYNTAX  Counter32
    MAX-ACCESS  read-only
    STATUS  current
    DESCRIPTION
        "Total datagrams successfully fragmented"
    ::= { ipv6Stats 19 }

ipv6Fragfails OBJECT-TYPE
    SYNTAX  Counter32
    MAX-ACCESS  read-only
    STATUS  current
    DESCRIPTION
        "Total datagrams for witch fragmentation failured"
    ::= { ipv6Stats 20 }

ipv6Fragcreates OBJECT-TYPE
    SYNTAX  Counter32
    MAX-ACCESS  read-only
    STATUS  current
    DESCRIPTION
        "Total number of fragments created"
    ::= { ipv6Stats 21 }

ipv6InNsols OBJECT-TYPE
    SYNTAX  Counter32
    MAX-ACCESS  read-only
    STATUS  current
    DESCRIPTION
        "Total number of received Neighbor Solicitations"
    ::= { ipv6Stats 22 }

ipv6InNadvs OBJECT-TYPE
    SYNTAX  Counter32
    MAX-ACCESS  read-only
    STATUS  current
    DESCRIPTION
        "Total number of received Neighbor Advertisements"
    ::= { ipv6Stats 23 }

ipv6InRoutsols OBJECT-TYPE
    SYNTAX  Counter32
    MAX-ACCESS  read-only
    STATUS  current
    DESCRIPTION
        "Total number of received Router Solicitations"
    ::= { ipv6Stats 25 }

ipv6InRoutadvs OBJECT-TYPE
    SYNTAX  Counter32
    MAX-ACCESS  read-only
    STATUS  current
    DESCRIPTION
        "Total number of received Router Advertisements"
    ::= { ipv6Stats 26 }

ipv6InRoutRedirs OBJECT-TYPE
    SYNTAX  Counter32
    MAX-ACCESS  read-only
    STATUS  current
    DESCRIPTION
        "Total number of received Router Redirect messages"
    ::= { ipv6Stats 27 }

ipv6OutNsols OBJECT-TYPE
    SYNTAX  Counter32
    MAX-ACCESS  read-only
    STATUS  current
    DESCRIPTION
        "Total number of sent Neighbor Solicitations"
    ::= { ipv6Stats 28 }

ipv6OutNadvs OBJECT-TYPE
    SYNTAX  Counter32
    MAX-ACCESS  read-only
    STATUS  current
    DESCRIPTION
        "Total number of sent Neighbor Advertisements"
    ::= { ipv6Stats 29 }

ipv6OutRoutadvs OBJECT-TYPE
    SYNTAX  Counter32
    MAX-ACCESS  read-only
    STATUS  current
    DESCRIPTION
        "Total number of sent Router Advertisements"
    ::= { ipv6Stats 30 }

ipv6OutRedirs OBJECT-TYPE
    SYNTAX  Counter32
    MAX-ACCESS  read-only
    STATUS  current
    DESCRIPTION
        "Total number of sent Redirects"
    ::= { ipv6Stats 31 }

ipv6OutRoutSols OBJECT-TYPE
    SYNTAX  Counter32
    MAX-ACCESS  read-only
    STATUS  current
    DESCRIPTION
        "Total number of sent Router Solicitations"
    ::= { ipv6Stats 32 }

-- Please see tIp6If structure: u4RaSchedTime and u4RaSentTime are interface
-- parameters. They are not part of interface statistics (tIp6IfStats stats;).
-- ipv6RaSchedTime OBJECT-TYPE
--     SYNTAX  Counter32
--     MAX-ACCESS  read-only
--     STATUS  current
--     DESCRIPTION
--         "Next multicast Router Advertisement scheduled time"
--     ::= { ipv6Stats 36 }

-- ipv6RaSentTime OBJECT-TYPE
--     SYNTAX  Counter32
--     MAX-ACCESS  read-only
--     STATUS  current
--     DESCRIPTION
--         "Last Router Advertisement sent time"
--     ::= { ipv6Stats 37 }

ipv6icmpInMsgs OBJECT-TYPE
    SYNTAX  Counter32
    MAX-ACCESS  read-only
    STATUS  current
    DESCRIPTION
        "The total number of ICMP messages received."
    ::= { ipv6Stats 39 }

ipv6icmpInErrs OBJECT-TYPE
    SYNTAX  Counter32
    MAX-ACCESS  read-only
    STATUS  current
    DESCRIPTION
        "The total number of ICMP messages attempted to send."
    ::= { ipv6Stats 40 }

ipv6icmpInBadcode OBJECT-TYPE
    SYNTAX  Counter32
    MAX-ACCESS  read-only
    STATUS  current
    DESCRIPTION
        "The total number of ICMP messages in bad code."
    ::= { ipv6Stats 41 }

ipv6icmpInToobig OBJECT-TYPE
    SYNTAX  Counter32
    MAX-ACCESS  read-only
    STATUS  current
    DESCRIPTION
        "The number of ICMP too big messages received."
    ::= { ipv6Stats 42 }

ipv6icmpInDstUnreach OBJECT-TYPE
    SYNTAX  Counter32
    MAX-ACCESS  read-only
    STATUS  current
    DESCRIPTION
        "The number of ICMP Destination Unreachable messages received."
    ::= { ipv6Stats 43 }

ipv6icmpInTmexceeded OBJECT-TYPE
    SYNTAX  Counter32
    MAX-ACCESS  read-only
    STATUS  current
    DESCRIPTION
        "The number of ICMP Time Exceeded messages received."
    ::= { ipv6Stats 44 }

ipv6icmpInParamprob OBJECT-TYPE
    SYNTAX  Counter32
    MAX-ACCESS  read-only
    STATUS  current
    DESCRIPTION
        "The number of ICMP Parameter Problem messages received."
    ::= { ipv6Stats 45 }

ipv6icmpInEchoReq OBJECT-TYPE
    SYNTAX  Counter32
    MAX-ACCESS  read-only
    STATUS  current
    DESCRIPTION
        "The number of ICMP Echo request messages received."
    ::= { ipv6Stats 46 }

ipv6icmpInEchoResp OBJECT-TYPE
    SYNTAX  Counter32
    MAX-ACCESS  read-only
    STATUS  current
    DESCRIPTION
        "The number of ICMP Echo Reply messages received."
    ::= { ipv6Stats 47 }

ipv6icmpOutMsgs OBJECT-TYPE
    SYNTAX  Counter32
    MAX-ACCESS  read-only
    STATUS  current
    DESCRIPTION
        "The total number of ICMP messages which this entity
         attempted to send."
    ::= { ipv6Stats 48 }

ipv6icmpOutErrs OBJECT-TYPE
    SYNTAX  Counter32
    MAX-ACCESS  read-only
    STATUS  current
    DESCRIPTION
        "The number of ICMP messages which this entity did not
         send due to problems discovered within ICMP
         such as a lack of buffers."
    ::= { ipv6Stats 49 }

ipv6icmpOutDstUnreach OBJECT-TYPE
    SYNTAX  Counter32
    MAX-ACCESS  read-only
    STATUS  current
    DESCRIPTION
        "The number of ICMP Destination Unreachable messages sent."
    ::= { ipv6Stats 50 }

ipv6icmpOutToobig OBJECT-TYPE
    SYNTAX  Counter32
    MAX-ACCESS  read-only
    STATUS  current
    DESCRIPTION
        "The number of ICMP too big messages sent."
    ::= { ipv6Stats 51 }

ipv6icmpOutTmexceeded OBJECT-TYPE
    SYNTAX  Counter32
    MAX-ACCESS  read-only
    STATUS  current
    DESCRIPTION
        "The number of ICMP Time Exceeded messages sent."
    ::= { ipv6Stats 52 }

ipv6icmpOutParamprob OBJECT-TYPE
    SYNTAX  Counter32
    MAX-ACCESS  read-only
    STATUS  current
    DESCRIPTION
        "The number of ICMP Parameter Problem messages sent."
    ::= { ipv6Stats 53 }

ipv6icmpOutEchoReq OBJECT-TYPE
    SYNTAX  Counter32
    MAX-ACCESS  read-only
    STATUS  current
    DESCRIPTION
        "The number of ICMP Echo request messages sent."
    ::= { ipv6Stats 54 }

ipv6icmpOutEchoResp OBJECT-TYPE
    SYNTAX  Counter32
    MAX-ACCESS  read-only
    STATUS  current
    DESCRIPTION
        "The number of ICMP Echo Reply messages sent."
    ::= { ipv6Stats 55 }

ipv6icmpInRouterSol OBJECT-TYPE
    SYNTAX  Counter32
    MAX-ACCESS  read-only
    STATUS  current
    DESCRIPTION
        "The number of ICMP router solicitations received."
    ::= { ipv6Stats 56 }

ipv6icmpInRouterAdv OBJECT-TYPE
    SYNTAX  Counter32
    MAX-ACCESS  read-only
    STATUS  current
    DESCRIPTION
        "The number of ICMP router advertisements received."
    ::= { ipv6Stats 57 }

ipv6icmpInNeighSol OBJECT-TYPE
    SYNTAX  Counter32
    MAX-ACCESS  read-only
    STATUS  current
    DESCRIPTION
        "The number of ICMP neighbor solicitations received."
    ::= { ipv6Stats 58 }

ipv6icmpInNeighAdv OBJECT-TYPE
    SYNTAX  Counter32
    MAX-ACCESS  read-only
    STATUS  current
    DESCRIPTION
        "The number of ICMP neighbor advertisements received."
    ::= { ipv6Stats 59 }

ipv6icmpInRedir OBJECT-TYPE
    SYNTAX  Counter32
    MAX-ACCESS  read-only
    STATUS  current
    DESCRIPTION
        "The number of ICMP Redirect messages received."
    ::= { ipv6Stats 60 }

ipv6icmpOutRouterSol OBJECT-TYPE
    SYNTAX  Counter32
    MAX-ACCESS  read-only
    STATUS  current
    DESCRIPTION
        "The number of ICMP router solicitations sent."
    ::= { ipv6Stats 61 }

ipv6icmpOutRouterAdv OBJECT-TYPE
    SYNTAX  Counter32
    MAX-ACCESS  read-only
    STATUS  current
    DESCRIPTION
        "The number of ICMP router advertisements sent."
    ::= { ipv6Stats 62 }

ipv6icmpOutNeighSol OBJECT-TYPE
    SYNTAX  Counter32
    MAX-ACCESS  read-only
    STATUS  current
    DESCRIPTION
        "The number of ICMP neighbor solicitations sent."
    ::= { ipv6Stats 63 }

ipv6icmpOutNeighAdv OBJECT-TYPE
    SYNTAX  Counter32
    MAX-ACCESS  read-only
    STATUS  current
    DESCRIPTION
        "The number of ICMP neighbor advertisements sent."
    ::= { ipv6Stats 64 }

ipv6icmpOutRedir OBJECT-TYPE
    SYNTAX  Counter32
    MAX-ACCESS  read-only
    STATUS  current
    DESCRIPTION
        "The number of ICMP Redirect messages sent."
    ::= { ipv6Stats 65 }

ipv6udpInDgrams OBJECT-TYPE
    SYNTAX  Counter32
    MAX-ACCESS  read-only
    STATUS  current
    DESCRIPTION
        "Total number of UDP received datagrams."
    ::= { ipv6Stats 66 }

ipv6udpInErrs OBJECT-TYPE
    SYNTAX  Counter32
    MAX-ACCESS  read-only
    STATUS  current
    DESCRIPTION
        "Total number of UDP error encountered during
         processing of packet."
    ::= { ipv6Stats 67 }

ipv6udpOutDgrams OBJECT-TYPE
    SYNTAX  Counter32
    MAX-ACCESS  read-only
    STATUS  current
    DESCRIPTION
        "Total number of UDP datagrams passed to IP6 layer."
    ::= { ipv6Stats 68 }

ipv6udpNumPorts OBJECT-TYPE
    SYNTAX  Counter32
    MAX-ACCESS  read-only
    STATUS  current
    DESCRIPTION
        "Total number of UDP ports that are currently open."
    ::= { ipv6Stats 69 }

ipv6icmpInAdminProhib OBJECT-TYPE
    SYNTAX  Counter32
    MAX-ACCESS  read-only
    STATUS  current
    DESCRIPTION
        "The total number of received Destination Unreachable
         ICMP packets."
    ::= { ipv6Stats 70 }

ipv6icmpOutAdminProhib OBJECT-TYPE
    SYNTAX  Counter32
    MAX-ACCESS  read-only
    STATUS  current
    DESCRIPTION
        "The total number of sent Destination Unreachable
         ICMP packets."
    ::= { ipv6Stats 71 }


-- Ospf3 Statistics 

-- Ospf3 Statistics for all interfaces and Ospf3 areas 
ospf3GeneralStats       OBJECT IDENTIFIER ::= { ospf3Stats  1 }
ospf3CumRxTxDisdStats   OBJECT IDENTIFIER ::= { ospf3GeneralStats  1 }
ospf3CumNbrChangeStats  OBJECT IDENTIFIER ::= { ospf3GeneralStats  2 }
ospf3CumIntfChangeStats OBJECT IDENTIFIER ::= { ospf3GeneralStats  3 }
ospf3TimersKickOffStats OBJECT IDENTIFIER ::= { ospf3GeneralStats  4 }

-- Ospf3 Statistics / Area
ospf3Area          OBJECT IDENTIFIER ::= { ospf3Stats  2 }

ospf3AreaRxTxDisdStats OBJECT-TYPE
    SYNTAX SEQUENCE OF Ospf3AreaRxTxDisdStatsEntry
    MAX-ACCESS not-accessible
    STATUS current
    DESCRIPTION
      "The table of Ospf3 Area Rx/Tx Statistics."
    ::= { ospf3Area 1 }

ospf3AreaRxTxDisdStatsEntry OBJECT-TYPE
    SYNTAX Ospf3AreaRxTxDisdStatsEntry
    MAX-ACCESS not-accessible
    STATUS current
    DESCRIPTION
      "Rx Tx packet Statistics about a Ospf3 area."
    INDEX { ospf3AreaRxTxDisdIndex }
    ::= { ospf3AreaRxTxDisdStats 1 }
 
Ospf3AreaRxTxDisdStatsEntry ::= SEQUENCE {
    ospf3AreaRxTxDisdIndex      Integer32,
    ospf3AreaRxPkts             Counter32,
    ospf3AreaTxPkts             Counter32,
    ospf3AreaDisdPkts           Counter32, 
    ospf3AreaRxHello            Counter32,
    ospf3AreaTxHello            Counter32,
    ospf3AreaDisdHello          Counter32,
    ospf3AreaRxDatabase         Counter32,
    ospf3AreaTxDatabase         Counter32,
    ospf3AreaDisdDatabase       Counter32,
    ospf3AreaRxlsReqs           Counter32,
    ospf3AreaTxlsReqs           Counter32,
    ospf3AreaDisdlsReqs         Counter32,
    ospf3AreaRxlsAcks           Counter32,
    ospf3AreaTxlsAcks           Counter32,
    ospf3AreaDisdlsAcks         Counter32,
    ospf3AreaRxlsUpdates        Counter32,
    ospf3AreaTxlsUpdates        Counter32,
    ospf3AreaDisdlsUpdates      Counter32
    }

ospf3AreaRxTxDisdIndex OBJECT-TYPE
    SYNTAX  Integer32
    MAX-ACCESS  read-only
    STATUS  current
    DESCRIPTION
        "The index of the ospf3 Area for which these statistics apply."
    ::= { ospf3AreaRxTxDisdStatsEntry 1 }

ospf3AreaRxPkts OBJECT-TYPE
    SYNTAX  Counter32
    MAX-ACCESS  read-only
    STATUS  current
    DESCRIPTION
        "The total number of Ospf3 packets received in this Ospf3 area."
    ::= { ospf3AreaRxTxDisdStatsEntry 2 }
 
ospf3AreaTxPkts OBJECT-TYPE
    SYNTAX  Counter32
    MAX-ACCESS  read-only
    STATUS  current
    DESCRIPTION
        "The total number of Ospf3 packets transmitted in this Ospf3 area."
    ::= { ospf3AreaRxTxDisdStatsEntry 3 }
    
ospf3AreaDisdPkts OBJECT-TYPE
    SYNTAX  Counter32
    MAX-ACCESS  read-only
    STATUS  current
    DESCRIPTION
        "The total number of Ospf3 packets discaded in this Ospf3 area."
    ::= { ospf3AreaRxTxDisdStatsEntry 4 }
 
ospf3AreaRxHello OBJECT-TYPE
    SYNTAX  Counter32 
    MAX-ACCESS  read-only
    STATUS  current
    DESCRIPTION
        "The total number of Hello packets received in this Ospf3 area."
    ::= { ospf3AreaRxTxDisdStatsEntry 5 }

ospf3AreaTxHello OBJECT-TYPE
    SYNTAX  Counter32
    MAX-ACCESS  read-only
    STATUS  current
    DESCRIPTION
        "The total number of Hello packets transmitted in this Ospf3
         area."
    ::= { ospf3AreaRxTxDisdStatsEntry 6 }
    
ospf3AreaDisdHello OBJECT-TYPE
    SYNTAX  Counter32
    MAX-ACCESS  read-only
    STATUS  current
    DESCRIPTION
        "The total number of Hello packets discaded in this Ospf3
         area."
    ::= { ospf3AreaRxTxDisdStatsEntry 7 }
 
ospf3AreaRxDatabase OBJECT-TYPE
    SYNTAX  Counter32 
    MAX-ACCESS  read-only
    STATUS  current
    DESCRIPTION
        "The total number of Database Description packets transmitted 
         for this Ospf3 area."
    ::= { ospf3AreaRxTxDisdStatsEntry 8 }

ospf3AreaTxDatabase OBJECT-TYPE
    SYNTAX  Counter32
    MAX-ACCESS  read-only
    STATUS  current
    DESCRIPTION
        "The total number of Database Description packets transmitted 
         for this Ospf3 area."
    ::= { ospf3AreaRxTxDisdStatsEntry 9 }
    
ospf3AreaDisdDatabase OBJECT-TYPE
    SYNTAX  Counter32
    MAX-ACCESS  read-only
    STATUS  current
    DESCRIPTION
        "The total number of Database Description packets discarded 
         for this Ospf3 area."
    ::= { ospf3AreaRxTxDisdStatsEntry 10 }
 
 
ospf3AreaRxlsReqs OBJECT-TYPE
    SYNTAX  Counter32 
    MAX-ACCESS  read-only
    STATUS  current
    DESCRIPTION
        "The total number of Link State Request packets received for 
         this Ospf3 area."
    ::= { ospf3AreaRxTxDisdStatsEntry 11 }

ospf3AreaTxlsReqs OBJECT-TYPE
    SYNTAX  Counter32 
    MAX-ACCESS  read-only
    STATUS  current
    DESCRIPTION
        "The total number of Link State Request packets transmitted for 
         this Ospf3 area."
    ::= { ospf3AreaRxTxDisdStatsEntry 12 }
    
ospf3AreaDisdlsReqs OBJECT-TYPE
    SYNTAX  Counter32 
    MAX-ACCESS  read-only
    STATUS  current
    DESCRIPTION
        "The total number of Link State Request packets discarded for 
         this Ospf3 area."
    ::= { ospf3AreaRxTxDisdStatsEntry 13 }

ospf3AreaRxlsAcks OBJECT-TYPE
    SYNTAX  Counter32
    MAX-ACCESS  read-only
    STATUS  current
    DESCRIPTION
        "The total number of Link State Acknowledgement packets received for 
         this Ospf3 area."
    ::= { ospf3AreaRxTxDisdStatsEntry 14 }
 
ospf3AreaTxlsAcks OBJECT-TYPE
    SYNTAX  Counter32 
    MAX-ACCESS  read-only
    STATUS  current
    DESCRIPTION
        "The total number of Link State Acknowledgement packets transmitted
         for this Ospf3 area."
    ::= { ospf3AreaRxTxDisdStatsEntry 15 }
    
ospf3AreaDisdlsAcks OBJECT-TYPE
    SYNTAX  Counter32 
    MAX-ACCESS  read-only
    STATUS  current
    DESCRIPTION
        "The total number of Link State Acknowledgement packets discarded
         for this Ospf3 area."
    ::= { ospf3AreaRxTxDisdStatsEntry 16 }

ospf3AreaRxlsUpdates OBJECT-TYPE
    SYNTAX  Counter32
    MAX-ACCESS  read-only
    STATUS  current
    DESCRIPTION
        "The total number of Link State Update packets received for 
         this Ospf3 area."
    ::= { ospf3AreaRxTxDisdStatsEntry 17 }
 
ospf3AreaTxlsUpdates OBJECT-TYPE
    SYNTAX  Counter32 
    MAX-ACCESS  read-only
    STATUS  current
    DESCRIPTION
        "The total number of Link State Update packets transmitted for 
         this Ospf3 area."
    ::= { ospf3AreaRxTxDisdStatsEntry 18 }
    
ospf3AreaDisdlsUpdates OBJECT-TYPE
    SYNTAX  Counter32 
    MAX-ACCESS  read-only
    STATUS  current
    DESCRIPTION
        "The total number of Link State Update packets discarded for 
         this Ospf3 area."
    ::= { ospf3AreaRxTxDisdStatsEntry 19 }

ospf3AreaNbrChangeStats OBJECT-TYPE
    SYNTAX SEQUENCE OF Ospf3AreaNbrChangeStatsEntry
    MAX-ACCESS not-accessible
    STATUS current
    DESCRIPTION
      "The table of Ospf3 Neighbor change Statistics."
    ::= { ospf3Area 2 }

ospf3AreaNbrChangeStatsEntry OBJECT-TYPE
    SYNTAX Ospf3AreaNbrChangeStatsEntry
    MAX-ACCESS not-accessible
    STATUS current
    DESCRIPTION
      "Ospf3 Neighbor Change statistics."
    INDEX { ospf3AreaNbrIndex }
    ::= { ospf3AreaNbrChangeStats 1 }

Ospf3AreaNbrChangeStatsEntry ::= SEQUENCE {
    ospf3AreaNbrIndex           Integer32,
    ospf3AreaNbrDown            Counter32,
    ospf3AreaNbrAttempt     Counter32,
    ospf3AreaNbrInit            Counter32,
    ospf3AreaNbrN2way           Counter32,
    ospf3AreaNbrExStart         Counter32,
    ospf3AreaNbrExchange        Counter32,
    ospf3AreaNbrLoading         Counter32,
    ospf3AreaNbrFull        Counter32,
    ospf3AreaNbrAllEvents       Counter32
    }

ospf3AreaNbrIndex OBJECT-TYPE
    SYNTAX  Integer32
    MAX-ACCESS  read-only
    STATUS  current
    DESCRIPTION
        "The index of the Ospf3 Area for which these statistics apply."
    ::= { ospf3AreaNbrChangeStatsEntry 1 }

ospf3AreaNbrDown OBJECT-TYPE
    SYNTAX  Counter32
    MAX-ACCESS  read-only
    STATUS  current
    DESCRIPTION
        "The total number of times neighbors now existing on this area
        have changed into DOWN state."
    ::= { ospf3AreaNbrChangeStatsEntry 2 }

ospf3AreaNbrAttempt OBJECT-TYPE
    SYNTAX  Counter32
    MAX-ACCESS  read-only
    STATUS  current
    DESCRIPTION
        "The total number of times neighbors now existing on this area
        have changed into ATTEMPT state."
    ::= { ospf3AreaNbrChangeStatsEntry  3 }

ospf3AreaNbrInit OBJECT-TYPE
    SYNTAX  Counter32
    MAX-ACCESS  read-only
    STATUS  current
    DESCRIPTION
        "The total number of times neighbors now existing on this area
        have changed into INIT state."
    ::= { ospf3AreaNbrChangeStatsEntry 4 }

ospf3AreaNbrN2way OBJECT-TYPE
    SYNTAX  Counter32
    MAX-ACCESS  read-only
    STATUS  current
    DESCRIPTION
        "The total number of times neighbors now existing on this area
        have changed into 2WAY state."
    ::= { ospf3AreaNbrChangeStatsEntry 5 }

ospf3AreaNbrExStart OBJECT-TYPE
    SYNTAX  Counter32
    MAX-ACCESS  read-only
    STATUS  current
    DESCRIPTION
        "The total number of times neighbors now existing on this area
        have changed into EXSTART state."
    ::= { ospf3AreaNbrChangeStatsEntry 6 }

ospf3AreaNbrExchange OBJECT-TYPE
    SYNTAX  Counter32
    MAX-ACCESS  read-only
    STATUS  current
    DESCRIPTION
        "The total number of times neighbors now existing on this area
        have changed into EXCHANGE state."
    ::= { ospf3AreaNbrChangeStatsEntry 7 }

ospf3AreaNbrLoading OBJECT-TYPE
    SYNTAX  Counter32
    MAX-ACCESS  read-only
    STATUS  current
    DESCRIPTION
        "The total number of times neighbors now existing on this area
        have changed into LOADING state."
    ::= { ospf3AreaNbrChangeStatsEntry 8 }

ospf3AreaNbrFull OBJECT-TYPE
    SYNTAX  Counter32
    MAX-ACCESS  read-only
    STATUS  current
    DESCRIPTION
        "The total number of times neighbors now existing on this area
        have changed into FULL state."
    ::= { ospf3AreaNbrChangeStatsEntry 9 }

ospf3AreaNbrAllEvents OBJECT-TYPE
    SYNTAX  Counter32
    MAX-ACCESS  read-only
    STATUS  current
    DESCRIPTION
        "The total number of times neighbors now existing on this area
        have changed state or an error had occured."
    ::= { ospf3AreaNbrChangeStatsEntry 10 }
    
ospf3AreaIntfChangeStats OBJECT-TYPE
    SYNTAX SEQUENCE OF Ospf3AreaIntfChangeStatsEntry
    MAX-ACCESS not-accessible
    STATUS current
    DESCRIPTION
      "The table of Ospf3 Interface change Statistics."
    ::= { ospf3Area 3 }


ospf3AreaIntfChangeStatsEntry OBJECT-TYPE
    SYNTAX Ospf3AreaIntfChangeStatsEntry
    MAX-ACCESS not-accessible
    STATUS current
    DESCRIPTION
      "Ospf3 interface Change statistics."
    INDEX { ospf3AreaIntfIndex }
    ::= { ospf3AreaIntfChangeStats 1 }

Ospf3AreaIntfChangeStatsEntry ::= SEQUENCE {
    ospf3AreaIntfIndex              Integer32,
    ospf3AreaIntfDown               Counter32,
    ospf3AreaIntfLoop               Counter32,
    ospf3AreaIntfWaiting        Counter32,
    ospf3AreaIntfPtop               Counter32,
    ospf3AreaIntfDr                 Counter32,
    ospf3AreaIntfBackup             Counter32,
    ospf3AreaIntfDrOther            Counter32,
    ospf3AreaIntfAllEvents          Counter32
    }

ospf3AreaIntfIndex OBJECT-TYPE
    SYNTAX  Integer32
    MAX-ACCESS  read-only
    STATUS  current
    DESCRIPTION
        "The index of the Ospf3 Interface for which these statistics apply."
    ::= { ospf3AreaIntfChangeStatsEntry 1 }

ospf3AreaIntfDown OBJECT-TYPE
    SYNTAX   Counter32
    MAX-ACCESS   read-only
    STATUS   current
    DESCRIPTION
        "The total number of changes into the DOWN State of the interfaces
         associated with this OSPF area."
    ::= { ospf3AreaIntfChangeStatsEntry 2 }

ospf3AreaIntfLoop OBJECT-TYPE
    SYNTAX    Counter32
    MAX-ACCESS    read-only
    STATUS    current
    DESCRIPTION
        "The total number of changes into the LOOP State of the interfaces
         associated with this OSPF area."
    ::= { ospf3AreaIntfChangeStatsEntry 3 }

ospf3AreaIntfWaiting OBJECT-TYPE
    SYNTAX        Counter32
    MAX-ACCESS        read-only
    STATUS        current
    DESCRIPTION
        "The total number of changes into the WAITING State of the interfaces
         associated with this OSPF area."
    ::= { ospf3AreaIntfChangeStatsEntry 4 }
    
ospf3AreaIntfPtop OBJECT-TYPE
    SYNTAX        Counter32
    MAX-ACCESS        read-only
    STATUS        current
    DESCRIPTION
        "The total number of changes into the PTOP State of the interfaces
         associated with this OSPF area."
    ::= { ospf3AreaIntfChangeStatsEntry 5 }

ospf3AreaIntfDr OBJECT-TYPE
    SYNTAX        Counter32
    MAX-ACCESS        read-only
    STATUS        current
    DESCRIPTION
        "The total number of changes into the DR State of the interfaces
         associated with this OSPF area."
    ::= { ospf3AreaIntfChangeStatsEntry 6 }    

ospf3AreaIntfBackup OBJECT-TYPE
    SYNTAX     Counter32
    MAX-ACCESS     read-only
    STATUS     current
    DESCRIPTION
        "The total number of changes into the BACKUP State of the interfaces
         associated with this OSPF area."
    ::= { ospf3AreaIntfChangeStatsEntry 7 }

ospf3AreaIntfDrOther OBJECT-TYPE
    SYNTAX     Counter32
    MAX-ACCESS     read-only
    STATUS     current
    DESCRIPTION
        "The total number of changes into the DROTHER State of the interfaces
         associated with this OSPF area."
    ::= { ospf3AreaIntfChangeStatsEntry 8 }
    
ospf3AreaIntfAllEvents OBJECT-TYPE
    SYNTAX     Counter32
    MAX-ACCESS     read-only
    STATUS     current
    DESCRIPTION
        "The total number of State changes of the interfaces
         associated with this OSPF area"
    ::= { ospf3AreaIntfChangeStatsEntry 9 }

ospf3AreaErrorStats OBJECT-TYPE
    SYNTAX SEQUENCE OF Ospf3AreaErrorStatsEntry
    MAX-ACCESS not-accessible
    STATUS current
    DESCRIPTION
      "The table of Ospf3 Interface Error Statistics."
    ::= { ospf3Area 4 }

ospf3AreaErrorStatsEntry OBJECT-TYPE
    SYNTAX Ospf3AreaErrorStatsEntry
    MAX-ACCESS not-accessible
    STATUS current
    DESCRIPTION
      "Error Statistics for an Ospf3 area."
    INDEX { ospf3AreaErrIndex }
    ::= { ospf3AreaErrorStats 1 }
 
Ospf3AreaErrorStatsEntry ::= SEQUENCE {
    ospf3AreaErrIndex              Integer32,
    ospf3AreaErrRxOnPasv           Counter32,
    ospf3AreaErrRxOspfOff          Counter32,
    ospf3AreaErrRxOnNotup          Counter32,
    ospf3AreaErrRxVerMismatch      Counter32,
    ospf3AreaErrRxZeroRTRID        Counter32,
    ospf3AreaErrRxSameRTRID        Counter32,
    ospf3AreaErrRxMismatchInstID   Counter32,
    ospf3AreaErrBadAreaID          Counter32,
    ospf3AreaErrBadDestAddr        Counter32,
    ospf3AreaErrBadChecksum        Counter32,
    ospf3AreaErrBadNeighbour       Counter32,
    ospf3AreaErrBadPktType         Counter32,
    ospf3AreaErrHelloMismatch      Counter32,
    ospf3AreaErrOptionsMismatch    Counter32,
    ospf3AreaErrDeadMismatch       Counter32,
    ospf3AreaErrHelloNoNbr         Counter32
    }

ospf3AreaErrIndex OBJECT-TYPE
    SYNTAX    Integer32
    MAX-ACCESS    read-only
    STATUS    current
    DESCRIPTION
        "The index of the Ospf3 Area for which these statistics apply."
    ::= { ospf3AreaErrorStatsEntry 1 }

ospf3AreaErrRxOnPasv  OBJECT-TYPE
    SYNTAX    Counter32
    MAX-ACCESS    read-only
    STATUS    current
    DESCRIPTION
        "The total number of packets received by all of the interfaces in this area  that are
         received on a passive interface."
    ::= { ospf3AreaErrorStatsEntry 2 }

ospf3AreaErrRxOspfOff OBJECT-TYPE
    SYNTAX    Counter32
    MAX-ACCESS    read-only
    STATUS    current
    DESCRIPTION
        "The total number of packets received by all of the interfaces in this area  that are
         received while OSPF was disabled."
    ::= { ospf3AreaErrorStatsEntry 3 }

ospf3AreaErrRxOnNotup OBJECT-TYPE
    SYNTAX    Counter32
    MAX-ACCESS    read-only
    STATUS    current
    DESCRIPTION
        "The total number of packets received by all of the interfaces in this area  that are
         received while the interface was disabled."
    ::= { ospf3AreaErrorStatsEntry 4 }
    
ospf3AreaErrRxVerMismatch OBJECT-TYPE
    SYNTAX    Counter32
    MAX-ACCESS    read-only
    STATUS    current
    DESCRIPTION
        "The total number of packets received by all of the interfaces in this area  that have
         an OSPF version number not equal to the one of the interface."
    ::= { ospf3AreaErrorStatsEntry 5 }
    
ospf3AreaErrRxZeroRTRID OBJECT-TYPE
    SYNTAX    Counter32
    MAX-ACCESS    read-only
    STATUS    current
    DESCRIPTION
        "The total number of packets received by all of the interfaces in this area  that have
         a RouterID of 0."
    ::= { ospf3AreaErrorStatsEntry 6 }
    
ospf3AreaErrRxSameRTRID OBJECT-TYPE
    SYNTAX    Counter32
    MAX-ACCESS    read-only
    STATUS    current
    DESCRIPTION
        "The total number of packets received by all of the interfaces in this area  that have
         the same RouterID as this Router."
    ::= { ospf3AreaErrorStatsEntry 7 }
    
ospf3AreaErrRxMismatchInstID OBJECT-TYPE
    SYNTAX    Counter32
    MAX-ACCESS    read-only
    STATUS    current
    DESCRIPTION
        "The total number of packets received by all of the interfaces in this area  that have
         an instance number not equal to the one of the interface."
    ::= { ospf3AreaErrorStatsEntry 8 }
       
ospf3AreaErrBadAreaID OBJECT-TYPE
    SYNTAX    Counter32
    MAX-ACCESS    read-only
    STATUS    current
    DESCRIPTION
        "The total number of packets received by all of the interfaces in this area  that have
         an area number not equal to the one of the area of the interface."
    ::= { ospf3AreaErrorStatsEntry 9 }

ospf3AreaErrBadDestAddr OBJECT-TYPE
    SYNTAX    Counter32
    MAX-ACCESS    read-only
    STATUS    current
    DESCRIPTION
        "The total number of packets discarded by all of the interfaces in this area  because of
         a destination address mismatch."
    ::= { ospf3AreaErrorStatsEntry 10 }

ospf3AreaErrBadChecksum OBJECT-TYPE
    SYNTAX    Counter32
    MAX-ACCESS    read-only
    STATUS    current
    DESCRIPTION
        "The total number of packets discarded by all of the interfaces in this area  because of
         a bad checksum."
    ::= { ospf3AreaErrorStatsEntry 11 }

ospf3AreaErrBadNeighbour OBJECT-TYPE
    SYNTAX    Counter32
    MAX-ACCESS    read-only
    STATUS    current
    DESCRIPTION
        "The total number of packets discarded by all of the interfaces in this area  because
         they could not be associated with any neighbor."
    ::= { ospf3AreaErrorStatsEntry 12 }

ospf3AreaErrBadPktType OBJECT-TYPE
    SYNTAX    Counter32
    MAX-ACCESS    read-only
    STATUS    current
    DESCRIPTION
        "The total number of packets discarded by all of the interfaces in this area  because
         the packet type was not recognized."
    ::= { ospf3AreaErrorStatsEntry 13 }

ospf3AreaErrHelloMismatch OBJECT-TYPE
    SYNTAX    Counter32
    MAX-ACCESS    read-only
    STATUS    current
    DESCRIPTION
        "The total number of packets received with a different hello interval
         by all of the interfaces in this area ."
    ::= { ospf3AreaErrorStatsEntry 14 }

ospf3AreaErrOptionsMismatch OBJECT-TYPE
    SYNTAX    Counter32
    MAX-ACCESS    read-only
    STATUS    current
    DESCRIPTION
        "The total number of packets received with a different options
         by all of the interfaces in this area ."
    ::= { ospf3AreaErrorStatsEntry 15 }

ospf3AreaErrDeadMismatch OBJECT-TYPE
    SYNTAX    Counter32
    MAX-ACCESS    read-only
    STATUS    current
    DESCRIPTION
        "The total number of packets received with a different dead interval
         in this area."
    ::= { ospf3AreaErrorStatsEntry 16 }
    
ospf3AreaErrHelloNoNbr OBJECT-TYPE
    SYNTAX    Counter32
    MAX-ACCESS    read-only
    STATUS    current
    DESCRIPTION
        "The total number of packets received from an unknown neighbor
         when all of the interfaces in this area  has a Network Type of NBMA or PTOMP."
    ::= { ospf3AreaErrorStatsEntry 17 }

-- Ospf3 Statistics / Interface
ospf3Interface         OBJECT IDENTIFIER ::= { ospf3Stats  3 }


ospf3IntfRxTxDisdStats OBJECT-TYPE
    SYNTAX SEQUENCE OF Ospf3IntfRxTxDisdStatsEntry
    MAX-ACCESS not-accessible
    STATUS current
    DESCRIPTION
      "The table of Ospf3 Intf Rx/Tx Statistics."
    ::= { ospf3Interface 1 }

ospf3IntfRxTxDisdStatsEntry OBJECT-TYPE
    SYNTAX Ospf3IntfRxTxDisdStatsEntry
    MAX-ACCESS not-accessible
    STATUS current
    DESCRIPTION
      "Rx Tx packet Statistics about a Ospf3 area."
    INDEX { ospf3IntfRxTxDisdIndex }
    ::= { ospf3IntfRxTxDisdStats 1 }
 
Ospf3IntfRxTxDisdStatsEntry ::= SEQUENCE {
    ospf3IntfRxTxDisdIndex      Integer32,
    ospf3IntfRxPkts             Counter32,
    ospf3IntfTxPkts             Counter32,
    ospf3IntfDisdPkts           Counter32, 
    ospf3IntfRxHello            Counter32,
    ospf3IntfTxHello            Counter32,
    ospf3IntfDisdHello          Counter32,
    ospf3IntfRxDatabase         Counter32,
    ospf3IntfTxDatabase         Counter32,
    ospf3IntfDisdDatabase       Counter32,
    ospf3IntfRxlsReqs           Counter32,
    ospf3IntfTxlsReqs           Counter32,
    ospf3IntfDisdlsReqs         Counter32,
    ospf3IntfRxlsAcks           Counter32,
    ospf3IntfTxlsAcks           Counter32,
    ospf3IntfDisdlsAcks         Counter32,
    ospf3IntfRxlsUpdates        Counter32,
    ospf3IntfTxlsUpdates        Counter32,
    ospf3IntfDisdlsUpdates      Counter32
    }

ospf3IntfRxTxDisdIndex OBJECT-TYPE
    SYNTAX  Integer32
    MAX-ACCESS  read-only
    STATUS  current
    DESCRIPTION
        "The index of the ospf3 Intf for which these statistics apply."
    ::= { ospf3IntfRxTxDisdStatsEntry 1 }

ospf3IntfRxPkts OBJECT-TYPE
    SYNTAX  Counter32
    MAX-ACCESS  read-only
    STATUS  current
    DESCRIPTION
        "The total number of Ospf3 packets received on this Ospf3 interface."
    ::= { ospf3IntfRxTxDisdStatsEntry 2 }
 
ospf3IntfTxPkts OBJECT-TYPE
    SYNTAX  Counter32
    MAX-ACCESS  read-only
    STATUS  current
    DESCRIPTION
        "The total number of Ospf3 packets transmitted on this Ospf3 interface."
    ::= { ospf3IntfRxTxDisdStatsEntry 3 }
    
ospf3IntfDisdPkts OBJECT-TYPE
    SYNTAX  Counter32
    MAX-ACCESS  read-only
    STATUS  current
    DESCRIPTION
        "The total number of Ospf3 packets discaded on this Ospf3 interface."
    ::= { ospf3IntfRxTxDisdStatsEntry 4 }
 
ospf3IntfRxHello OBJECT-TYPE
    SYNTAX  Counter32 
    MAX-ACCESS  read-only
    STATUS  current
    DESCRIPTION
        "The total number of Hello packets received on this Ospf3 interface."
    ::= { ospf3IntfRxTxDisdStatsEntry 5 }

ospf3IntfTxHello OBJECT-TYPE
    SYNTAX  Counter32
    MAX-ACCESS  read-only
    STATUS  current
    DESCRIPTION
        "The total number of Hello packets transmitted on this Ospf3
         interface."
    ::= { ospf3IntfRxTxDisdStatsEntry 6 }
    
ospf3IntfDisdHello OBJECT-TYPE
    SYNTAX  Counter32
    MAX-ACCESS  read-only
    STATUS  current
    DESCRIPTION
        "The total number of Hello packets discaded in this Ospf3
         interface."
    ::= { ospf3IntfRxTxDisdStatsEntry 7 }
 
ospf3IntfRxDatabase OBJECT-TYPE
    SYNTAX  Counter32 
    MAX-ACCESS  read-only
    STATUS  current
    DESCRIPTION
        "The total number of Database Description packets transmitted 
         for this Ospf3 interface."
    ::= { ospf3IntfRxTxDisdStatsEntry 8 }

ospf3IntfTxDatabase OBJECT-TYPE
    SYNTAX  Counter32
    MAX-ACCESS  read-only
    STATUS  current
    DESCRIPTION
        "The total number of Database Description packets transmitted 
         for this Ospf3 interface."
    ::= { ospf3IntfRxTxDisdStatsEntry 9 }
    
ospf3IntfDisdDatabase OBJECT-TYPE
    SYNTAX  Counter32
    MAX-ACCESS  read-only
    STATUS  current
    DESCRIPTION
        "The total number of Database Description packets discarded 
         for this Ospf3 interface."
    ::= { ospf3IntfRxTxDisdStatsEntry 10 }
 
 
ospf3IntfRxlsReqs OBJECT-TYPE
    SYNTAX  Counter32 
    MAX-ACCESS  read-only
    STATUS  current
    DESCRIPTION
        "The total number of Link State Request packets received for 
         this Ospf3 interface."
    ::= { ospf3IntfRxTxDisdStatsEntry 11 }

ospf3IntfTxlsReqs OBJECT-TYPE
    SYNTAX  Counter32 
    MAX-ACCESS  read-only
    STATUS  current
    DESCRIPTION
        "The total number of Link State Request packets transmitted for 
         this Ospf3 interface."
    ::= { ospf3IntfRxTxDisdStatsEntry 12 }
    
ospf3IntfDisdlsReqs OBJECT-TYPE
    SYNTAX  Counter32 
    MAX-ACCESS  read-only
    STATUS  current
    DESCRIPTION
        "The total number of Link State Request packets discarded for 
         this Ospf3 interface."
    ::= { ospf3IntfRxTxDisdStatsEntry 13 }

ospf3IntfRxlsAcks OBJECT-TYPE
    SYNTAX  Counter32
    MAX-ACCESS  read-only
    STATUS  current
    DESCRIPTION
        "The total number of Link State Acknowledgement packets received for 
         this Ospf3 interface."
    ::= { ospf3IntfRxTxDisdStatsEntry 14 }
 
ospf3IntfTxlsAcks OBJECT-TYPE
    SYNTAX  Counter32 
    MAX-ACCESS  read-only
    STATUS  current
    DESCRIPTION
        "The total number of Link State Acknowledgement packets transmitted
         for this Ospf3 interface."
    ::= { ospf3IntfRxTxDisdStatsEntry 15 }
    
ospf3IntfDisdlsAcks OBJECT-TYPE
    SYNTAX  Counter32 
    MAX-ACCESS  read-only
    STATUS  current
    DESCRIPTION
        "The total number of Link State Acknowledgement packets discarded
         for this Ospf3 interface."
    ::= { ospf3IntfRxTxDisdStatsEntry 16 }

ospf3IntfRxlsUpdates OBJECT-TYPE
    SYNTAX  Counter32
    MAX-ACCESS  read-only
    STATUS  current
    DESCRIPTION
        "The total number of Link State Update packets received for 
         this Ospf3 interface."
    ::= { ospf3IntfRxTxDisdStatsEntry 17 }
 
ospf3IntfTxlsUpdates OBJECT-TYPE
    SYNTAX  Counter32 
    MAX-ACCESS  read-only
    STATUS  current
    DESCRIPTION
        "The total number of Link State Update packets transmitted for 
         this Ospf3 interface."
    ::= { ospf3IntfRxTxDisdStatsEntry 18 }
    
ospf3IntfDisdlsUpdates OBJECT-TYPE
    SYNTAX  Counter32 
    MAX-ACCESS  read-only
    STATUS  current
    DESCRIPTION
        "The total number of Link State Update packets discarded for 
         this Ospf3 interface."
    ::= { ospf3IntfRxTxDisdStatsEntry 19 }

ospf3IntfNbrChangeStats OBJECT-TYPE
    SYNTAX SEQUENCE OF Ospf3IntfNbrChangeStatsEntry
    MAX-ACCESS not-accessible
    STATUS current
    DESCRIPTION
      "The table of Ospf3 Interface Neighbour change Statistics."
    ::= { ospf3Interface 2 }

ospf3IntfNbrChangeStatsEntry OBJECT-TYPE
    SYNTAX Ospf3IntfNbrChangeStatsEntry
    MAX-ACCESS not-accessible
    STATUS current
    DESCRIPTION
      "Ospf3 interface Neighbour Change statistics."
    INDEX { ospf3IntfNbrIndex }
    ::= { ospf3IntfNbrChangeStats 1 }

Ospf3IntfNbrChangeStatsEntry ::= SEQUENCE {
    ospf3IntfNbrIndex           Integer32,
    ospf3IntfNbrDown            Counter32,
    ospf3IntfNbrAttempt         Counter32,
    ospf3IntfNbrInit            Counter32,
    ospf3IntfNbrN2way           Counter32,
    ospf3IntfNbrExStart         Counter32,
    ospf3IntfNbrExchange        Counter32,
    ospf3IntfNbrLoading         Counter32,
    ospf3IntfNbrFull            Counter32,
    ospf3IntfNbrAllEvents       Counter32
    }

ospf3IntfNbrIndex OBJECT-TYPE
    SYNTAX  Integer32
    MAX-ACCESS  read-only
    STATUS  current
    DESCRIPTION
        "The index of the Ospf3 Interface for which these statistics apply."
    ::= { ospf3IntfNbrChangeStatsEntry 1 }

ospf3IntfNbrDown OBJECT-TYPE
    SYNTAX  Counter32
    MAX-ACCESS  read-only
    STATUS  current
    DESCRIPTION
        "The total number of times neighbors now existing on this interface
        have changed into DOWN state."
    ::= { ospf3IntfNbrChangeStatsEntry 2 }

ospf3IntfNbrAttempt OBJECT-TYPE
    SYNTAX  Counter32
    MAX-ACCESS  read-only
    STATUS  current
    DESCRIPTION
        "The total number of times neighbors now existing on this interface
        have changed into ATTEMPT state."
    ::= { ospf3IntfNbrChangeStatsEntry  3 }

ospf3IntfNbrInit OBJECT-TYPE
    SYNTAX  Counter32
    MAX-ACCESS  read-only
    STATUS  current
    DESCRIPTION
        "The total number of times neighbors now existing on this interface
        have changed into INIT state."
    ::= { ospf3IntfNbrChangeStatsEntry 4 }

ospf3IntfNbrN2way OBJECT-TYPE
    SYNTAX  Counter32
    MAX-ACCESS  read-only
    STATUS  current
    DESCRIPTION
        "The total number of times neighbors now existing on this interface
        have changed into 2WAY state."
    ::= { ospf3IntfNbrChangeStatsEntry 5 }

ospf3IntfNbrExStart OBJECT-TYPE
    SYNTAX  Counter32
    MAX-ACCESS  read-only
    STATUS  current
    DESCRIPTION
        "The total number of times neighbors now existing on this interface
        have changed into EXSTART state."
    ::= { ospf3IntfNbrChangeStatsEntry 6 }

ospf3IntfNbrExchange OBJECT-TYPE
    SYNTAX  Counter32
    MAX-ACCESS  read-only
    STATUS  current
    DESCRIPTION
        "The total number of times neighbors now existing on this interface
        have changed into EXCHANGE state."
    ::= { ospf3IntfNbrChangeStatsEntry 7 }

ospf3IntfNbrLoading OBJECT-TYPE
    SYNTAX  Counter32
    MAX-ACCESS  read-only
    STATUS  current
    DESCRIPTION
        "The total number of times neighbors now existing on this interface
        have changed into LOADING state."
    ::= { ospf3IntfNbrChangeStatsEntry 8 }

ospf3IntfNbrFull OBJECT-TYPE
    SYNTAX  Counter32
    MAX-ACCESS  read-only
    STATUS  current
    DESCRIPTION
        "The total number of times neighbors now existing on this interface
        have changed into FULL state."
    ::= { ospf3IntfNbrChangeStatsEntry 9 }

ospf3IntfNbrAllEvents OBJECT-TYPE
    SYNTAX  Counter32
    MAX-ACCESS  read-only
    STATUS  current
    DESCRIPTION
        "The total number of times neighbors now existing on this interface
        have changed state or an error had occured."
    ::= { ospf3IntfNbrChangeStatsEntry 10 }

ospf3IntfChangeStats OBJECT-TYPE
    SYNTAX SEQUENCE OF Ospf3IntfChangeStatsEntry
    MAX-ACCESS not-accessible
    STATUS current
    DESCRIPTION
      "The table of Ospf3 Interface change Statistics."
    ::= { ospf3Interface 3 }

ospf3IntfChangeStatsEntry OBJECT-TYPE
    SYNTAX Ospf3IntfChangeStatsEntry
    MAX-ACCESS not-accessible
    STATUS current
    DESCRIPTION
      "Ospf3 interface Change statistics."
    INDEX { ospf3IntfIndex }
    ::= { ospf3IntfChangeStats 1 }

Ospf3IntfChangeStatsEntry ::= SEQUENCE {
    ospf3IntfIndex              Integer32,
    ospf3IntfDown               Counter32,
    ospf3IntfLoop               Counter32,
    ospf3IntfWaiting        Counter32,
    ospf3IntfPtop               Counter32,
    ospf3IntfDr                 Counter32,
    ospf3IntfBackup             Counter32,
    ospf3IntfDrOther            Counter32,
    ospf3IntfAllEvents          Counter32
    }

ospf3IntfIndex OBJECT-TYPE
    SYNTAX  Integer32
    MAX-ACCESS  read-only
    STATUS  current
    DESCRIPTION
        "The index of the Ospf3 Interface for which these statistics apply."
    ::= { ospf3IntfChangeStatsEntry 1 }

ospf3IntfDown OBJECT-TYPE
    SYNTAX   Counter32
    MAX-ACCESS   read-only
    STATUS   current
    DESCRIPTION
        "The total number of times the interface was down."
    ::= { ospf3IntfChangeStatsEntry 2 }

ospf3IntfLoop OBJECT-TYPE
    SYNTAX    Counter32
    MAX-ACCESS    read-only
    STATUS    current
    DESCRIPTION
        "The total number of times this interface changed State into the LOOP State."
    ::= { ospf3IntfChangeStatsEntry 3 }

ospf3IntfWaiting OBJECT-TYPE
    SYNTAX        Counter32
    MAX-ACCESS        read-only
    STATUS        current
    DESCRIPTION
        "The total number of times this interface changed State into the Waiting State."
    ::= { ospf3IntfChangeStatsEntry 4 }
    
ospf3IntfPtop OBJECT-TYPE
    SYNTAX        Counter32
    MAX-ACCESS        read-only
    STATUS        current
    DESCRIPTION
        "The total number of times this interface changed State into the PTOP State."
    ::= { ospf3IntfChangeStatsEntry 5 }

ospf3IntfDr OBJECT-TYPE
    SYNTAX        Counter32
    MAX-ACCESS        read-only
    STATUS        current
    DESCRIPTION
        "The total number of times this interface changed State into the DR State."
    ::= { ospf3IntfChangeStatsEntry 6 }    

ospf3IntfBackup OBJECT-TYPE
    SYNTAX     Counter32
    MAX-ACCESS     read-only
    STATUS     current
    DESCRIPTION
        "The total number of times this interface changed State into the Backup State."
    ::= { ospf3IntfChangeStatsEntry 7 }

ospf3IntfDrOther OBJECT-TYPE
    SYNTAX     Counter32
    MAX-ACCESS     read-only
    STATUS     current
    DESCRIPTION
        "The total number of times this interface changed State into the DrOther State."
    ::= { ospf3IntfChangeStatsEntry 8 }
    
ospf3IntfAllEvents OBJECT-TYPE
    SYNTAX     Counter32
    MAX-ACCESS     read-only
    STATUS     current
    DESCRIPTION
        "The total number of times this interface changed State."
    ::= { ospf3IntfChangeStatsEntry 9 }

ospf3IntfErrorStats OBJECT-TYPE
    SYNTAX SEQUENCE OF Ospf3IntfErrorStatsEntry
    MAX-ACCESS not-accessible
    STATUS current
    DESCRIPTION
      "The table of Ospf3 Interface Error Statistics."
    ::= { ospf3Interface 4 }

ospf3IntfErrorStatsEntry OBJECT-TYPE
    SYNTAX Ospf3IntfErrorStatsEntry
    MAX-ACCESS not-accessible
    STATUS current
    DESCRIPTION
      "Error Statistics for an Ospf3 interface."
    INDEX { ospf3IntfErrIndex }
    ::= { ospf3IntfErrorStats 1 }
 
Ospf3IntfErrorStatsEntry ::= SEQUENCE {
    ospf3IntfErrIndex              Integer32,
    ospf3IntfErrRxOnPasv           Counter32,
    ospf3IntfErrRxOspfOff          Counter32,
    ospf3IntfErrRxOnNotup          Counter32,
    ospf3IntfErrRxVerMismatch      Counter32,
    ospf3IntfErrRxZeroRTRID        Counter32,
    ospf3IntfErrRxSameRTRID        Counter32,
    ospf3IntfErrRxMismatchInstID   Counter32,
    ospf3IntfErrBadAreaID          Counter32,
    ospf3IntfErrBadDestAddr        Counter32,
    ospf3IntfErrBadChecksum        Counter32,
    ospf3IntfErrBadNeighbour       Counter32,
    ospf3IntfErrBadPktType         Counter32,
    ospf3IntfErrHelloMismatch      Counter32,
    ospf3IntfErrOptionsMismatch    Counter32,
    ospf3IntfErrDeadMismatch       Counter32,
    ospf3IntfErrMTUMismatch        Counter32,
    ospf3IntfErrHelloNoNbr         Counter32
    }

ospf3IntfErrIndex OBJECT-TYPE
    SYNTAX    Integer32
    MAX-ACCESS    read-only
    STATUS    current
    DESCRIPTION
        "The index of the Ospf3 Intf for which these statistics apply."
    ::= { ospf3IntfErrorStatsEntry 1 }

ospf3IntfErrRxOnPasv  OBJECT-TYPE
    SYNTAX    Counter32
    MAX-ACCESS    read-only
    STATUS    current
    DESCRIPTION
        "The total number of packets received by this interface that are
         received on a passive interface."
    ::= { ospf3IntfErrorStatsEntry 2 }

ospf3IntfErrRxOspfOff OBJECT-TYPE
    SYNTAX    Counter32
    MAX-ACCESS    read-only
    STATUS    current
    DESCRIPTION
        "The total number of packets received by this interface that are
         received while OSPF was disabled."
    ::= { ospf3IntfErrorStatsEntry 3 }

ospf3IntfErrRxOnNotup OBJECT-TYPE
    SYNTAX    Counter32
    MAX-ACCESS    read-only
    STATUS    current
    DESCRIPTION
        "The total number of packets received by this interface that are
         received while the interface was disabled."
    ::= { ospf3IntfErrorStatsEntry 4 }
    
ospf3IntfErrRxVerMismatch OBJECT-TYPE
    SYNTAX    Counter32
    MAX-ACCESS    read-only
    STATUS    current
    DESCRIPTION
        "The total number of packets received by this interface that have
         an OSPF version number not equal to the one of the interface."
    ::= { ospf3IntfErrorStatsEntry 5 }
    
ospf3IntfErrRxZeroRTRID OBJECT-TYPE
    SYNTAX    Counter32
    MAX-ACCESS    read-only
    STATUS    current
    DESCRIPTION
        "The total number of packets received by this interface that have
         a RouterID of 0."
    ::= { ospf3IntfErrorStatsEntry 6 }
    
ospf3IntfErrRxSameRTRID OBJECT-TYPE
    SYNTAX    Counter32
    MAX-ACCESS    read-only
    STATUS    current
    DESCRIPTION
        "The total number of packets received by this interface that have
         the same RouterID as this Router."
    ::= { ospf3IntfErrorStatsEntry 7 }
    
ospf3IntfErrRxMismatchInstID OBJECT-TYPE
    SYNTAX    Counter32
    MAX-ACCESS    read-only
    STATUS    current
    DESCRIPTION
        "The total number of packets received by this interface that have
         an instance number not equal to the one of the interface."
    ::= { ospf3IntfErrorStatsEntry 8 }
       
ospf3IntfErrBadAreaID OBJECT-TYPE
    SYNTAX    Counter32
    MAX-ACCESS    read-only
    STATUS    current
    DESCRIPTION
        "The total number of packets received by this interface that have
         an area number not equal to the one of the area of the interface."
    ::= { ospf3IntfErrorStatsEntry 9 }

ospf3IntfErrBadDestAddr OBJECT-TYPE
    SYNTAX    Counter32
    MAX-ACCESS    read-only
    STATUS    current
    DESCRIPTION
        "The total number of packets discarded by this interface because of
         a destination address mismatch."
    ::= { ospf3IntfErrorStatsEntry 10 }

ospf3IntfErrBadChecksum OBJECT-TYPE
    SYNTAX    Counter32
    MAX-ACCESS    read-only
    STATUS    current
    DESCRIPTION
        "The total number of packets discarded by this interface because of
         a bad checksum."
    ::= { ospf3IntfErrorStatsEntry 11 }

ospf3IntfErrBadNeighbour OBJECT-TYPE
    SYNTAX    Counter32
    MAX-ACCESS    read-only
    STATUS    current
    DESCRIPTION
        "The total number of packets discarded by this interface because
         they could not be associated with any neighbor."
    ::= { ospf3IntfErrorStatsEntry 12 }

ospf3IntfErrBadPktType OBJECT-TYPE
    SYNTAX    Counter32
    MAX-ACCESS    read-only
    STATUS    current
    DESCRIPTION
        "The total number of packets discarded by this interface because
         the packet type was not recognized."
    ::= { ospf3IntfErrorStatsEntry 13 }

ospf3IntfErrHelloMismatch OBJECT-TYPE
    SYNTAX    Counter32
    MAX-ACCESS    read-only
    STATUS    current
    DESCRIPTION
        "The total number of packets received with a different hello interval
         by this interface."
    ::= { ospf3IntfErrorStatsEntry 14 }

ospf3IntfErrOptionsMismatch OBJECT-TYPE
    SYNTAX    Counter32
    MAX-ACCESS    read-only
    STATUS    current
    DESCRIPTION
        "The total number of packets received with a different options
         by this interface."
    ::= { ospf3IntfErrorStatsEntry 15 }

ospf3IntfErrDeadMismatch OBJECT-TYPE
    SYNTAX    Counter32
    MAX-ACCESS    read-only
    STATUS    current
    DESCRIPTION
        "The total number of packets received with a different dead interval
         by this interface."
    ::= { ospf3IntfErrorStatsEntry 16 }

ospf3IntfErrMTUMismatch OBJECT-TYPE
    SYNTAX    Counter32
    MAX-ACCESS    read-only
    STATUS    current
    DESCRIPTION
        "The total number of packets received with a different MTU size 
         by this interface."
    ::= { ospf3IntfErrorStatsEntry 17 }
    
ospf3IntfErrHelloNoNbr OBJECT-TYPE
    SYNTAX    Counter32
    MAX-ACCESS    read-only
    STATUS    current
    DESCRIPTION
        "The total number of packets received from an unknown neighbor
         when this interface has a Network Type of NBMA or PTOMP."
    ::= { ospf3IntfErrorStatsEntry 18 }

-- Ospf3 General Statistics contains the cumulative stats for all
-- areas / interfaces

ospf3CumRxPkts OBJECT-TYPE
    SYNTAX  Counter32
    MAX-ACCESS  read-only
    STATUS  current
    DESCRIPTION
        "The total number of Ospf3 packets received on all 
        of the router's interfaces."
 ::= { ospf3CumRxTxDisdStats 1 }
 
ospf3CumTxPkts OBJECT-TYPE
    SYNTAX  Counter32
    MAX-ACCESS  read-only
    STATUS  current
    DESCRIPTION
        "The total number of Ospf3 packets transmitted on all 
        of the router's interfaces."
    ::= { ospf3CumRxTxDisdStats 2 }
    
ospf3CumDisdPkts OBJECT-TYPE
    SYNTAX  Counter32
    MAX-ACCESS  read-only
    STATUS  current
    DESCRIPTION
        "The total number of Ospf3 packets discaded on all 
        of the router's interfaces."
    ::= { ospf3CumRxTxDisdStats 3 }
 
ospf3CumRxHello OBJECT-TYPE
    SYNTAX  Counter32 
    MAX-ACCESS  read-only
    STATUS  current
    DESCRIPTION
        "The total number of Hello packets received on all 
        of the router's interfaces."
    ::= { ospf3CumRxTxDisdStats 4 }

ospf3CumTxHello OBJECT-TYPE
    SYNTAX  Counter32
    MAX-ACCESS  read-only
    STATUS  current
    DESCRIPTION
        "The total number of Hello packets transmitted on all 
        of the router's interfaces."
    ::= { ospf3CumRxTxDisdStats 5 }
    
ospf3CumDisdHello OBJECT-TYPE
    SYNTAX  Counter32
    MAX-ACCESS  read-only
    STATUS  current
    DESCRIPTION
        "The total number of Hello packets discaded on all 
        of the router's interfaces."
    ::= { ospf3CumRxTxDisdStats 6 }
 
ospf3CumRxDatabase OBJECT-TYPE
    SYNTAX  Counter32 
    MAX-ACCESS  read-only
    STATUS  current
    DESCRIPTION
        "The total number of Database Description packets received on all 
        of the router's interfaces."
    ::= { ospf3CumRxTxDisdStats 7 }

ospf3CumTxDatabase OBJECT-TYPE
    SYNTAX  Counter32
    MAX-ACCESS  read-only
    STATUS  current
    DESCRIPTION
        "The total number of Database Description packets transmitted 
         on all of the router's interfaces."
    ::= { ospf3CumRxTxDisdStats 8 }
    
ospf3CumDisdDatabase OBJECT-TYPE
    SYNTAX  Counter32
    MAX-ACCESS  read-only
    STATUS  current
    DESCRIPTION
        "The total number of Database Description packets discarded 
         on all of the router's interfaces."
    ::= { ospf3CumRxTxDisdStats 9 }
 
 
ospf3CumRxlsReqs OBJECT-TYPE
    SYNTAX  Counter32 
    MAX-ACCESS  read-only
    STATUS  current
    DESCRIPTION
        "The total number of Link State Request packets received  
         on all of the router's interfaces."
    ::= { ospf3CumRxTxDisdStats 10 }

ospf3CumTxlsReqs OBJECT-TYPE
    SYNTAX  Counter32 
    MAX-ACCESS  read-only
    STATUS  current
    DESCRIPTION
        "The total number of Link State Request packets transmitted  
         on all of the router's interfaces."
    ::= { ospf3CumRxTxDisdStats 11 }
    
ospf3CumDisdlsReqs OBJECT-TYPE
    SYNTAX  Counter32 
    MAX-ACCESS  read-only
    STATUS  current
    DESCRIPTION
        "The total number of Link State Request packets discarded  
         on all of the router's interfaces."
    ::= { ospf3CumRxTxDisdStats 12 }

ospf3CumRxlsAcks OBJECT-TYPE
    SYNTAX  Counter32
    MAX-ACCESS  read-only
    STATUS  current
    DESCRIPTION
        "The total number of Link State Acknowledgement packets received  
         on all of the router's interfaces."
    ::= { ospf3CumRxTxDisdStats 13 }
 
ospf3CumTxlsAcks OBJECT-TYPE
    SYNTAX  Counter32 
    MAX-ACCESS  read-only
    STATUS  current
    DESCRIPTION
        "The total number of Link State Acknowledgement packets transmitted
         on all of the router's interfaces."
    ::= { ospf3CumRxTxDisdStats 14 }
    
ospf3CumDisdlsAcks OBJECT-TYPE
    SYNTAX  Counter32 
    MAX-ACCESS  read-only
    STATUS  current
    DESCRIPTION
        "The total number of Link State Acknowledgement packets discarded
         on all of the router's interfaces."
    ::= { ospf3CumRxTxDisdStats 15 }

ospf3CumRxlsUpdates OBJECT-TYPE
    SYNTAX  Counter32
    MAX-ACCESS  read-only
    STATUS  current
    DESCRIPTION
        "The total number of Link State Update packets received  
         on all of the router's interfaces."
    ::= { ospf3CumRxTxDisdStats 16 }
 
ospf3CumTxlsUpdates OBJECT-TYPE
    SYNTAX  Counter32 
    MAX-ACCESS  read-only
    STATUS  current
    DESCRIPTION
        "The total number of Link State Update packets transmitted  
         on all of the router's interfaces."
    ::= { ospf3CumRxTxDisdStats 17 }
    
ospf3CumDisdlsUpdates OBJECT-TYPE
    SYNTAX  Counter32 
    MAX-ACCESS  read-only
    STATUS  current
    DESCRIPTION
        "The total number of Link State Update packets discarded  
         on all of the router's interfaces."
    ::= { ospf3CumRxTxDisdStats 18 }


ospf3CumNbrDown OBJECT-TYPE
    SYNTAX  Counter32
    MAX-ACCESS  read-only
    STATUS  current
    DESCRIPTION
        "The total number of times neighbors now existing on the interfaces now
        present on the router have changed into DOWN state."
        ::= { ospf3CumNbrChangeStats 1 }

ospf3CumNbrAttempt OBJECT-TYPE
    SYNTAX  Counter32
    MAX-ACCESS  read-only
    STATUS  current
    DESCRIPTION
        "The total number of times neighbors now existing the on interfaces now
        present on the router have changed into ATTEMPT state."
    ::= { ospf3CumNbrChangeStats 2 }

ospf3CumNbrInit OBJECT-TYPE
    SYNTAX  Counter32
    MAX-ACCESS  read-only
    STATUS  current
    DESCRIPTION
        "The total number of times neighbors now existing the on interfaces now
        present on the router have changed into INIT state."
    ::= { ospf3CumNbrChangeStats 3 }

ospf3CumNbrN2way OBJECT-TYPE
    SYNTAX  Counter32
    MAX-ACCESS  read-only
    STATUS  current
    DESCRIPTION
        "The total number of times neighbors now existing the on interfaces now
        present on the router have changed into 2WAY state."
    ::= { ospf3CumNbrChangeStats 4 }

ospf3CumNbrExStart OBJECT-TYPE
    SYNTAX  Counter32
    MAX-ACCESS  read-only
    STATUS  current
    DESCRIPTION
        "The total number of times neighbors now existing the on interfaces now
        present on the router have changed into EXSTART state."
    ::= { ospf3CumNbrChangeStats 5 }

ospf3CumNbrExchange OBJECT-TYPE
    SYNTAX  Counter32
    MAX-ACCESS  read-only
    STATUS  current
    DESCRIPTION
        "The total number of times neighbors now existing the on interfaces now
        present on the router have changed into EXCHANGE state."
    ::= { ospf3CumNbrChangeStats 6 }

ospf3CumNbrLoading OBJECT-TYPE
    SYNTAX  Counter32
    MAX-ACCESS  read-only
    STATUS  current
    DESCRIPTION
        "The total number of times neighbors now existing the on interfaces now
        present on the router have changed into LOADING state."
    ::= { ospf3CumNbrChangeStats 7 }

ospf3CumNbrFull OBJECT-TYPE
    SYNTAX  Counter32
    MAX-ACCESS  read-only
    STATUS  current
    DESCRIPTION
        "The total number of times neighbors now existing the on interfaces now
        present on the router have changed into FULL state."
    ::= { ospf3CumNbrChangeStats 8 }

ospf3CumNbrAllEvents OBJECT-TYPE
    SYNTAX  Counter32
    MAX-ACCESS  read-only
    STATUS  current
    DESCRIPTION
        "The total number of times neighbors now existing the on interfaces now
        present on the router have changed state."
    ::= { ospf3CumNbrChangeStats 9 }

ospf3CumIntfDown OBJECT-TYPE
    SYNTAX   Counter32
    MAX-ACCESS   read-only
    STATUS   current
    DESCRIPTION
        "The total number of times, for all the interfaces on the router,
         an interface was down."
    ::= { ospf3CumIntfChangeStats 1 }

ospf3CumIntfLoop OBJECT-TYPE
    SYNTAX    Counter32
    MAX-ACCESS    read-only
    STATUS    current
    DESCRIPTION
        "The total number of times , for all the interfaces on the router,
        an interface changed State into the LOOP State."
    ::= { ospf3CumIntfChangeStats 2 }

ospf3CumIntfWaiting OBJECT-TYPE
    SYNTAX        Counter32
    MAX-ACCESS        read-only
    STATUS        current
    DESCRIPTION
        "The total number of times , for all the interfaces on the router,
        an interface changed State into the WAITING State."
    ::= { ospf3CumIntfChangeStats 3 }
    
ospf3CumIntfPtop OBJECT-TYPE
    SYNTAX        Counter32
    MAX-ACCESS        read-only
    STATUS        current
    DESCRIPTION
        "The total number of times , for all the interfaces on the router,
        an interface changed State into the PTOP State."
    ::= { ospf3CumIntfChangeStats 4 }

ospf3CumIntfDr OBJECT-TYPE
    SYNTAX        Counter32
    MAX-ACCESS        read-only
    STATUS        current
    DESCRIPTION
        "The total number of times , for all the interfaces on the router,
        an interface changed State into the DR State."
    ::= { ospf3CumIntfChangeStats 5 }    

ospf3CumIntfBackup OBJECT-TYPE
    SYNTAX     Counter32
    MAX-ACCESS     read-only
    STATUS     current
    DESCRIPTION
        "The total number of times , for all the interfaces on the router,
        an interface changed State into the BACKUP State."
    ::= { ospf3CumIntfChangeStats 6 }

ospf3CumIntfDrOther OBJECT-TYPE
    SYNTAX     Counter32
    MAX-ACCESS     read-only
    STATUS     current
    DESCRIPTION
        "The total number of times , for all the interfaces on the router,
        an interface changed State into the DROTHER State."
    ::= { ospf3CumIntfChangeStats 7 }
    
ospf3CumIntfAllEvents OBJECT-TYPE
    SYNTAX     Counter32
    MAX-ACCESS     read-only
    STATUS     current
    DESCRIPTION
        "The total number of times , for all the interfaces on the router,
        an interface changed it's state."
    ::= { ospf3CumIntfChangeStats 8 }

ospf3TmrsKckOffHello OBJECT-TYPE
    SYNTAX    Counter32
    MAX-ACCESS    read-only
    STATUS    current
    DESCRIPTION
        "The sum total number of times the Hello timer has been fired
         (which triggers the send of a Hello packet) across all OPSF 
         areas and interfaces."
    ::= { ospf3TimersKickOffStats 1 }

ospf3TmrsKckOffWait OBJECT-TYPE
    SYNTAX   Counter32
    MAX-ACCESS   read-only
    STATUS   current
    DESCRIPTION
        "The sum total number of times the KickOffWait timer has been fired
         (which triggers the send of a KickOffWait packet) across all OPSF 
         areas and interfaces."
    ::= { ospf3TimersKickOffStats 2 }

ospf3TmrsKckOffPoll OBJECT-TYPE
    SYNTAX    Counter32
    MAX-ACCESS    read-only
    STATUS    current
    DESCRIPTION
        "The sum total number of times the KickOffPoll timer has been fired
         (which triggers the send of a KickOffPoll packet) across all OPSF 
         areas and interfaces."
    ::= { ospf3TimersKickOffStats 3 }

ospf3TmrsKckOffNbrProbe OBJECT-TYPE
    SYNTAX   Counter32
    MAX-ACCESS   read-only
    STATUS   current
    DESCRIPTION
        "The sum total number of times the KickOffNbrProbe timer has been fired
         (which triggers the send of a KickOffNbrProbe packet) across all OPSF 
         areas and interfaces."
    ::= { ospf3TimersKickOffStats 4 }


mldIfStatsTable OBJECT-TYPE
    SYNTAX SEQUENCE OF MldIfStatsEntry  
	  MAX-ACCESS not-accessible
	  STATUS current
	  DESCRIPTION
	    "The table listing the interfaces on which
	     MLD is enabled."
	  ::= { mldStats 1 }
	
mldIfStatsEntry OBJECT-TYPE
    SYNTAX     MldIfStatsEntry
    MAX-ACCESS not-accessible
    STATUS     current
    DESCRIPTION
      "An entry representing an interface stats on
       which MLD is enabled."
    INDEX      { mldIfStatsIfIndex }
    ::= { mldIfStatsTable 1 }

MldIfStatsEntry ::= SEQUENCE {
    mldIfStatsIfIndex                       Integer32,
    rxMldIfStatsGeneralQuery                Counter32,
    rxMldIfStatsMASQuery                    Counter32,
    rxMldIfStatsMASSQQuery                  Counter32,
    rxMldIfStatsMLDv1Report                 Counter32,
    rxMldIfStatsMLDv1Done                   Counter32,
    rxMldIfStatsMLDv2Report                 Counter32,
    rxMldIfStatsIncCrsv2                    Counter32,
    rxMldIfStatsExcCrsv2                    Counter32,
    rxMldIfStatsToIncFmcrsv2                Counter32,
    rxMldIfStatsToExcFmcrsv2                Counter32,
    rxMldIfStatsAllowSlcrsv2                Counter32,
    rxMldIfStatsBlockSlcrsv2                Counter32,
    txMldIfStatsGeneralQuery                Counter32,
    txMldIfStatsMASQuery                    Counter32,
    txMldIfStatsMASSQQuery                  Counter32,
    txMldIfStatsMLDv1Report                 Counter32,
    txMldIfStatsMLDv1Done                   Counter32,
    txMldIfStatsMLDv2Report                 Counter32,
    txMldIfStatsIncCrsv2                    Counter32,
    txMldIfStatsExcCrsv2                    Counter32,
    txMldIfStatsToIncFmcrsv2                Counter32,
    txMldIfStatsToExcFmcrsv2                Counter32,
    txMldIfStatsAllowSlcrsv2                Counter32,
    txMldIfStatsBlockSlcrsv2                Counter32,
    errMldIfStatsGeneralQuery                Counter32,
    errMldIfStatsMASQuery                    Counter32,
    errMldIfStatsMASSQQuery                  Counter32,
    errMldIfStatsMLDv1Report                 Counter32,
    errMldIfStatsMLDv1Done                   Counter32,
    errMldIfStatsMLDv2Report                 Counter32,
    errMldIfStatsIncCrsv2                    Counter32,
    errMldIfStatsExcCrsv2                    Counter32,
    errMldIfStatsToIncFmcrsv2                Counter32,
    errMldIfStatsToExcFmcrsv2                Counter32,
    errMldIfStatsAllowSlcrsv2                Counter32,
    errMldIfStatsBlockSlcrsv2                Counter32
}
	
mldIfStatsIfIndex OBJECT-TYPE
    SYNTAX     Integer32
    MAX-ACCESS read-only
    STATUS     current
    DESCRIPTION
      "The internetwork-layer interface value of the interface
       for which MLD msg stats is counted."
    ::= { mldIfStatsEntry 1 }

rxMldIfStatsGeneralQuery OBJECT-TYPE
    SYNTAX    Counter32
    MAX-ACCESS    read-only
    STATUS    current
    DESCRIPTION
        "The total number of MLD Listener Queries received." 
    ::= { mldIfStatsEntry 2 }

rxMldIfStatsMASQuery OBJECT-TYPE
    SYNTAX    Counter32
    MAX-ACCESS    read-only
    STATUS    current
    DESCRIPTION
        "The total number of MLD Listener MAS Queries received." 
    ::= { mldIfStatsEntry 3 }

rxMldIfStatsMASSQQuery OBJECT-TYPE
    SYNTAX    Counter32
    MAX-ACCESS    read-only
    STATUS    current
    DESCRIPTION
        "The total number of MLD Listener MASSQ Queries received." 
    ::= { mldIfStatsEntry 4 }

rxMldIfStatsMLDv1Report OBJECT-TYPE
    SYNTAX    Counter32
    MAX-ACCESS    read-only
    STATUS    current
    DESCRIPTION
        "The total number of MLD Listener Reports (v1) received." 
    ::= { mldIfStatsEntry 5 }

rxMldIfStatsMLDv1Done OBJECT-TYPE
    SYNTAX    Counter32
    MAX-ACCESS    read-only
    STATUS    current
    DESCRIPTION
        "The total number of MLD Listener Dones (v1/v2) received." 
    ::= { mldIfStatsEntry 6 }

rxMldIfStatsMLDv2Report OBJECT-TYPE
    SYNTAX    Counter32
    MAX-ACCESS    read-only
    STATUS    current
    DESCRIPTION
        "The total number of MLD Listener Reports (v2) received." 
    ::= { mldIfStatsEntry 7 }

rxMldIfStatsIncCrsv2 OBJECT-TYPE
    SYNTAX    Counter32
    MAX-ACCESS    read-only
    STATUS    current
    DESCRIPTION
        "The total number of MLD INC CRs (v2) received." 
    ::= { mldIfStatsEntry 8 }

rxMldIfStatsExcCrsv2 OBJECT-TYPE
    SYNTAX    Counter32
    MAX-ACCESS    read-only
    STATUS    current
    DESCRIPTION
        "The total number of MLD EXC CRs (v2) received." 
    ::= { mldIfStatsEntry 9 }

rxMldIfStatsToIncFmcrsv2 OBJECT-TYPE
    SYNTAX    Counter32
    MAX-ACCESS    read-only
    STATUS    current
    DESCRIPTION
        "The total number of MLD TO_INC FMCRs (v2) received." 
    ::= { mldIfStatsEntry 10 }

rxMldIfStatsToExcFmcrsv2 OBJECT-TYPE
    SYNTAX    Counter32
    MAX-ACCESS    read-only
    STATUS    current
    DESCRIPTION
        "The total number of MLD TO_EXC FMCRs (v2) received." 
    ::= { mldIfStatsEntry 11 }

rxMldIfStatsAllowSlcrsv2 OBJECT-TYPE
    SYNTAX    Counter32
    MAX-ACCESS    read-only
    STATUS    current
    DESCRIPTION
        "The total number of MLD ALLOW SLCRs (v2) received." 
    ::= { mldIfStatsEntry 12 }

rxMldIfStatsBlockSlcrsv2 OBJECT-TYPE
    SYNTAX    Counter32
    MAX-ACCESS    read-only
    STATUS    current
    DESCRIPTION
        "The total number of MLD BLOCK SLCRs (v2) received." 
    ::= { mldIfStatsEntry 13 }

txMldIfStatsGeneralQuery OBJECT-TYPE
    SYNTAX    Counter32
    MAX-ACCESS    read-only
    STATUS    current
    DESCRIPTION
        "The total number of MLD Listener Queries sent." 
    ::= { mldIfStatsEntry 14 }

txMldIfStatsMASQuery OBJECT-TYPE
    SYNTAX    Counter32
    MAX-ACCESS    read-only
    STATUS    current
    DESCRIPTION
        "The total number of MLD Listener MAS Queries sent." 
    ::= { mldIfStatsEntry 15 }

txMldIfStatsMASSQQuery OBJECT-TYPE
    SYNTAX    Counter32
    MAX-ACCESS    read-only
    STATUS    current
    DESCRIPTION
        "The total number of MLD Listener MASSQ Queries sent." 
    ::= { mldIfStatsEntry 16 }

txMldIfStatsMLDv1Report OBJECT-TYPE
    SYNTAX    Counter32
    MAX-ACCESS    read-only
    STATUS    current
    DESCRIPTION
        "The total number of MLD Listener Reports (v1) sent." 
    ::= { mldIfStatsEntry 17 }

txMldIfStatsMLDv1Done OBJECT-TYPE
    SYNTAX    Counter32
    MAX-ACCESS    read-only
    STATUS    current
    DESCRIPTION
        "The total number of MLD Listener Dones (v1/v2) sent." 
    ::= { mldIfStatsEntry 18 }

txMldIfStatsMLDv2Report OBJECT-TYPE
    SYNTAX    Counter32
    MAX-ACCESS    read-only
    STATUS    current
    DESCRIPTION
        "The total number of MLD Listener Reports (v2) sent." 
    ::= { mldIfStatsEntry 19 }

txMldIfStatsIncCrsv2 OBJECT-TYPE
    SYNTAX    Counter32
    MAX-ACCESS    read-only
    STATUS    current
    DESCRIPTION
        "The total number of MLD INC CRs (v2) sent" 
    ::= { mldIfStatsEntry 20 }

txMldIfStatsExcCrsv2 OBJECT-TYPE
    SYNTAX    Counter32
    MAX-ACCESS    read-only
    STATUS    current
    DESCRIPTION
        "The total number of MLD EXC CRs (v2) sent" 
    ::= { mldIfStatsEntry 21 }

txMldIfStatsToIncFmcrsv2 OBJECT-TYPE
    SYNTAX    Counter32
    MAX-ACCESS    read-only
    STATUS    current
    DESCRIPTION
        "The total number of MLD TO_INC FMCRs (v2) sent" 
    ::= { mldIfStatsEntry 22 }

txMldIfStatsToExcFmcrsv2 OBJECT-TYPE
    SYNTAX    Counter32
    MAX-ACCESS    read-only
    STATUS    current
    DESCRIPTION
        "The total number of MLD TO_EXC FMCRs (v2) sent" 
    ::= { mldIfStatsEntry 23 }

txMldIfStatsAllowSlcrsv2 OBJECT-TYPE
    SYNTAX    Counter32
    MAX-ACCESS    read-only
    STATUS    current
    DESCRIPTION
        "The total number of MLD ALLOW SLCRs (v2) sent" 
    ::= { mldIfStatsEntry 24 }

txMldIfStatsBlockSlcrsv2 OBJECT-TYPE
    SYNTAX    Counter32
    MAX-ACCESS    read-only
    STATUS    current
    DESCRIPTION
        "The total number of MLD BLOCK SLCRs (v2) received." 
    ::= { mldIfStatsEntry 25 }

errMldIfStatsGeneralQuery OBJECT-TYPE
    SYNTAX    Counter32
    MAX-ACCESS    read-only
    STATUS    current
    DESCRIPTION
        "The total number of MLD Listener Queries errors." 
    ::= { mldIfStatsEntry 27 }

errMldIfStatsMASQuery OBJECT-TYPE
    SYNTAX    Counter32
    MAX-ACCESS    read-only
    STATUS    current
    DESCRIPTION
        "The total number of MLD Listener MAS Queries errors." 
    ::= { mldIfStatsEntry 28 }

errMldIfStatsMASSQQuery OBJECT-TYPE
    SYNTAX    Counter32
    MAX-ACCESS    read-only
    STATUS    current
    DESCRIPTION
        "The total number of MLD Listener MASSQ Queries errors." 
    ::= { mldIfStatsEntry 29 }

errMldIfStatsMLDv1Report OBJECT-TYPE
    SYNTAX    Counter32
    MAX-ACCESS    read-only
    STATUS    current
    DESCRIPTION
        "The total number of MLD Listener Report (v1) errors." 
    ::= { mldIfStatsEntry 30 }

errMldIfStatsMLDv1Done OBJECT-TYPE
    SYNTAX    Counter32
    MAX-ACCESS    read-only
    STATUS    current
    DESCRIPTION
        "The total number of MLD Listener Done (v1/v2) errors." 
    ::= { mldIfStatsEntry 31 }

errMldIfStatsMLDv2Report OBJECT-TYPE
    SYNTAX    Counter32
    MAX-ACCESS    read-only
    STATUS    current
    DESCRIPTION
        "The total number of MLD Listener Report (v2) errors." 
    ::= { mldIfStatsEntry 32}

errMldIfStatsIncCrsv2 OBJECT-TYPE
    SYNTAX    Counter32
    MAX-ACCESS    read-only
    STATUS    current
    DESCRIPTION
        "The total number of MLD INC CRs (v2) errors." 
    ::= { mldIfStatsEntry 33 }

errMldIfStatsExcCrsv2 OBJECT-TYPE
    SYNTAX    Counter32
    MAX-ACCESS    read-only
    STATUS    current
    DESCRIPTION
        "The total number of MLD EXC CRs (v2) errors." 
    ::= { mldIfStatsEntry 34 }

errMldIfStatsToIncFmcrsv2 OBJECT-TYPE
    SYNTAX    Counter32
    MAX-ACCESS    read-only
    STATUS    current
    DESCRIPTION
        "The total number of MLD TO_INC FMCRs (v2) errors." 
    ::= { mldIfStatsEntry 35 }

errMldIfStatsToExcFmcrsv2 OBJECT-TYPE
    SYNTAX    Counter32
    MAX-ACCESS    read-only
    STATUS    current
    DESCRIPTION
        "The total number of MLD TO_EXC FMCRs (v2) errors." 
    ::= { mldIfStatsEntry 36 }

errMldIfStatsAllowSlcrsv2 OBJECT-TYPE
    SYNTAX    Counter32
    MAX-ACCESS    read-only
    STATUS    current
    DESCRIPTION
        "The total number of MLD ALLOW SLCRs (v2) errors." 
    ::= { mldIfStatsEntry 37 }

errMldIfStatsBlockSlcrsv2 OBJECT-TYPE
    SYNTAX    Counter32
    MAX-ACCESS    read-only
    STATUS    current
    DESCRIPTION
        "The total number of MLD BLOCK SLCRs (v2) errors." 
    ::= { mldIfStatsEntry 38 }

mldStatBadLength OBJECT-TYPE
    SYNTAX  Counter32
	  MAX-ACCESS  read-only
	  STATUS  current
	  DESCRIPTION
	    "The total number of bad length mld packet."
	  ::= { mldStats 2 }
		
mldStatBadChecksum OBJECT-TYPE
    SYNTAX  Counter32
      MAX-ACCESS  read-only
      STATUS  current
      DESCRIPTION
        "The total number of bad checksum mld packet."
	  ::= { mldStats 3 }
		
mldStatBadReceiveIf OBJECT-TYPE
    SYNTAX  Counter32
      MAX-ACCESS  read-only
      STATUS  current
      DESCRIPTION
        "The total number of bad reveive if mld packet."
	  ::= { mldStats 4 }
		
mldStatReceiveNonLocal OBJECT-TYPE
    SYNTAX  Counter32
      MAX-ACCESS  read-only
      STATUS  current
      DESCRIPTION
        "The total number of non local received mld packet."
      ::= { mldStats 5 }
    
mldStatInvalidPkts OBJECT-TYPE
    SYNTAX  Counter32
	  MAX-ACCESS  read-only
	  STATUS  current
	  DESCRIPTION
	    "The total number of invalid packets."
	  ::= { mldStats 6 }

mldStatTotalL3Ipv6SgvEntries OBJECT-TYPE
    SYNTAX  Counter32
	  MAX-ACCESS  read-only
	  STATUS  current
	  DESCRIPTION
	    "Total L3 IPv6 (S, G, V) entries"
	  ::= { mldStats 7 }

mldStatTotalMLDGroups OBJECT-TYPE
    SYNTAX  Counter32
	  MAX-ACCESS  read-only
	  STATUS  current
	  DESCRIPTION
	    "The total number of MLD Groups."
	  ::= { mldStats 8 }

mldStatClearAll OBJECT-TYPE
    SYNTAX  INTEGER {
        other(1),
        clear(2)
      }
	  MAX-ACCESS  read-write
	  STATUS  current
	  DESCRIPTION
	    "Clear all MLD stats. Returns other(1) when read."
	  ::= { mldStats 9 }



-- Information - Run-time IP Route Table 

ipInfoRouterID OBJECT-TYPE
    SYNTAX  IpAddress
    MAX-ACCESS  read-only
    STATUS  current
    DESCRIPTION
        "Router ID information."
    ::= { ipInfo 1 }


ipIntfInfoTable OBJECT-TYPE
    SYNTAX  SEQUENCE OF IntfInfoEntry
    MAX-ACCESS not-accessible
    STATUS current 
    DESCRIPTION
        "The table of IP interface information."
    ::= {ipIntfInfo 1 }

intfInfoEntry OBJECT-TYPE
    SYNTAX  IntfInfoEntry 
    MAX-ACCESS not-accessible
    STATUS  current 
    DESCRIPTION
        "A row in IP interface information table."
    INDEX   { intfInfoIndex }
    ::= { ipIntfInfoTable 1 }

IntfInfoEntry ::= SEQUENCE {
    intfInfoIndex        Integer32,
    intfInfoAddr          DisplayString,
    intfInfoNetMask       DisplayString,
    intfInfoBcastAddr     DisplayString,
    intfInfoVlan          Integer32,
    intfInfoStatus        INTEGER
    }

intfInfoIndex OBJECT-TYPE
    SYNTAX  Integer32
    MAX-ACCESS  read-only
    STATUS  current
    DESCRIPTION
    "The interface number for which the information is related."
    ::= { intfInfoEntry 1}


intfInfoAddr  OBJECT-TYPE
    SYNTAX   DisplayString 
    MAX-ACCESS  read-only
    STATUS  current
    DESCRIPTION
    "The IP address of the interface."
    ::= { intfInfoEntry 3 }

intfInfoNetMask OBJECT-TYPE
    SYNTAX   DisplayString 
    MAX-ACCESS  read-only
    STATUS  current
    DESCRIPTION
        "The subnet mask of the interface."
    ::= { intfInfoEntry 4 }

intfInfoBcastAddr OBJECT-TYPE
    SYNTAX   DisplayString 
    MAX-ACCESS  read-only
    STATUS  current
    DESCRIPTION
        "The broadcast address of the interface."
    ::= { intfInfoEntry 5 }

intfInfoVlan OBJECT-TYPE
    SYNTAX  Integer32
    MAX-ACCESS  read-only
    STATUS  current
    DESCRIPTION
        "The VLAN number for this interface."
    ::= { intfInfoEntry 6 }

intfInfoStatus OBJECT-TYPE
    SYNTAX  INTEGER {
    up(1),
    down(2),
        disabled(3)
    }  
    MAX-ACCESS  read-only
    STATUS  current
    DESCRIPTION
    "The status of the interface."
    ::= { intfInfoEntry 7 }



ipIntfLoopbackInfoTable OBJECT-TYPE
    SYNTAX  SEQUENCE OF IntfLoopbackInfoEntry
    MAX-ACCESS not-accessible
    STATUS current 
    DESCRIPTION
        "The table of IP Loopback interface information."
    ::= {ipIntfLoopbackInfo 1 }

intfLoopbackInfoEntry OBJECT-TYPE
    SYNTAX  IntfLoopbackInfoEntry 
    MAX-ACCESS not-accessible
    STATUS  current 
    DESCRIPTION
        "A row in IP Loopback interface information table."
    INDEX   { intfLoopbackInfoIndex }
    ::= { ipIntfLoopbackInfoTable 1 }

IntfLoopbackInfoEntry ::= SEQUENCE {
    intfLoopbackInfoIndex         Integer32,
    intfLoopbackInfoAddr          DisplayString,
    intfLoopbackInfoNetMask       DisplayString,
    intfLoopbackInfoBcastAddr     DisplayString,
    intfLoopbackInfoStatus        INTEGER
    }

intfLoopbackInfoIndex OBJECT-TYPE
    SYNTAX  Integer32
    MAX-ACCESS  read-only
    STATUS  current
    DESCRIPTION
    "The Loopback interface number for which the information is related."
    ::= { intfLoopbackInfoEntry 1}

intfLoopbackInfoAddr  OBJECT-TYPE
    SYNTAX   DisplayString 
    MAX-ACCESS  read-only
    STATUS  current
    DESCRIPTION
    "The IP address of the interface."
    ::= { intfLoopbackInfoEntry 3 }

intfLoopbackInfoNetMask OBJECT-TYPE
    SYNTAX   DisplayString 
    MAX-ACCESS  read-only
    STATUS  current
    DESCRIPTION
        "The subnet mask of the interface."
    ::= { intfLoopbackInfoEntry 4 }

intfLoopbackInfoBcastAddr OBJECT-TYPE
    SYNTAX   DisplayString 
    MAX-ACCESS  read-only
    STATUS  current
    DESCRIPTION
        "The broadcast address of the interface."
    ::= { intfLoopbackInfoEntry 5 }

intfLoopbackInfoStatus OBJECT-TYPE
    SYNTAX  INTEGER {
    up(1),
    down(2),
        disabled(3)
    }  
    MAX-ACCESS  read-only
    STATUS  current
    DESCRIPTION
    "The status of the interface."
    ::= { intfLoopbackInfoEntry 7 }

ipMgmtRouteInfoTable OBJECT-TYPE
    SYNTAX  SEQUENCE OF IpMgmtRouteInfoEntry
    MAX-ACCESS  not-accessible
    STATUS  current
    DESCRIPTION
        "The table of run-time IP routes."
    ::= { ipRoutingInfo 3 }

ipMgmtRouteInfoEntry OBJECT-TYPE
    SYNTAX  IpMgmtRouteInfoEntry
    MAX-ACCESS  not-accessible
    STATUS  current
    DESCRIPTION
        "A row in the run-time IP route table"
    INDEX   { ipMgmtRouteInfoIndx }
    ::= { ipMgmtRouteInfoTable 1 }

IpMgmtRouteInfoEntry ::= SEQUENCE {
    ipMgmtRouteInfoIndx         Integer32,
    ipMgmtRouteInfoDestIp           IpAddress,
    ipMgmtRouteInfoMask             IpAddress,
    ipMgmtRouteInfoGateway          IpAddress,
    ipMgmtRouteInfoTag          INTEGER,
    ipMgmtRouteInfoType         INTEGER,
    ipMgmtRouteInfoInterface        Integer32,
    ipMgmtRouteInfoGateway1         IpAddress,
    ipMgmtRouteInfoGateway2         IpAddress,
    ipMgmtRouteInfoMetric           Integer32
    }

ipMgmtRouteInfoIndx OBJECT-TYPE
    SYNTAX  Integer32
    MAX-ACCESS  read-only
    STATUS  current
    DESCRIPTION
        "The index of this route table."
    ::= { ipMgmtRouteInfoEntry 1 }

ipMgmtRouteInfoDestIp OBJECT-TYPE
    SYNTAX  IpAddress
    MAX-ACCESS  read-only
    STATUS  current
    DESCRIPTION
        "The destination IP address of this route."
    ::= { ipMgmtRouteInfoEntry 2 }

ipMgmtRouteInfoMask OBJECT-TYPE
    SYNTAX  IpAddress
    MAX-ACCESS  read-only
    STATUS  current
    DESCRIPTION
        "The destination IP mask of this route."
    ::= { ipMgmtRouteInfoEntry 3 }

ipMgmtRouteInfoGateway OBJECT-TYPE
    SYNTAX  IpAddress
    MAX-ACCESS  read-only
    STATUS  current
    DESCRIPTION
        "The next-hop router address for this route."
    ::= { ipMgmtRouteInfoEntry 4 }

ipMgmtRouteInfoTag OBJECT-TYPE
    SYNTAX  INTEGER {
        fixed(1),
        static(2),
        addr(3),
        rip(4),
        broadcast(5),
        martian(6),
        multicast(7),
        vip(8),
        bgp(9),
        ospf(10),
        none(11)
        }
    MAX-ACCESS  read-only
    STATUS  current
    DESCRIPTION
        "The tag-type for this route."
    ::= { ipMgmtRouteInfoEntry 5 }

ipMgmtRouteInfoType OBJECT-TYPE
    SYNTAX  INTEGER {
        indirect(1),
        direct(2),
        local(3),
        broadcast(4),
        martian(5),
        multicast(6),
        other(7)
        }
    MAX-ACCESS  read-only
    STATUS  current
    DESCRIPTION
        "The type of the route."
    ::= { ipMgmtRouteInfoEntry 6 }

ipMgmtRouteInfoInterface OBJECT-TYPE
    SYNTAX  Integer32
    MAX-ACCESS  read-only
    STATUS  current
    DESCRIPTION
        "The interface number for which the destination address is applicable."
    ::= { ipMgmtRouteInfoEntry 7 }

ipMgmtRouteInfoGateway1 OBJECT-TYPE
    SYNTAX  IpAddress
    MAX-ACCESS  read-only
    STATUS  current
    DESCRIPTION
        "The next-hop router address for this route."
    ::= { ipMgmtRouteInfoEntry 8 }

ipMgmtRouteInfoGateway2 OBJECT-TYPE
    SYNTAX  IpAddress
    MAX-ACCESS  read-only
    STATUS  current
    DESCRIPTION
        "The next-hop router address for this route."
    ::= { ipMgmtRouteInfoEntry 9 }

ipMgmtRouteInfoMetric OBJECT-TYPE
    SYNTAX Integer32
    MAX-ACCESS  read-only
    STATUS  current
    DESCRIPTION
        "The Metric for this route."
    ::= { ipMgmtRouteInfoEntry 10 }

ipDataRouteInfoTable OBJECT-TYPE
    SYNTAX  SEQUENCE OF IpDataRouteInfoEntry
    MAX-ACCESS  not-accessible
    STATUS  current
    DESCRIPTION
        "The table of run-time IP routes."
    ::= { ipRoutingInfo 1 }

ipDataRouteInfoEntry OBJECT-TYPE
    SYNTAX  IpDataRouteInfoEntry
    MAX-ACCESS  not-accessible
    STATUS  current
    DESCRIPTION
        "A row in the run-time IP route table"
    INDEX   { ipDataRouteInfoIndx }
    ::= { ipDataRouteInfoTable 1 }

IpDataRouteInfoEntry ::= SEQUENCE {
    ipDataRouteInfoIndx             Integer32,
    ipDataRouteInfoDestIp           IpAddress,
    ipDataRouteInfoMask             IpAddress,
    ipDataRouteInfoGateway          IpAddress,
    ipDataRouteInfoTag              INTEGER,
    ipDataRouteInfoType             INTEGER,
    ipDataRouteInfoInterface        Integer32,
    ipDataRouteInfoGateway1         IpAddress,
    ipDataRouteInfoGateway2         IpAddress,
    ipDataRouteInfoMetric           Integer32
    }

ipDataRouteInfoIndx OBJECT-TYPE
    SYNTAX  Integer32
    MAX-ACCESS  read-only
    STATUS  current
    DESCRIPTION
        "The index of this route table."
    ::= { ipDataRouteInfoEntry 1 }

ipDataRouteInfoDestIp OBJECT-TYPE
    SYNTAX  IpAddress
    MAX-ACCESS  read-only
    STATUS  current
    DESCRIPTION
        "The destination IP address of this route."
    ::= { ipDataRouteInfoEntry 2 }

ipDataRouteInfoMask OBJECT-TYPE
    SYNTAX  IpAddress
    MAX-ACCESS  read-only
    STATUS  current
    DESCRIPTION
        "The destination IP mask of this route."
    ::= { ipDataRouteInfoEntry 3 }

ipDataRouteInfoGateway OBJECT-TYPE
    SYNTAX  IpAddress
    MAX-ACCESS  read-only
    STATUS  current
    DESCRIPTION
        "The next-hop router address for this route."
    ::= { ipDataRouteInfoEntry 4 }

ipDataRouteInfoTag OBJECT-TYPE
    SYNTAX  INTEGER {
        fixed(1),
        static(2),
        addr(3),
        rip(4),
        broadcast(5),
        martian(6),
        multicast(7),
        vip(8),
        bgp(9),
        ospf(10),
        none(11)
        }
    MAX-ACCESS  read-only
    STATUS  current
    DESCRIPTION
        "The tag-type for this route."
    ::= { ipDataRouteInfoEntry 5 }

ipDataRouteInfoType OBJECT-TYPE
    SYNTAX  INTEGER {
        indirect(1),
        direct(2),
        local(3),
        broadcast(4),
        martian(5),
        multicast(6),
        other(7)
        }
    MAX-ACCESS  read-only
    STATUS  current
    DESCRIPTION
        "The type of the route."
    ::= { ipDataRouteInfoEntry 6 }

ipDataRouteInfoInterface OBJECT-TYPE
    SYNTAX  Integer32
    MAX-ACCESS  read-only
    STATUS  current
    DESCRIPTION
        "The interface number for which the destination address is applicable.
        Loopback interfaces are numbered starting with maximum allowed 
        IP interfaces +1." 
    ::= { ipDataRouteInfoEntry 7 }

ipDataRouteInfoGateway1 OBJECT-TYPE
    SYNTAX  IpAddress
    MAX-ACCESS  read-only
    STATUS  current
    DESCRIPTION
        "The next-hop router address for this route."
    ::= { ipDataRouteInfoEntry 8 }

ipDataRouteInfoGateway2 OBJECT-TYPE
    SYNTAX  IpAddress
    MAX-ACCESS  read-only
    STATUS  current
    DESCRIPTION
        "The next-hop router address for this route."
    ::= { ipDataRouteInfoEntry 9 }

ipDataRouteInfoMetric OBJECT-TYPE
    SYNTAX Integer32
    MAX-ACCESS  read-only
    STATUS  current
    DESCRIPTION
        "The Metric for this route."
    ::= { ipDataRouteInfoEntry 10 }


routeTableClear OBJECT-TYPE
    SYNTAX  INTEGER {
        ok(1),
        clear(2)
        }
    MAX-ACCESS  read-write
    STATUS  current 
    DESCRIPTION
        "Setting this value to clear(2) clears the route table."
    ::= { ipRoutingInfo 2 }


ipRouteEcmpInfoTable OBJECT-TYPE
    SYNTAX  SEQUENCE OF IpRouteEcmpInfoEntry
    MAX-ACCESS  not-accessible
    STATUS  current
    DESCRIPTION
        "The table of run-time IP routes."
    ::= { ipEcmpRoutingInfo 1 }
    
ipRouteEcmpInfoEntry OBJECT-TYPE
    SYNTAX  IpRouteEcmpInfoEntry
    MAX-ACCESS  not-accessible
    STATUS  current
    DESCRIPTION
        "A row in the run-time IP route table"
    INDEX   { ipRouteEcmpInfoDestIndx, ipRouteEcmpInfoGwIndx }
    ::= { ipRouteEcmpInfoTable 1 }
    
IpRouteEcmpInfoEntry ::= SEQUENCE {
    ipRouteEcmpInfoDestIndx     Integer32,
    ipRouteEcmpInfoGwIndx   Integer32,
    ipRouteEcmpInfoDest         IpAddress,
    ipRouteEcmpInfoMask         IpAddress,
    ipRouteEcmpInfoGateway      IpAddress,
    ipRouteEcmpInfoInterface    Integer32,
    ipRouteEcmpInfoGwStatus     INTEGER
    }


ipRouteEcmpInfoDestIndx OBJECT-TYPE
    SYNTAX  Integer32
    MAX-ACCESS  read-only
    STATUS  current
    DESCRIPTION
        "The index of unique destinations IP."
    ::= { ipRouteEcmpInfoEntry 1 }  
    
ipRouteEcmpInfoGwIndx OBJECT-TYPE
    SYNTAX  Integer32
    MAX-ACCESS  read-only
    STATUS  current
    DESCRIPTION
        "The index of the gateway per destination."
    ::= { ipRouteEcmpInfoEntry 2 }

ipRouteEcmpInfoDest OBJECT-TYPE
    SYNTAX  IpAddress
    MAX-ACCESS  read-only
    STATUS  current
    DESCRIPTION
        "The destination IP of this route."
    ::= { ipRouteEcmpInfoEntry 3 }
    
ipRouteEcmpInfoMask OBJECT-TYPE
    SYNTAX  IpAddress
    MAX-ACCESS  read-only
    STATUS  current
    DESCRIPTION
        "The destination IP mask of this route."
    ::= { ipRouteEcmpInfoEntry 4 }
 
ipRouteEcmpInfoGateway OBJECT-TYPE
    SYNTAX  IpAddress
    MAX-ACCESS  read-only
    STATUS  current
    DESCRIPTION
        "The next-hop router address for this route."
    ::= { ipRouteEcmpInfoEntry 5 }
    
ipRouteEcmpInfoInterface OBJECT-TYPE
    SYNTAX  Integer32
    MAX-ACCESS  read-only
    STATUS  current
    DESCRIPTION
        "The interface for the next-hop."
    ::= { ipRouteEcmpInfoEntry 6 }
 
ipRouteEcmpInfoGwStatus OBJECT-TYPE
    SYNTAX  INTEGER { 
    up(1),
    down(2)
    }
    MAX-ACCESS  read-only
    STATUS  current
    DESCRIPTION
        "The Up/Down status of the gateway"
    ::= { ipRouteEcmpInfoEntry 7 }


ipEcmpHashSIPAddr OBJECT-TYPE
    SYNTAX  IpAddress
    MAX-ACCESS  read-write
    STATUS  current
    DESCRIPTION
        "The SIP Address."
    ::= { ipEcmpHash 1 }
    
ipEcmpHashDIPAddr OBJECT-TYPE
    SYNTAX  IpAddress
    MAX-ACCESS  read-write
    STATUS  current
    DESCRIPTION
        "The DIP Address (enter 0 for SIP only)."
    ::= { ipEcmpHash 2 }

ipEcmpHashNumberPaths OBJECT-TYPE
    SYNTAX INTEGER (2..5) 
    MAX-ACCESS  read-write
    STATUS  current
    DESCRIPTION
        "The number of ECMP paths."
    ::= { ipEcmpHash 3 }

ipEcmpHashRouteNumber OBJECT-TYPE
    SYNTAX  Integer32
    MAX-ACCESS  read-only
    STATUS  current
    DESCRIPTION
        "The result of the hash algorithm. 
        For this to work the values for ipEcmpHashSIPAddr,
        ipEcmpHashDIPAddr, ipEcmpHashNumberPaths must be set.
        If the result is 0 ipEcmpHashNumberPaths is not correctly set."
    ::= { ipEcmpHash 4 }
    


mldInfoGroupsTable OBJECT-TYPE
    SYNTAX SEQUENCE OF MldInfoGroupEntry
    MAX-ACCESS not-accessible
    STATUS current
    DESCRIPTION
      "The table listing the IPv6 multicast
       groups for which there are members on a particular interface."
    ::= { mldInfo 1 }
        
mldInfoGroupEntry OBJECT-TYPE
    SYNTAX     MldInfoGroupEntry
    MAX-ACCESS not-accessible
    STATUS     current
    DESCRIPTION
      "An entry in the mldInfoGroupsTable"
    INDEX      { mldInfoGroupId }
    ::= { mldInfoGroupsTable 1 }
       
MldInfoGroupEntry ::= SEQUENCE {
    mldInfoGroupIfIndex         	Integer32,
    mldInfoGroupAddress         	InetAddressIPv6,
    mldInfoGroupPortNumber       	Integer32,
    mldInfoGroupVlanID        	    Integer32,
    mldInfoGroupLastReporter   	InetAddressIPv6,
    mldInfoGroupSource             InetAddressIPv6,
    mldInfoGroupFilterType         DisplayString,
    mldInfoGroupExpiryTime       	DisplayString,
    mldInfoGroupVersion            Integer32,
    mldInfoGroupFwd                Integer32,
    mldInfoGroupId                 Integer32
}

mldInfoGroupIfIndex OBJECT-TYPE
    SYNTAX     Integer32
    MAX-ACCESS read-only
    STATUS     current
    DESCRIPTION
      "The internetwork-layer interface for which this entry
       contains information for an IPv6 multicast group address."
    ::= { mldInfoGroupEntry 1 }

mldInfoGroupAddress OBJECT-TYPE
    SYNTAX     InetAddressIPv6
    MAX-ACCESS read-only
    STATUS     current
    DESCRIPTION
      "The IPv6 multicast group address for which this entry
       contains information. Its address MUST be of format:
       2x:2x:2x:2x:2x:2x:2x:2x"
    ::= { mldInfoGroupEntry 2 }

mldInfoGroupPortNumber OBJECT-TYPE
    SYNTAX Integer32
    MAX-ACCESS read-only
    STATUS     current
    DESCRIPTION  "The port number for which this entry
       contains information for an IPv6 multicast group address."
    ::= { mldInfoGroupEntry 3 }

mldInfoGroupVlanID OBJECT-TYPE
    SYNTAX Integer32
    MAX-ACCESS read-only
    STATUS     current
    DESCRIPTION  "The VLAN ID for which this entry
       contains information for an IPv6 multicast group address."
    ::= { mldInfoGroupEntry 4 }

mldInfoGroupLastReporter OBJECT-TYPE
    SYNTAX     InetAddressIPv6
    MAX-ACCESS read-only
    STATUS     current
    DESCRIPTION
      "The IPv6 address of the source of the last membership
       report received for this IPv6 Multicast group address on
       this interface.  If no membership report has been
       received, this object has the value 00:0:00:00:00:00:00:00.
       Its address MUST be of format:2x:2x:2x:2x:2x:2x:2x:2x"
    ::= { mldInfoGroupEntry 5 }

mldInfoGroupSource OBJECT-TYPE
    SYNTAX     InetAddressIPv6
    MAX-ACCESS read-only
    STATUS     current
    DESCRIPTION
      "ONLY for MLDv2. The IPv6 address for which the this entry's
      filter is applied. Its address MUST be of format:
      2x:2x:2x:2x:2x:2x:2x:2x"
    ::= { mldInfoGroupEntry 6 }

mldInfoGroupFilterType OBJECT-TYPE
    SYNTAX DisplayString
    MAX-ACCESS read-only
    STATUS     current
    DESCRIPTION  "ONLY for MLDv2. The filter type for the specified source."
    ::= { mldInfoGroupEntry 7 }
	
mldInfoGroupExpiryTime OBJECT-TYPE
    SYNTAX     DisplayString
    MAX-ACCESS read-only
    STATUS     current
    DESCRIPTION
      "The minimum amount of time remaining before this entry
       will be aged out.  A value of 0 indicates that the entry
       is only present because mldCacheSelf is true and that if
       the router left the group, this entry would be aged out
       immediately.  Note that some implementations may process
       Membership Reports from the local system in the same way
       as reports from other hosts, so a value of 0 is not
       required."
    ::= { mldInfoGroupEntry 8 }

mldInfoGroupVersion OBJECT-TYPE
    SYNTAX Integer32
    MAX-ACCESS read-only
    STATUS     current
    DESCRIPTION  "The version of this MLD entry."
    ::= { mldInfoGroupEntry 9 }

mldInfoGroupFwd OBJECT-TYPE
    SYNTAX Integer32
    MAX-ACCESS read-only
    STATUS     current
    DESCRIPTION  "Specifies if forwarding is enabled for this entry."
    ::= { mldInfoGroupEntry 10 }

mldInfoGroupId OBJECT-TYPE
    SYNTAX Integer32
    MAX-ACCESS read-only
    STATUS     current
    DESCRIPTION  "MLD group index."
    ::= { mldInfoGroupEntry 11 }

mldInfoMRoutersTable OBJECT-TYPE
    SYNTAX SEQUENCE OF MldInfoMRouterEntry
    MAX-ACCESS not-accessible
    STATUS current
    DESCRIPTION
      "The table listing the IPv6 multicast routers on an interface."
    ::= { mldInfo 2 }
		
mldInfoMRouterEntry OBJECT-TYPE
    SYNTAX     MldInfoMRouterEntry
    MAX-ACCESS not-accessible
    STATUS     current
    DESCRIPTION
      "An entry in the mldInfoMRoutersTable"
    INDEX      { mldInfoMRouterId }
    ::= { mldInfoMRoutersTable 1 }
	   
MldInfoMRouterEntry ::= SEQUENCE {
    mldInfoMRouterIfIndex         	Integer32,
    mldInfoMRouterSrcIp         	InetAddressIPv6,
    mldInfoMRouterPortNumber       	Integer32,
    mldInfoMRouterVlan        	    Integer32,
    mldInfoMRouterQrv               Integer32,
    mldInfoMRouterQqic              Integer32,
    mldInfoMRouterMaxRespDelay      Integer32,
    mldInfoMRouterVersion           Integer32,
    mldInfoMRouterExpiryTime       	DisplayString,
    mldInfoMRouterId                Integer32
}

mldInfoMRouterIfIndex OBJECT-TYPE
    SYNTAX     Integer32
    MAX-ACCESS read-only
    STATUS     current
    DESCRIPTION
      "The interface on which the multicast router is learnt."
    ::= { mldInfoMRouterEntry 1 }

mldInfoMRouterSrcIp OBJECT-TYPE
    SYNTAX     InetAddressIPv6
    MAX-ACCESS read-only
    STATUS     current
    DESCRIPTION
      "The multicast router's ip."
    ::= { mldInfoMRouterEntry 2 }

mldInfoMRouterPortNumber OBJECT-TYPE
    SYNTAX     Integer32
    MAX-ACCESS read-only
    STATUS     current
    DESCRIPTION
      "The port on which the multicast router is learnt."
    ::= { mldInfoMRouterEntry 3 }

mldInfoMRouterVlan OBJECT-TYPE
    SYNTAX     Integer32
    MAX-ACCESS read-only
    STATUS     current
    DESCRIPTION
      "The vlan in which the multicast router is learnt."
    ::= { mldInfoMRouterEntry 4 }

mldInfoMRouterQrv OBJECT-TYPE
    SYNTAX     Integer32
    MAX-ACCESS read-only
    STATUS     current
    DESCRIPTION
      "This multicast router's Maximum Response Delay"
    ::= { mldInfoMRouterEntry 5 }

mldInfoMRouterQqic OBJECT-TYPE
    SYNTAX     Integer32
    MAX-ACCESS read-only
    STATUS     current
    DESCRIPTION
      "ONLY for MLDv2. This multicast router's QQIC"
    ::= { mldInfoMRouterEntry 6 }

mldInfoMRouterMaxRespDelay OBJECT-TYPE
    SYNTAX     Integer32
    MAX-ACCESS read-only
    STATUS     current
    DESCRIPTION
      "This multicast router's Maximum Response Delay."
    ::= { mldInfoMRouterEntry 7 }

mldInfoMRouterVersion OBJECT-TYPE
    SYNTAX     Integer32
    MAX-ACCESS read-only
    STATUS     current
    DESCRIPTION
      "This multicast router's MLD version."
    ::= { mldInfoMRouterEntry 8 }

mldInfoMRouterExpiryTime OBJECT-TYPE
    SYNTAX     DisplayString
    MAX-ACCESS read-only
    STATUS     current
    DESCRIPTION
      "This multicast router's expiry time."
    ::= { mldInfoMRouterEntry 9 }
	
mldInfoMRouterId OBJECT-TYPE
    SYNTAX     Integer32
    MAX-ACCESS read-only
    STATUS     current
    DESCRIPTION
      "This multicast router's index."
    ::= { mldInfoMRouterEntry 10 }


mldClearTables OBJECT-TYPE
    SYNTAX INTEGER {
        none(0),
        clearGroups(1),
        clearMrouters(2),
        clearAll(3)
    }
    MAX-ACCESS read-write
    STATUS current
    DESCRIPTION
        "Clear the MLD tables. When setting clearGroups(1), the dynamic
         groups are removed, when setting clearMrouters(2), the mrouter tables
         are removed and when setting clearAll(3), both the dynamic groups
         and the mrouter tables are removed.
         When read, none(0) is always returned."
    ::= { mldInfo 3 }

mldInfoInterfaceTable OBJECT-TYPE
    SYNTAX SEQUENCE OF MldInfoInterfaceEntry
    MAX-ACCESS not-accessible
    STATUS current
    DESCRIPTION
      "The (conceptual) table listing the informatio of interfaces on which
       MLD is enabled."
    ::= { mldInfo 4 }	
     
mldInfoInterfaceEntry OBJECT-TYPE
    SYNTAX     MldInfoInterfaceEntry
    MAX-ACCESS not-accessible
    STATUS     current
    DESCRIPTION
      "An entry (conceptual row) representing the information of an 
       interface on which MLD is enabled."
    INDEX      { mldInfoInterfaceIfIndex }
   ::= { mldInfoInterfaceTable 1 }
     
MldInfoInterfaceEntry ::= SEQUENCE {
    mldInfoInterfaceIfIndex                 Integer32,
    mldInfoInterfaceState                   INTEGER,
    mldInfoInterfaceVersion                 INTEGER,
    mldInfoInterfaceQuerierStatus           INTEGER,
    mldInfoInterfaceQuerier                 InetAddressIPv6,
    mldInfoInterfaceQuerierExpiryTime     	DisplayString,
    mldInfoInterfaceQuerierPort             Integer32,
    mldInfoInterfaceGroups                  INTEGER
}    
    
mldInfoInterfaceIfIndex OBJECT-TYPE
    SYNTAX     Integer32
    MAX-ACCESS read-only
    STATUS     current
    DESCRIPTION
      "The internetwork-layer interface value of the interface
       for which MLD is enabled."
    ::= { mldInfoInterfaceEntry 1 }
       
mldInfoInterfaceState OBJECT-TYPE
    SYNTAX INTEGER {
      up(1),
      down(2)
    }
    MAX-ACCESS  read-only 
    STATUS     current
    DESCRIPTION
      "The internetwork-layer interface value of the interface
       for which MLD is enabled."
    ::= { mldInfoInterfaceEntry 2 }    
       
mldInfoInterfaceVersion OBJECT-TYPE
    SYNTAX     INTEGER
    MAX-ACCESS read-only
    STATUS     current
    DESCRIPTION
      "The version of MLD which is running on this interface.
       This object is a place holder to allow for new versions
       of MLD to be introduced.  Version 1 of MLD is defined
       in RFC 2710."
    DEFVAL     { 1 }
    ::= { mldInfoInterfaceEntry 3 }    
       
mldInfoInterfaceQuerierStatus OBJECT-TYPE
    SYNTAX     INTEGER
    MAX-ACCESS read-only
    STATUS     current
    DESCRIPTION
      "Specifies if the switch is Querier or not"
    ::= { mldInfoInterfaceEntry 4 }

mldInfoInterfaceQuerier OBJECT-TYPE
    SYNTAX     InetAddressIPv6 
    MAX-ACCESS read-only
    STATUS     current
    DESCRIPTION
      "The address of the MLD Querier on the IPv6 subnet to
       which this interface is attached. 
       Its address MUST be of format:2x:2x:2x:2x:2x:2x:2x:2x"
    ::= { mldInfoInterfaceEntry 5 }
	
mldInfoInterfaceQuerierExpiryTime OBJECT-TYPE
    SYNTAX     DisplayString
    MAX-ACCESS read-only
    STATUS     current
    DESCRIPTION
      "The time remaining before the Other Querier Present
       Timer expires.  If the local system is the querier,
       the value of this object is zero."
    ::= { mldInfoInterfaceEntry 6 }

mldInfoInterfaceQuerierPort OBJECT-TYPE
    SYNTAX     Integer32
    MAX-ACCESS read-only
    STATUS     current
    DESCRIPTION
      "The port on which the Querier is learnt.
       If the local system is the querier,
       the value of this object is zero."
    ::= { mldInfoInterfaceEntry 7 }
	
mldInfoInterfaceGroups OBJECT-TYPE
    SYNTAX     INTEGER
    MAX-ACCESS read-only
    STATUS     current
    DESCRIPTION
      "The current number of entries for this interface in the
       Cache Table."
    ::= { mldInfoInterfaceEntry 8 }


-- Run Time ARP Table

arpInfoTable OBJECT-TYPE
    SYNTAX  SEQUENCE OF AgArpInfoEntry
    MAX-ACCESS  not-accessible
    STATUS  current
    DESCRIPTION
        "The table of ARP entries."
    ::= { arpInfo 1 }

arpInfoEntry OBJECT-TYPE
    SYNTAX  AgArpInfoEntry
    MAX-ACCESS  not-accessible
    STATUS  current
    DESCRIPTION
        "A row in the ARP table"
    INDEX   { arpInfoDestIp }
    ::= { arpInfoTable 1 }

AgArpInfoEntry ::= SEQUENCE {
    arpInfoDestIp         IpAddress,
    arpInfoMacAddr        PhysAddress,
    arpInfoVLAN           Integer32,
    arpInfoSrcPort        PortNumber,
    arpInfoFlag           INTEGER
    }

arpInfoDestIp OBJECT-TYPE
    SYNTAX  IpAddress
    MAX-ACCESS  read-only
    STATUS  current
    DESCRIPTION
        "The destination IP address of the ARP entry."
    ::= { arpInfoEntry 1 }

arpInfoMacAddr OBJECT-TYPE
    SYNTAX  PhysAddress
    MAX-ACCESS  read-only
    STATUS  current
    DESCRIPTION
        "The MAC address for the ARP entry."
    ::= { arpInfoEntry 2 }

arpInfoVLAN OBJECT-TYPE 
    SYNTAX  Integer32 
    MAX-ACCESS  read-only 
    STATUS  current 
    DESCRIPTION 
        "The VLAN identifier for the ARP entry." 
    ::= { arpInfoEntry 3 }

arpInfoSrcPort OBJECT-TYPE  
    SYNTAX  PortNumber 
    MAX-ACCESS  read-only  
    STATUS  current  
    DESCRIPTION  
        "The  port number on which this entry's equivalence is effective."  
    ::= { arpInfoEntry 4 }


arpInfoFlag OBJECT-TYPE   
    SYNTAX  INTEGER {
    clear(1),
    unresolved(2),
    permanent(3),
    indirect(4),
    layer4(5)
    }
    MAX-ACCESS  read-only   
    STATUS  current   
    DESCRIPTION   
        "The flag associated with this ARP entry."   
    ::= { arpInfoEntry 6 }




arpCacheClear OBJECT-TYPE
    SYNTAX  INTEGER {
        ok(1),
        clear(2)
        }
    MAX-ACCESS  read-write
    STATUS  current 
    DESCRIPTION
        "Setting this value to clear(2) clears the ARP cache."
    ::= { arpInfo 2 }


-- VRRP Information

vrrpInfoVirtRtrTable OBJECT-TYPE
    SYNTAX  SEQUENCE OF VrrpInfoVirtRtrTableEntry
    MAX-ACCESS  not-accessible
    STATUS  current
    DESCRIPTION
        "The table of VRRP virtual router run-time information."
    ::= { vrrpInfo 1 }

vrrpInfoVirtGroupState OBJECT-TYPE
    SYNTAX  DisplayString (SIZE(1..128))
    MAX-ACCESS  read-only
    STATUS  current
    DESCRIPTION
        "VRRP group state."
    ::= { vrrpInfo 2 }

vrrpInfoVirtGroupPriority OBJECT-TYPE
    SYNTAX  Integer32
    MAX-ACCESS  read-only
    STATUS  current
    DESCRIPTION
        "VRRP group priority."
    ::= { vrrpInfo 3 }


vrrpInfoVirtRtrTableEntry OBJECT-TYPE
    SYNTAX  VrrpInfoVirtRtrTableEntry
    MAX-ACCESS  not-accessible
    STATUS  current
    DESCRIPTION
        "The run-time information about a VRRP virtual router."
    INDEX   { vrrpInfoVirtRtrIndex }
    ::= { vrrpInfoVirtRtrTable 1 }
 
VrrpInfoVirtRtrTableEntry ::= SEQUENCE {
    vrrpInfoVirtRtrIndex      Integer32,
    vrrpInfoVirtRtrState      INTEGER,
    vrrpInfoVirtRtrOwnership  INTEGER,
    vrrpInfoVirtRtrConfig     INTEGER,
    vrrpInfoVirtRtrID         INTEGER,
    vrrpInfoVirtRtrAddr       IpAddress,
    vrrpInfoVirtRtrIfIndex    Integer32,
    vrrpInfoVirtRtrPriority   INTEGER
    }

vrrpInfoVirtRtrIndex OBJECT-TYPE
    SYNTAX  Integer32
    MAX-ACCESS  read-only
    STATUS  current
    DESCRIPTION
        "The VRRP virtual router index." 
    ::= { vrrpInfoVirtRtrTableEntry 1 }

vrrpInfoVirtRtrState OBJECT-TYPE   
    SYNTAX  INTEGER {
    init(1),
    master(2),
    backup(3),
    holdoff(4)
    }
    MAX-ACCESS  read-only   
    STATUS  current   
    DESCRIPTION   
        "The VRRP virtual router state."   
    ::= { vrrpInfoVirtRtrTableEntry 2 }

vrrpInfoVirtRtrOwnership OBJECT-TYPE   
    SYNTAX  INTEGER {
    owner(1),
    renter(2)
    }
    MAX-ACCESS  read-only   
    STATUS  current   
    DESCRIPTION   
        "The VRRP virtual router ownership status."   
    ::= { vrrpInfoVirtRtrTableEntry 3 }

vrrpInfoVirtRtrConfig OBJECT-TYPE
    SYNTAX  INTEGER {
        enabled(1),
        disabled(2)
        }
    MAX-ACCESS  read-only
    STATUS  current
    DESCRIPTION
        "The status of the VRRP virtual router."
    ::= { vrrpInfoVirtRtrTableEntry 4 }

vrrpInfoVirtRtrID OBJECT-TYPE
    SYNTAX  INTEGER (1..255)
    MAX-ACCESS  read-only
    STATUS  current
    DESCRIPTION
        "The VRRP virtual router identifier."
    ::= { vrrpInfoVirtRtrTableEntry 5 }

vrrpInfoVirtRtrAddr OBJECT-TYPE
    SYNTAX  IpAddress
    MAX-ACCESS  read-only
    STATUS  current
    DESCRIPTION
        "The VRRP virtual router IP address."
    ::= { vrrpInfoVirtRtrTableEntry 6 }

vrrpInfoVirtRtrIfIndex OBJECT-TYPE
    SYNTAX  Integer32
    MAX-ACCESS  read-only
    STATUS  current
    DESCRIPTION
        "The IfIndex that the VRRP virtual router is representing."
    ::= { vrrpInfoVirtRtrTableEntry 7 }

vrrpInfoVirtRtrPriority OBJECT-TYPE
    SYNTAX  INTEGER (1..254)
    MAX-ACCESS  read-only
    STATUS  current
    DESCRIPTION
        "The priority value to be used by the specified VRRP virtual routers."
    ::= { vrrpInfoVirtRtrTableEntry 8 }



-- Ospf Information 

ospfGeneralInfo  OBJECT IDENTIFIER ::= { ospfinfo 1 }

ospfStartTime OBJECT-TYPE   
    SYNTAX  TimeTicks
    MAX-ACCESS  read-only   
    STATUS  current   
    DESCRIPTION   
        "The time when ospf has been started."   
    ::= { ospfGeneralInfo 1 }

ospfProcessUptime OBJECT-TYPE   
    SYNTAX  TimeTicks
    MAX-ACCESS  read-only   
    STATUS  current   
    DESCRIPTION   
        "The time since ospf has been started."   
    ::= { ospfGeneralInfo 2 }

ospfLsTypesSupported OBJECT-TYPE   
    SYNTAX  Integer32 
    MAX-ACCESS  read-only   
    STATUS  current   
    DESCRIPTION   
        "The Link State Types that are supported."   
    ::= { ospfGeneralInfo 3 }

ospfIntfCountForRouter OBJECT-TYPE   
    SYNTAX  Integer32 
    MAX-ACCESS  read-only   
    STATUS  current   
    DESCRIPTION   
        "The number of interfaces for this router." 
    ::= { ospfGeneralInfo 4 }

ospfVlinkCountForRouter OBJECT-TYPE   
    SYNTAX  Integer32 
    MAX-ACCESS  read-only   
    STATUS  current   
    DESCRIPTION   
        "The number of virtual links for this router." 
    ::= { ospfGeneralInfo 5 }

ospfTotalNeighbours OBJECT-TYPE   
    SYNTAX  Integer32 
    MAX-ACCESS  read-only   
    STATUS  current   
    DESCRIPTION   
        "The total number of OSPF neighbours." 
    ::= { ospfGeneralInfo 6 }

ospfNbrInInitState OBJECT-TYPE   
    SYNTAX  Integer32 
    MAX-ACCESS  read-only   
    STATUS  current   
    DESCRIPTION   
        "The number of neighbours in the initial state of exchange." 
    ::= { ospfGeneralInfo 7 }

ospfNbrInExchState OBJECT-TYPE   
    SYNTAX  Integer32 
    MAX-ACCESS  read-only   
    STATUS  current   
    DESCRIPTION   
        "The number of neighbours in the exchange state." 
    ::= { ospfGeneralInfo 8 }

ospfNbrInFullState OBJECT-TYPE   
    SYNTAX  Integer32 
    MAX-ACCESS  read-only   
    STATUS  current   
    DESCRIPTION   
        "The number of neighbours in the Full state of exchange." 
    ::= { ospfGeneralInfo 9 }

ospfTotalAreas OBJECT-TYPE   
    SYNTAX  Integer32 
    MAX-ACCESS  read-only   
    STATUS  current   
    DESCRIPTION   
        "The Total number of areas." 
    ::= { ospfGeneralInfo 10 }

ospfTotalTransitAreas OBJECT-TYPE   
    SYNTAX  Integer32 
    MAX-ACCESS  read-only   
    STATUS  current   
    DESCRIPTION   
        "The Total number of Transit areas." 
    ::= { ospfGeneralInfo 11 }

ospfTotalNssaAreas OBJECT-TYPE   
    SYNTAX  Integer32 
    MAX-ACCESS  read-only   
    STATUS  current   
    DESCRIPTION   
        "The Total number of NSSA areas." 
    ::= { ospfGeneralInfo 12 }

ospfTotalStubAreas OBJECT-TYPE
    SYNTAX  Integer32
    MAX-ACCESS  read-only
    STATUS  current
    DESCRIPTION
        "The Total number of STUB areas."
    ::= { ospfGeneralInfo 13 }

ospfAreaInfoTable OBJECT-TYPE
    SYNTAX SEQUENCE OF OspfAreaInfoEntry
    MAX-ACCESS not-accessible
    STATUS current
    DESCRIPTION
      "The table of OSPF Area information."
    ::= { ospfinfo 2 }

ospfAreaInfoEntry OBJECT-TYPE
    SYNTAX OspfAreaInfoEntry
    MAX-ACCESS not-accessible
    STATUS current
    DESCRIPTION
      "Information about a OSPF area."
    INDEX { ospfAreaInfoIndex }
    ::= { ospfAreaInfoTable 1 }
 
OspfAreaInfoEntry ::= SEQUENCE {
    ospfAreaInfoIndex               Integer32,
    ospfAreaInfoId                  IpAddress,
    ospfTotalNumberOfInterfaces     Integer32,
    ospfNumberOfInterfacesUp        Integer32,
    ospfNumberOfLsdbEntries         Integer32,
    ospfAreaInfoAuthType            INTEGER,
    ospfAreaInfoLsTypesAccepted     DisplayString,
    ospfAreaInfoSPF                 Integer32,
    ospfAreaInfoAreaBorderRouter    Integer32,
    ospfAreaInfoASBoundaryRouter    Integer32,
    ospfAreaInfoTotalNeighbours     Integer32,
    ospfAreaInfoNeighborsINITstate      Integer32,
    ospfAreaInfoNeighborsEXCHstate      Integer32,
    ospfAreaInfoNeighborsFULLstate      Integer32
    }
 
ospfAreaInfoIndex OBJECT-TYPE
    SYNTAX Integer32
    MAX-ACCESS read-only
    STATUS current
    DESCRIPTION
    "The OSPF area number for which the OSPF info table is related."
    ::= { ospfAreaInfoEntry 1}

ospfAreaInfoId OBJECT-TYPE
    SYNTAX IpAddress
    MAX-ACCESS read-only
    STATUS current
    DESCRIPTION
        "The IP address of the OSPF area."
    ::= { ospfAreaInfoEntry 2 }

ospfTotalNumberOfInterfaces OBJECT-TYPE
    SYNTAX Integer32
    MAX-ACCESS read-only
    STATUS current
    DESCRIPTION
        "The total number of interfaces for this OSPF area."
    ::= { ospfAreaInfoEntry 3 }

ospfNumberOfInterfacesUp OBJECT-TYPE
    SYNTAX Integer32
    MAX-ACCESS read-only
    STATUS current
    DESCRIPTION
        "The number of interfaces UP in area."
    ::= { ospfAreaInfoEntry 4 }

ospfNumberOfLsdbEntries OBJECT-TYPE
    SYNTAX Integer32
    MAX-ACCESS read-only
    STATUS current
    DESCRIPTION
        "The number of Link State Database entries for this OSPF area."
    ::= { ospfAreaInfoEntry 5 }

ospfAreaInfoAuthType OBJECT-TYPE
    SYNTAX INTEGER {
        none(1),
        password(2),
        md5(3)
        }
    MAX-ACCESS read-only
    STATUS current
    DESCRIPTION
        "Area authentication."
    ::= { ospfAreaInfoEntry 6 }

ospfAreaInfoLsTypesAccepted OBJECT-TYPE
    SYNTAX DisplayString  (SIZE(0..40))
    MAX-ACCESS read-only
    STATUS current
    DESCRIPTION
        "LS types accepted by this area."
    ::= { ospfAreaInfoEntry 7 }

ospfAreaInfoSPF OBJECT-TYPE
    SYNTAX Integer32
    MAX-ACCESS read-only
    STATUS current
    DESCRIPTION
        "Number of times SPF algorithm has been executed."
    ::= { ospfAreaInfoEntry 8 }

ospfAreaInfoAreaBorderRouter OBJECT-TYPE
    SYNTAX Integer32
    MAX-ACCESS read-only
    STATUS current
    DESCRIPTION
        "Count of ABR local to this area."
    ::= { ospfAreaInfoEntry 9 }

ospfAreaInfoASBoundaryRouter OBJECT-TYPE
    SYNTAX Integer32
    MAX-ACCESS read-only
    STATUS current
    DESCRIPTION
        "Count of ASBR local to this area."
    ::= { ospfAreaInfoEntry 10 }

ospfAreaInfoTotalNeighbours OBJECT-TYPE
    SYNTAX  Integer32
    MAX-ACCESS  read-only
    STATUS  current
    DESCRIPTION
        "The total number of OSPF neighbors."
    ::= { ospfAreaInfoEntry 11 }

 ospfAreaInfoNeighborsINITstate OBJECT-TYPE
    SYNTAX Integer32
    MAX-ACCESS read-only
    STATUS current
    DESCRIPTION
        "Total neighbors in INIT state."
    ::= { ospfAreaInfoEntry 12 }

ospfAreaInfoNeighborsEXCHstate OBJECT-TYPE
    SYNTAX Integer32
    MAX-ACCESS read-only
    STATUS current
    DESCRIPTION
        "Total neighbors in EXCH state."
    ::= { ospfAreaInfoEntry 13 }

ospfAreaInfoNeighborsFULLstate OBJECT-TYPE
    SYNTAX Integer32
    MAX-ACCESS read-only
    STATUS current
    DESCRIPTION
        "Total neighbors in FULL state."
    ::= { ospfAreaInfoEntry 14 }

ospfIntfInfoTable OBJECT-TYPE
    SYNTAX SEQUENCE OF OspfIntfInfoEntry
    MAX-ACCESS not-accessible
    STATUS current
    DESCRIPTION
      "The table of OSPF Interface information."
    ::= { ospfinfo 3 }

ospfIntfInfoEntry OBJECT-TYPE
    SYNTAX OspfIntfInfoEntry
    MAX-ACCESS not-accessible
    STATUS current
    DESCRIPTION
      "Information about a OSPF interface."
    INDEX { ospfIfInfoIndex }
    ::= { ospfIntfInfoTable 1 }
 
OspfIntfInfoEntry ::= SEQUENCE {
    ospfIfInfoIndex                     Integer32,
    ospfIfInfoIpAddress                         IpAddress,
    ospfIfInfoArea                              INTEGER,
    ospfIfInfoAdminStatus                       INTEGER,
    ospfIfInfoPassive                           INTEGER,
    ospfIfInfoPtop                              INTEGER,
    ospfIfInfoRouterIP                          IpAddress,
    ospfIfInfoState                             INTEGER,
    ospfIfInfoPriority                          INTEGER,
    ospfIfInfoDesignatedRouterIP                IpAddress,
    ospfIfInfoDesignatedRouterIpAddress         IpAddress,
    ospfIfInfoBackupDesignatedRouterIP          IpAddress,
    ospfIfInfoBackupDesignatedRouterIpAddress   IpAddress,
    ospfIfInfoHello                             INTEGER,
    ospfIfInfoHelloMS                           INTEGER,
    ospfIfInfoDead                              INTEGER,
    ospfIfInfoDeadMS                            INTEGER,
    ospfIfInfoWaitInterval                      Integer32,
    ospfIfInfoWaitIntervalMS                    INTEGER,
    ospfIfInfoRetransmit                        INTEGER,
    ospfIfInfoTransitDelay                      INTEGER,
    ospfIfInfoTotalNeighbours                   Integer32,
    ospfIfInfoEvents                            Integer32,
    ospfIfInfoAuthType                          INTEGER
    }
 
ospfIfInfoIndex OBJECT-TYPE
    SYNTAX Integer32
    MAX-ACCESS read-only
    STATUS current
    DESCRIPTION
    "The OSPF interface number for which the OSPF info table is related."
    ::= { ospfIntfInfoEntry 1}

ospfIfInfoIpAddress OBJECT-TYPE
    SYNTAX IpAddress
    MAX-ACCESS read-only
    STATUS current
    DESCRIPTION
        "The IP address of the OSPF interface."
    ::= { ospfIntfInfoEntry 2 }

ospfIfInfoArea OBJECT-TYPE
    SYNTAX INTEGER (0..2)
    MAX-ACCESS read-only
    STATUS current
    DESCRIPTION
        "The index of the area that the interface belongs."
    ::= { ospfIntfInfoEntry 3 }

ospfIfInfoAdminStatus  OBJECT-TYPE
    SYNTAX  INTEGER {
        down(0),
        up(1)
        }
    MAX-ACCESS read-only
    STATUS current
    DESCRIPTION
        "Admin Status of the interface:
        down(0), up(1)."
    ::= { ospfIntfInfoEntry 4 }

ospfIfInfoPassive  OBJECT-TYPE
    SYNTAX  INTEGER {
        disabled(0),
        enabled(1)
        }
    MAX-ACCESS read-only
    STATUS current
    DESCRIPTION
        "Passive status of the interface:
        disabled(0), enabled(1)." 
    ::= { ospfIntfInfoEntry 5 }

ospfIfInfoPtop  OBJECT-TYPE
    SYNTAX  INTEGER {
        disabled(0),
        enabled(1)
        }
    MAX-ACCESS read-only
    STATUS current
    DESCRIPTION
        "Point-to-point status of the interface:
        disabled(0), enabled(1)." 
    ::= { ospfIntfInfoEntry 24 }

ospfIfInfoRouterIP OBJECT-TYPE
    SYNTAX IpAddress
    MAX-ACCESS read-only
    STATUS current
    DESCRIPTION
        "The router ID of the switch."
    ::= { ospfIntfInfoEntry 6 }

ospfIfInfoState  OBJECT-TYPE
    SYNTAX  INTEGER {
        down(0),
        loopback(1),
        waiting(2),
        ptop(3),
        dr(4),
        backupdr(5),
        drother(6)
        }
    MAX-ACCESS read-only
    STATUS current
    DESCRIPTION
        "The state of the interface:
        Down(0), Loopback(1),
        Waiting(2), P to P(3),
        DR(4), BackuDR(5),
        DR Other(6)."
    ::= { ospfIntfInfoEntry 7 }

ospfIfInfoPriority   OBJECT-TYPE
   SYNTAX INTEGER (1..255)
    MAX-ACCESS read-only
    STATUS current
    DESCRIPTION
        "Interface router priority"
    ::= { ospfIntfInfoEntry 8 }

ospfIfInfoDesignatedRouterIP OBJECT-TYPE
    SYNTAX IpAddress
    MAX-ACCESS read-only
    STATUS current
    DESCRIPTION
        "The OSPF Designated Router IP (IP Address) for this OSPF interface."
    ::= { ospfIntfInfoEntry 9 }

ospfIfInfoDesignatedRouterIpAddress OBJECT-TYPE
    SYNTAX IpAddress
    MAX-ACCESS read-only
    STATUS current
    DESCRIPTION
        "The OSPF Designated Router IP Address for this OSPF interface."
    ::= { ospfIntfInfoEntry 10 }

ospfIfInfoBackupDesignatedRouterIP OBJECT-TYPE
    SYNTAX IpAddress
    MAX-ACCESS read-only
    STATUS current
    DESCRIPTION
        "The OSPF Backup Designated Router IP for this OSPF
         interface."
    ::= { ospfIntfInfoEntry 11 }

ospfIfInfoBackupDesignatedRouterIpAddress OBJECT-TYPE
    SYNTAX IpAddress
    MAX-ACCESS read-only
    STATUS current
    DESCRIPTION
        "The OSPF Backup Designated Router Ip Address for this OSPF
         interface."
    ::= { ospfIntfInfoEntry 12 }

ospfIfInfoHello  OBJECT-TYPE
    SYNTAX INTEGER (1..65535)
    MAX-ACCESS read-only
    STATUS current
    DESCRIPTION
        "The hello timer for this OSPF interface."
    ::= { ospfIntfInfoEntry 13 }

ospfIfInfoHelloMS  OBJECT-TYPE
    SYNTAX  INTEGER {
        seconds(0),
        milliseconds(1)
        }
    MAX-ACCESS read-only
    STATUS current
    DESCRIPTION
    "Units of time measurement for Hello interval
    seconds(0),
        milliseconds(1)" 
    ::= { ospfIntfInfoEntry 14 }

ospfIfInfoDead   OBJECT-TYPE
   SYNTAX INTEGER (1..65535)
    MAX-ACCESS read-only
    STATUS current
    DESCRIPTION
        "The dead timer for this OSPF interface."
    ::= { ospfIntfInfoEntry 15 }

ospfIfInfoDeadMS  OBJECT-TYPE
    SYNTAX  INTEGER {
        seconds(0),
        milliseconds(1)
        }
    MAX-ACCESS read-only
    STATUS current
    DESCRIPTION
    "Units of time measurement for Dead interval
    seconds(0),
        milliseconds(1)" 
    ::= { ospfIntfInfoEntry 16 }

ospfIfInfoWaitInterval OBJECT-TYPE
    SYNTAX Integer32
    MAX-ACCESS read-only
    STATUS current
    DESCRIPTION
        "The OSPF Wait interval for this OSPF interface."
    ::= { ospfIntfInfoEntry 17 }

ospfIfInfoWaitIntervalMS  OBJECT-TYPE
    SYNTAX  INTEGER {
        seconds(0),
        milliseconds(1)
        }
    MAX-ACCESS read-only
    STATUS current
    DESCRIPTION
    "Units of time measurement for Wait interval
    seconds(0),
        milliseconds(1)" 
    ::= { ospfIntfInfoEntry 18 }

ospfIfInfoRetransmit OBJECT-TYPE
    SYNTAX INTEGER (1..3600)
    MAX-ACCESS read-only
    STATUS current
    DESCRIPTION
        "The retransmit interval for this OSPF interface."
    ::= { ospfIntfInfoEntry 19 }

ospfIfInfoTransitDelay  OBJECT-TYPE
   SYNTAX INTEGER (1..3600)
    MAX-ACCESS read-only
    STATUS current
    DESCRIPTION
        "The transit delay for this OSPF interface."
    ::= { ospfIntfInfoEntry 20 }

ospfIfInfoTotalNeighbours OBJECT-TYPE
    SYNTAX Integer32
    MAX-ACCESS read-only
    STATUS current
    DESCRIPTION
        "The Total number of neighbours for this OSPF interface."
    ::= { ospfIntfInfoEntry 21 }

ospfIfInfoEvents OBJECT-TYPE
    SYNTAX Integer32
    MAX-ACCESS read-only
    STATUS current
    DESCRIPTION
        "The total number of events for this OSPF interface."
    ::= { ospfIntfInfoEntry 22 }

ospfIfInfoAuthType OBJECT-TYPE
    SYNTAX  INTEGER {
        none(1),
        password(2),
        md5(3)
        }
    MAX-ACCESS  read-only
    STATUS  current
    DESCRIPTION
        "Type of authentication being used:
         none(1) - no authentication,
         password(2) - use password,
         md5(3) - use MD5 authentication."
    ::= { ospfIntfInfoEntry 23 }



-- OSPF Interface/Virtual Interface Table

ospfVirtIntfInfoTable OBJECT-TYPE
    SYNTAX SEQUENCE OF OspfVirtIntfInfoEntry
    MAX-ACCESS not-accessible
    STATUS current
    DESCRIPTION
      "The table of OSPF virtual interfaces information."
    ::= { ospfinfo 4 }

ospfVirtIntfInfoEntry OBJECT-TYPE
    SYNTAX OspfVirtIntfInfoEntry
    MAX-ACCESS not-accessible
    STATUS current
    DESCRIPTION
      "Information about an OSPF virtual interface."
    INDEX { ospfVirtIntfInfoIndex }
    ::= { ospfVirtIntfInfoTable 1 }

OspfVirtIntfInfoEntry ::= SEQUENCE {
    ospfVirtIntfInfoIndex         Integer32,
    ospfVirtIntfInfoIpAddr        IpAddress,
    ospfVirtIntfInfoArea          INTEGER,
    ospfVirtIntfInfoRouterId      IpAddress,
    ospfVirtIntfInfoState         INTEGER,
    ospfVirtIntfInfoCost          INTEGER,
    ospfVirtIntfInfoTrans         INTEGER,
    ospfVirtIntfInfoHello         INTEGER,
    ospfVirtIntfInfoHelloMS       INTEGER,
    ospfVirtIntfInfoDead          INTEGER,
    ospfVirtIntfInfoDeadMS        INTEGER,
    ospfVirtIntfInfoWait          INTEGER,
    ospfVirtIntfInfoWaitMS        INTEGER,
    ospfVirtIntfInfoRetra         INTEGER,
    ospfVirtIntfInfoAuth          DisplayString,
    ospfVirtIntfInfoEvents        INTEGER,
    ospfVirtIntfInfoNbr           IpAddress,
    ospfVirtIntfInfoNbrState      INTEGER,
    ospfVirtIntfInfoAreaId        IpAddress
    }

ospfVirtIntfInfoIndex OBJECT-TYPE
    SYNTAX Integer32
    MAX-ACCESS read-only
    STATUS current
    DESCRIPTION
        "The OSPF Virtual Interface number for which this table is
         related."
    ::= { ospfVirtIntfInfoEntry 1 }

ospfVirtIntfInfoIpAddr OBJECT-TYPE
    SYNTAX IpAddress
    MAX-ACCESS read-only
    STATUS current
    DESCRIPTION
        "The IP Address of this virtual interface."
    ::= { ospfVirtIntfInfoEntry 2 }

ospfVirtIntfInfoArea OBJECT-TYPE
    SYNTAX INTEGER (0..2)
    MAX-ACCESS read-only
    STATUS current
    DESCRIPTION
        "The index of the OSPF area to which this virtual interface
         belongs."
    ::= { ospfVirtIntfInfoEntry 3 }

ospfVirtIntfInfoRouterId OBJECT-TYPE
    SYNTAX IpAddress
    MAX-ACCESS read-only
    STATUS current
    DESCRIPTION
        "The Router ID."
    ::= { ospfVirtIntfInfoEntry 4 }

ospfVirtIntfInfoState   OBJECT-TYPE
    SYNTAX  INTEGER {
        disabled(0),
        enabled(1)
        }
    MAX-ACCESS read-only
    STATUS current
    DESCRIPTION
        "State
         disabled(0),
         enabled(1)"
    ::= { ospfVirtIntfInfoEntry 5 }

ospfVirtIntfInfoCost OBJECT-TYPE
    SYNTAX INTEGER
    MAX-ACCESS read-only
    STATUS current
    DESCRIPTION
        "The cost of the virtual interface."
    ::= { ospfVirtIntfInfoEntry 6 }

ospfVirtIntfInfoTrans OBJECT-TYPE
    SYNTAX INTEGER
    MAX-ACCESS read-only
    STATUS current
    DESCRIPTION
        "The transit delay for the virtual interface."
    ::= { ospfVirtIntfInfoEntry 7 }

ospfVirtIntfInfoHello  OBJECT-TYPE
    SYNTAX INTEGER (1..65535)
    MAX-ACCESS read-only
    STATUS current
    DESCRIPTION
        "Hello interval."
    ::= { ospfVirtIntfInfoEntry 8 }

ospfVirtIntfInfoHelloMS  OBJECT-TYPE
    SYNTAX  INTEGER {
        seconds(0),
        milliseconds(1)
        }
    MAX-ACCESS read-only
    STATUS current
    DESCRIPTION
    "Units of time measurement for Hello interval
     seconds(0),
        milliseconds(1)" 
    ::= { ospfVirtIntfInfoEntry 9 }

ospfVirtIntfInfoDead   OBJECT-TYPE
   SYNTAX INTEGER (1..65535)
    MAX-ACCESS read-only
    STATUS current
    DESCRIPTION
        "Dead interval."
    ::= { ospfVirtIntfInfoEntry 10 }

ospfVirtIntfInfoDeadMS  OBJECT-TYPE
    SYNTAX  INTEGER {
        seconds(0),
        milliseconds(1)
        }
    MAX-ACCESS read-only
    STATUS current
    DESCRIPTION
    "Units of time measurement for Dead interval
     seconds(0),
        milliseconds(1)" 
    ::= { ospfVirtIntfInfoEntry 11 }

ospfVirtIntfInfoWait   OBJECT-TYPE
    SYNTAX INTEGER (1..65535)
    MAX-ACCESS read-only
    STATUS current
    DESCRIPTION
        "Wait interval."
    ::= { ospfVirtIntfInfoEntry 12 }

ospfVirtIntfInfoWaitMS  OBJECT-TYPE
    SYNTAX  INTEGER {
        seconds(0),
        milliseconds(1)
        }
    MAX-ACCESS read-only
    STATUS current
    DESCRIPTION
    "Units of time measurement for Wait interval
     seconds(0),
        milliseconds(1)" 
    ::= { ospfVirtIntfInfoEntry 13 }

ospfVirtIntfInfoRetra  OBJECT-TYPE
    SYNTAX INTEGER (1..3600)
    MAX-ACCESS read-only
    STATUS current
    DESCRIPTION
        "Retransmit interval."
    ::= { ospfVirtIntfInfoEntry 14 }

ospfVirtIntfInfoAuth OBJECT-TYPE
   SYNTAX DisplayString (SIZE(0..8))
    MAX-ACCESS read-only
    STATUS current
    DESCRIPTION
        "Authentication."
    ::= { ospfVirtIntfInfoEntry 15 }

ospfVirtIntfInfoEvents OBJECT-TYPE
    SYNTAX INTEGER
    MAX-ACCESS read-only
    STATUS current
    DESCRIPTION
         "Events."
    ::= { ospfVirtIntfInfoEntry 16 }

ospfVirtIntfInfoNbr OBJECT-TYPE
    SYNTAX IpAddress
    MAX-ACCESS read-only
    STATUS current
    DESCRIPTION
        "The IP Address of the OSPF neighbor for this virtual interface."
    ::= { ospfVirtIntfInfoEntry 17 }

ospfVirtIntfInfoNbrState  OBJECT-TYPE
    SYNTAX  INTEGER {
        down(0),attempt(1),init(2),twoway(3),
        exstart(4),exchange(5),loading(6),full(7)
        }
    MAX-ACCESS read-only
    STATUS current
    DESCRIPTION
        "State
         down(0),attempt(1),init(2),2 way(3),
         exstart(4),exchange(5),loading(6),full(7)"
    ::= { ospfVirtIntfInfoEntry 18 }

ospfVirtIntfInfoAreaId OBJECT-TYPE
   SYNTAX IpAddress
   MAX-ACCESS read-only
   STATUS current
   DESCRIPTION
       "The AreaId of the virtual interface."
   ::= { ospfVirtIntfInfoEntry 19 }

-- OSPF Interface/Nbr Info Table

ospfIfNbrTable OBJECT-TYPE
    SYNTAX SEQUENCE OF OspfIfNbrEntry
    MAX-ACCESS not-accessible
    STATUS current
    DESCRIPTION
      "The table of OSPF Interface Neighbor information."
    ::= { ospfinfo 5 }

ospfIfNbrEntry OBJECT-TYPE
    SYNTAX OspfIfNbrEntry
    MAX-ACCESS not-accessible
    STATUS current
    DESCRIPTION
      "Information about a OSPF interface, neighbor pair."
    INDEX { ospfIfNbrIntfIndex, ospfIfNbrIpAddr }
    ::= { ospfIfNbrTable 1 }
 
OspfIfNbrEntry ::= SEQUENCE {
    ospfIfNbrIntfIndex               Integer32,
    ospfIfNbrIpAddr                  IpAddress,
    ospfIfNbrPriority                Integer32,
    ospfIfNbrState                   INTEGER,
    ospfIfNbrDesignatedRtr           IpAddress,
    ospfIfNbrBackupDesignatedRtr     IpAddress,
    ospfIfNbrIpAddress               IpAddress 
    }
 
ospfIfNbrIntfIndex OBJECT-TYPE
    SYNTAX Integer32
    MAX-ACCESS read-only
    STATUS current
    DESCRIPTION
    "The OSPF Interface number for which this Interface/Nbr table is 
         related."
    ::= { ospfIfNbrEntry 1}

ospfIfNbrIpAddr OBJECT-TYPE
    SYNTAX IpAddress 
    MAX-ACCESS read-only
    STATUS current
    DESCRIPTION
    "The OSPF Neighbor ID ." 
    ::= { ospfIfNbrEntry 2 }

ospfIfNbrPriority OBJECT-TYPE
    SYNTAX Integer32
    MAX-ACCESS read-only
    STATUS current
    DESCRIPTION
    "The priority of the OSPF neighbor."
    ::= { ospfIfNbrEntry 3 }

ospfIfNbrState OBJECT-TYPE
    SYNTAX  INTEGER { 
    down(1),
    attempt(2),
    init(3),
    twoway(4),
    exStart(5),
    exchange(6),
    loading(7),
    full(8)
    }
    MAX-ACCESS read-only
    STATUS current
    DESCRIPTION
    "The state of the OSPF neighbor."
    ::= { ospfIfNbrEntry 4 }

ospfIfNbrDesignatedRtr OBJECT-TYPE
    SYNTAX IpAddress 
    MAX-ACCESS read-only
    STATUS current
    DESCRIPTION
    "The IP Address of the Designated Router for this OSPF Neighbor." 
    ::= { ospfIfNbrEntry 5 }

ospfIfNbrBackupDesignatedRtr OBJECT-TYPE
    SYNTAX IpAddress 
    MAX-ACCESS read-only
    STATUS current
    DESCRIPTION
    "The IP Address of the backup designated Router for this OSPF Neighbor." 
    ::= { ospfIfNbrEntry 6 }

ospfIfNbrIpAddress OBJECT-TYPE
    SYNTAX IpAddress 
    MAX-ACCESS read-only
    STATUS current
    DESCRIPTION
    "The IP Address of the OSPF Neighbor." 
    ::= { ospfIfNbrEntry 7 }


-- OSPF Interface/Summary Ranges Table

ospfSumRangesInfoTable OBJECT-TYPE
    SYNTAX SEQUENCE OF OspfSumRangesInfoEntry
    MAX-ACCESS not-accessible
    STATUS current
    DESCRIPTION
      "The table of OSPF summary ranges information."
    ::= { ospfinfo 6 }

ospfSumRangesInfoEntry OBJECT-TYPE
    SYNTAX OspfSumRangesInfoEntry
    MAX-ACCESS not-accessible
    STATUS current
    DESCRIPTION
      "Summary ranges information."
    INDEX { ospfSumRangesInfoIndex }
    ::= { ospfSumRangesInfoTable 1 }

OspfSumRangesInfoEntry ::= SEQUENCE {
    ospfSumRangesInfoIndex         Integer32,
    ospfSumRangesInfoArea          INTEGER,
    ospfSumRangesInfoNetwork       IpAddress,
    ospfSumRangesInfoMask          IpAddress,
    ospfSumRangesInfoAction        INTEGER,
    ospfSumRangesInfoListType      INTEGER
    }

ospfSumRangesInfoIndex OBJECT-TYPE
    SYNTAX Integer32
    MAX-ACCESS read-only
    STATUS current
    DESCRIPTION
        "The OSPF range index for which this table is
         related."
    ::= { ospfSumRangesInfoEntry 1 }

ospfSumRangesInfoArea OBJECT-TYPE
    SYNTAX INTEGER (0..2)
    MAX-ACCESS read-only
    STATUS current
    DESCRIPTION
        "Area."
    ::= { ospfSumRangesInfoEntry 2 }

ospfSumRangesInfoNetwork OBJECT-TYPE
    SYNTAX IpAddress
    MAX-ACCESS read-only
    STATUS current
    DESCRIPTION
        "Network."
    ::= { ospfSumRangesInfoEntry 3 }

ospfSumRangesInfoMask OBJECT-TYPE
    SYNTAX IpAddress
    MAX-ACCESS read-only
    STATUS current
    DESCRIPTION
        "Mask."
    ::= { ospfSumRangesInfoEntry 4 }

ospfSumRangesInfoAction  OBJECT-TYPE
    SYNTAX  INTEGER {
        propagate(0),
        hide(1)
        }
    MAX-ACCESS read-only
    STATUS current
    DESCRIPTION
        "Action
         propagate(0),
         hide(1)"
    ::= { ospfSumRangesInfoEntry 5 }

ospfSumRangesInfoListType  OBJECT-TYPE
    SYNTAX  INTEGER {
        non-nssa(0),
        nssa(1)
        }
    MAX-ACCESS read-only
    STATUS current
    DESCRIPTION
       "Summary address list
         Non-NSSA(0),
         NSSA(1)"
    ::= { ospfSumRangesInfoEntry 6 }


-- OSPF Interface/Routes Table

ospfRoutesInfoTable OBJECT-TYPE
    SYNTAX SEQUENCE OF OspfRoutesInfoEntry
    MAX-ACCESS not-accessible
    STATUS current
    DESCRIPTION
      "The table of OSPF routes information."
    ::= { ospfinfo 7 }

ospfRoutesInfoEntry OBJECT-TYPE
    SYNTAX OspfRoutesInfoEntry
    MAX-ACCESS not-accessible
    STATUS current
    DESCRIPTION
      "OSPF routes information."
    INDEX { ospfRoutesInfoIndex }
    ::= { ospfRoutesInfoTable 1 }

OspfRoutesInfoEntry ::= SEQUENCE {
    ospfRoutesInfoIndex            Integer32,
    ospfRoutesInfoDestination      IpAddress,
    ospfRoutesInfoMask             IpAddress,
    ospfRoutesInfoVia              IpAddress,
    ospfRoutesInfoType             DisplayString
    }

ospfRoutesInfoIndex OBJECT-TYPE
    SYNTAX Integer32
    MAX-ACCESS read-only
    STATUS current
    DESCRIPTION
        "The OSPF route table entry index for which
          this table is related."
    ::= { ospfRoutesInfoEntry 1 }

ospfRoutesInfoDestination OBJECT-TYPE
    SYNTAX IpAddress
    MAX-ACCESS read-only
    STATUS current
    DESCRIPTION
        "Destination."
    ::= { ospfRoutesInfoEntry 2 }

ospfRoutesInfoMask OBJECT-TYPE
    SYNTAX IpAddress
    MAX-ACCESS read-only
    STATUS current
    DESCRIPTION
        "Mask."
    ::= { ospfRoutesInfoEntry 3 }

ospfRoutesInfoVia OBJECT-TYPE
    SYNTAX IpAddress
    MAX-ACCESS read-only
    STATUS current
    DESCRIPTION
        "Next hop."
    ::= { ospfRoutesInfoEntry 4 }

ospfRoutesInfoType OBJECT-TYPE
    SYNTAX DisplayString (SIZE(0..8))
    MAX-ACCESS read-only
    STATUS current
    DESCRIPTION
        "Route type. Codes: IA - OSPF inter area,
         N1 - OSPF NSSA external type 1, N2 - OSPF NSSA external type 2
         E1 - OSPF external type 1, E2 - OSPF external type 2
         *  - best"
    ::= { ospfRoutesInfoEntry 5 }


--  OSPF Link State Database

--      The Link State Database contains the Link State
--      Advertisements from throughout the areas that the
--      device is attached to.

--  The Area ID, in OSPF, has the same format as an IP Address,
--  but has the function of defining a summarization point for
--  Link State Advertisements.

--  The Router ID, in OSPF, has the same format as an IP Address,
--  but identifies the router independent of its IP Address.

    ospfLsdbInfoTable OBJECT-TYPE
        SYNTAX   SEQUENCE OF OspfLsdbInfoEntry
        MAX-ACCESS   not-accessible
        STATUS   current
        DESCRIPTION
           "The OSPF Process's Link State Database."
       REFERENCE
          "OSPF Version 2, Section 12  Link  State  Adver-
          tisements"
      ::= { ospfinfo 8 }


    ospfLsdbInfoEntry OBJECT-TYPE
        SYNTAX   OspfLsdbInfoEntry
        MAX-ACCESS   not-accessible
        STATUS   current
        DESCRIPTION
           "A single Link State Advertisement."
       INDEX { ospfLsdbInfoIndex }
       ::= { ospfLsdbInfoTable 1 }


OspfLsdbInfoEntry ::=
    SEQUENCE {
        ospfLsdbInfoIndex
            Integer32,
        ospfLsdbInfoAreaId
            IpAddress,
        ospfLsdbInfoType
            INTEGER,
        ospfLsdbInfoLsid
            IpAddress,
        ospfLsdbInfoRouterId
            IpAddress,
        ospfLsdbInfoSequence
            OCTET STRING,
        ospfLsdbInfoAge
            Integer32,
        ospfLsdbInfoChecksum
            Integer32,
        ospfLsdbInfoAdvertisement
            OCTET STRING
              }


 ospfLsdbInfoIndex OBJECT-TYPE
        SYNTAX   Integer32
        MAX-ACCESS   read-only
        STATUS   current
        DESCRIPTION
           "The 32 bit index in the table."
       REFERENCE
          "Private MIBS"
      ::= { ospfLsdbInfoEntry 1 }


    ospfLsdbInfoAreaId OBJECT-TYPE
        SYNTAX   IpAddress
        MAX-ACCESS   read-only
        STATUS   current
        DESCRIPTION
           "The 32 bit identifier of the Area  from  which
           the LSA was received."
       REFERENCE
          "OSPF Version 2, Appendix C.2 Area parameters"
      ::= { ospfLsdbInfoEntry 2 }

-- External Link State Advertisements are permitted
-- for backward compatibility, but should be displayed in
-- the ospfExtLsdbTable rather than here.

    ospfLsdbInfoType OBJECT-TYPE
        SYNTAX   INTEGER    {
                    routerLink (1),
                    networkLink (2),
                    summaryLink (3),
                    asSummaryLink (4),
                    asExternalLink (5), -- but see ospfExtLsdbTable
                    multicastLink (6),
                    nssaExternalLink (7)
                  }
        MAX-ACCESS   read-only
        STATUS   current
        DESCRIPTION
           "The type  of  the  link  state  advertisement.
           Each  link state type has a separate advertise-
           ment format."
       REFERENCE
          "OSPF Version 2, Appendix A.4.1 The  Link  State
          Advertisement header"
      ::= { ospfLsdbInfoEntry 3 }


    ospfLsdbInfoLsid OBJECT-TYPE
        SYNTAX   IpAddress
        MAX-ACCESS   read-only
        STATUS   current
        DESCRIPTION
           "The Link State ID is an LS Type Specific field
           containing either a Router ID or an IP Address;
           it identifies the piece of the  routing  domain
           that is being described by the advertisement."
       REFERENCE
          "OSPF Version 2, Section 12.1.4 Link State ID"
      ::= { ospfLsdbInfoEntry 4 }


    ospfLsdbInfoRouterId OBJECT-TYPE
        SYNTAX   IpAddress
        MAX-ACCESS   read-only
        STATUS   current
        DESCRIPTION
           "The 32 bit number that uniquely identifies the
           originating router in the Autonomous System."
       REFERENCE
          "OSPF Version 2, Appendix C.1 Global parameters"
      ::= { ospfLsdbInfoEntry 5 }

--  Note that the OSPF Sequence Number is a 32 bit signed
--  integer.  It starts with the value '80000001'h,
--  or -'7FFFFFFF'h, and increments until '7FFFFFFF'h
--  Thus, a typical sequence number will be very negative.
--  Modified to OCTET STRING - for BHM

    ospfLsdbInfoSequence OBJECT-TYPE
        SYNTAX   OCTET STRING (SIZE(10))
        MAX-ACCESS   read-only
        STATUS   current
        DESCRIPTION
           "The sequence number field is a  signed  32-bit
           integer.   It  is used to detect old and dupli-
           cate link state advertisements.  The  space  of
           sequence  numbers  is  linearly  ordered.   The
           larger the sequence number the more recent  the
           advertisement - displayed here in hexazecimal."
       REFERENCE
          "OSPF Version  2,  Section  12.1.6  LS  sequence
          number"
      ::= { ospfLsdbInfoEntry 6 }


    ospfLsdbInfoAge OBJECT-TYPE
        SYNTAX   Integer32    -- Should be 0..MaxAge
        MAX-ACCESS   read-only
        STATUS   current
        DESCRIPTION
           "This field is the age of the link state adver-
           tisement in seconds."
       REFERENCE
          "OSPF Version 2, Section 12.1.1 LS age"
      ::= { ospfLsdbInfoEntry 7 }


    ospfLsdbInfoChecksum OBJECT-TYPE
        SYNTAX   Integer32
        MAX-ACCESS   read-only
        STATUS   current
        DESCRIPTION
           "This field is the  checksum  of  the  complete
           contents  of  the  advertisement, excepting the
           age field.  The age field is excepted  so  that
           an   advertisement's  age  can  be  incremented
           without updating the  checksum.   The  checksum
           used  is  the same that is used for ISO connec-
           tionless datagrams; it is commonly referred  to
           as the Fletcher checksum."
       REFERENCE
          "OSPF Version 2, Section 12.1.7 LS checksum"
      ::= { ospfLsdbInfoEntry 8 }


    ospfLsdbInfoAdvertisement OBJECT-TYPE
        SYNTAX   OCTET STRING (SIZE(36))
        MAX-ACCESS   read-only
        STATUS   current
        DESCRIPTION
           "The entire Link State Advertisement, including
           its header. When the LSA is invalid, it is  
           message string 'Invalid LSDB'."
       REFERENCE
          "OSPF Version 2, Section 12  Link  State  Adver-
          tisements"
      ::= { ospfLsdbInfoEntry 9 }


--  SPF Link State Database, External

--      The Link State Database contains the Link State
--      Advertisements from throughout the areas that the
--      device is attached to.

--             This table is identical to the OSPF LSDB Table in
--      format, but contains only External Link State
--             Advertisements.  The purpose is to allow external
--      LSAs to be displayed once for the router rather
--      than once in each non-stub area.

    ospfExtLsdbInfoTable OBJECT-TYPE
        SYNTAX   SEQUENCE OF OspfExtLsdbInfoEntry
        MAX-ACCESS   not-accessible
        STATUS   current
        DESCRIPTION
           "The OSPF Process's Links State Database."
       REFERENCE
          "OSPF Version 2, Section 12  Link  State  Adver-
          tisements"
      ::= { ospfinfo 9 }


    ospfExtLsdbInfoEntry OBJECT-TYPE
        SYNTAX   OspfExtLsdbInfoEntry
        MAX-ACCESS   not-accessible
        STATUS   current
        DESCRIPTION
           "A single Link State Advertisement."
       INDEX { ospfExtLsdbInfoIndex }
       ::= { ospfExtLsdbInfoTable 1 }


OspfExtLsdbInfoEntry ::=
    SEQUENCE {
        ospfExtLsdbInfoIndex
            Integer32,
        ospfExtLsdbInfoType
            INTEGER,
        ospfExtLsdbInfoLsid
            IpAddress,
        ospfExtLsdbInfoRouterId
            IpAddress,
        ospfExtLsdbInfoSequence
            OCTET STRING,
        ospfExtLsdbInfoAge
            Integer32,
        ospfExtLsdbInfoChecksum
            Integer32,
        ospfExtLsdbInfoAdvertisement
            OCTET STRING
              }


ospfExtLsdbInfoIndex OBJECT-TYPE
        SYNTAX   Integer32
        MAX-ACCESS   read-only
        STATUS   current
        DESCRIPTION
           "The 32 bit index in the table."
       REFERENCE
          "Private MIBS"
      ::= { ospfExtLsdbInfoEntry 1 }


    ospfExtLsdbInfoType OBJECT-TYPE
        SYNTAX   INTEGER    {
                    asExternalLink (5)
                  }
        MAX-ACCESS   read-only
        STATUS   current
        DESCRIPTION
           "The type  of  the  link  state  advertisement.
           Each  link state type has a separate advertise-
           ment format."
       REFERENCE
          "OSPF Version 2, Appendix A.4.1 The  Link  State
          Advertisement header"
      ::= { ospfExtLsdbInfoEntry 2 }


    ospfExtLsdbInfoLsid OBJECT-TYPE
        SYNTAX   IpAddress
        MAX-ACCESS   read-only
        STATUS   current
        DESCRIPTION
           "The Link State ID is an LS Type Specific field
           containing either a Router ID or an IP Address;
           it identifies the piece of the  routing  domain
           that is being described by the advertisement."
       REFERENCE
          "OSPF Version 2, Section 12.1.4 Link State ID"
      ::= { ospfExtLsdbInfoEntry 3 }


    ospfExtLsdbInfoRouterId OBJECT-TYPE
        SYNTAX   IpAddress
        MAX-ACCESS   read-only
        STATUS   current
        DESCRIPTION
           "The 32 bit number that uniquely identifies the
           originating router in the Autonomous System."
       REFERENCE
          "OSPF Version 2, Appendix C.1 Global parameters"
      ::= { ospfExtLsdbInfoEntry 4 }

--  Note that the OSPF Sequence Number is a 32 bit signed
--  integer.  It starts with the value '80000001'h,
--  or -'7FFFFFFF'h, and increments until '7FFFFFFF'h
--  Thus, a typical sequence number will be very negative.
--  Modified to OCTET STRING - for BHM

    ospfExtLsdbInfoSequence OBJECT-TYPE
        SYNTAX   OCTET STRING (SIZE(10))
        MAX-ACCESS   read-only
        STATUS   current
        DESCRIPTION
           "The sequence number field is a  signed  32-bit
           integer.   It  is used to detect old and dupli-
           cate link state advertisements.  The  space  of
           sequence  numbers  is  linearly  ordered.   The
           larger the sequence number the more recent  the
           advertisement - displayed here in hexazecimal."
       REFERENCE
          "OSPF Version  2,  Section  12.1.6  LS  sequence
          number"
      ::= { ospfExtLsdbInfoEntry 5 }


    ospfExtLsdbInfoAge OBJECT-TYPE
        SYNTAX   Integer32    -- Should be 0..MaxAge
        MAX-ACCESS   read-only
        STATUS   current
        DESCRIPTION
           "This field is the age of the link state adver-
           tisement in seconds."
       REFERENCE
          "OSPF Version 2, Section 12.1.1 LS age"
      ::= { ospfExtLsdbInfoEntry 6 }


    ospfExtLsdbInfoChecksum OBJECT-TYPE
        SYNTAX   Integer32
        MAX-ACCESS   read-only
        STATUS   current
        DESCRIPTION
           "This field is the  checksum  of  the  complete
           contents  of  the  advertisement, excepting the
           age field.  The age field is excepted  so  that
           an   advertisement's  age  can  be  incremented
           without updating the  checksum.   The  checksum
           used  is  the same that is used for ISO connec-
           tionless datagrams; it is commonly referred  to
           as the Fletcher checksum."
       REFERENCE
          "OSPF Version 2, Section 12.1.7 LS checksum"
      ::= { ospfExtLsdbInfoEntry 7 }


    ospfExtLsdbInfoAdvertisement OBJECT-TYPE
        SYNTAX   OCTET STRING (SIZE(36))
        MAX-ACCESS   read-only
        STATUS   current
        DESCRIPTION
           "The entire Link State Advertisement, including
           its header."
       REFERENCE
          "OSPF Version 2, Section 12  Link  State  Adver-
          tisements"
      ::= { ospfExtLsdbInfoEntry 8 }


ospfLoopIfInfoTable OBJECT-TYPE
    SYNTAX SEQUENCE OF OspfLoopIfInfoEntry
    MAX-ACCESS not-accessible
    STATUS current
    DESCRIPTION
      "The table of OSPF Loopback Interface information."
    ::= { ospfinfo 10 }

ospfLoopIfInfoEntry OBJECT-TYPE
    SYNTAX OspfLoopIfInfoEntry
    MAX-ACCESS not-accessible
    STATUS current
    DESCRIPTION
      "Information about a OSPF loopback interface."
    INDEX { ospfLoopIfInfoIndex }
    ::= { ospfLoopIfInfoTable 1 }

OspfLoopIfInfoEntry ::= SEQUENCE {
    ospfLoopIfInfoIndex                             Integer32,
    ospfLoopIfInfoIpAddress                         IpAddress,
    ospfLoopIfInfoArea                              INTEGER,
    ospfLoopIfInfoAdminStatus                       INTEGER,
    ospfLoopIfInfoPassive                           INTEGER,
    ospfLoopIfInfoPtop                              INTEGER,
    ospfLoopIfInfoRouterIP                          IpAddress,
    ospfLoopIfInfoState                             INTEGER,
    ospfLoopIfInfoPriority                          INTEGER,
    ospfLoopIfInfoDesignatedRouterIP                IpAddress,
    ospfLoopIfInfoDesignatedRouterIpAddress         IpAddress,
    ospfLoopIfInfoBackupDesignatedRouterIP          IpAddress,
    ospfLoopIfInfoBackupDesignatedRouterIpAddress   IpAddress,
    ospfLoopIfInfoHello                             INTEGER,
    ospfLoopIfInfoHelloMS                           INTEGER,
    ospfLoopIfInfoDead                              INTEGER,
    ospfLoopIfInfoDeadMS                            INTEGER,
    ospfLoopIfInfoWaitInterval                      Integer32,
    ospfLoopIfInfoWaitIntervalMS                    INTEGER,
    ospfLoopIfInfoRetransmit                        INTEGER,
    ospfLoopIfInfoTransitDelay                      INTEGER,
    ospfLoopIfInfoTotalNeighbours                   Integer32,
    ospfLoopIfInfoEvents                            Integer32,
    ospfLoopIfInfoAuthType                          INTEGER
    }

ospfLoopIfInfoIndex OBJECT-TYPE
    SYNTAX Integer32
    MAX-ACCESS read-only
    STATUS current
    DESCRIPTION
        "The OSPF loopback interface number 
         for which the OSPF info table is related."
    ::= { ospfLoopIfInfoEntry 1}

ospfLoopIfInfoIpAddress OBJECT-TYPE
    SYNTAX IpAddress
    MAX-ACCESS read-only
    STATUS current
    DESCRIPTION
        "The IP address of the OSPF loopback interface."
    ::= { ospfLoopIfInfoEntry 2 }

ospfLoopIfInfoArea OBJECT-TYPE
    SYNTAX INTEGER
    MAX-ACCESS read-only
    STATUS current
    DESCRIPTION
        "The index of the area that the loopback interface belongs."
    ::= { ospfLoopIfInfoEntry 3 }

ospfLoopIfInfoAdminStatus  OBJECT-TYPE
    SYNTAX  INTEGER {
        down(0),
        up(1)
        }
    MAX-ACCESS read-only
    STATUS current
    DESCRIPTION
        "Admin Status of the interface:
        down(0), up(1)."
    ::= { ospfLoopIfInfoEntry 4 }

ospfLoopIfInfoPassive  OBJECT-TYPE
    SYNTAX  INTEGER {
        disabled(0),
        enabled(1)
        }
    MAX-ACCESS read-only
    STATUS current
    DESCRIPTION
        "Passive status of the interface:
        disabled(0), enabled(1)."
    ::= { ospfLoopIfInfoEntry 5 }

ospfLoopIfInfoPtop  OBJECT-TYPE
    SYNTAX  INTEGER {
        disabled(0),
        enabled(1)
        }
    MAX-ACCESS read-only
    STATUS current
    DESCRIPTION
        "Point-to-point status of the interface:
        disabled(0), enabled(1)."
    ::= { ospfLoopIfInfoEntry 24 }

ospfLoopIfInfoRouterIP OBJECT-TYPE
    SYNTAX IpAddress
    MAX-ACCESS read-only
    STATUS current
    DESCRIPTION
        "The router ID of the switch."
    ::= { ospfLoopIfInfoEntry 6 }

ospfLoopIfInfoState  OBJECT-TYPE
    SYNTAX  INTEGER {
        down(0),
        loopback(1),
        waiting(2),
        ptop(3),
        dr(4),
        backupdr(5),
        drother(6)
        }
    MAX-ACCESS read-only
    STATUS current
    DESCRIPTION
        "The state of the interface:
        Down(0), Loopback(1),
        Waiting(2), P to P(3),
        DR(4), BackuDR(5),
        DR Other(6)."
    ::= { ospfLoopIfInfoEntry 7 }

ospfLoopIfInfoPriority   OBJECT-TYPE
   SYNTAX INTEGER (1..255)
    MAX-ACCESS read-only
    STATUS current
    DESCRIPTION
        "Interface router priority"
    ::= { ospfLoopIfInfoEntry 8 }

ospfLoopIfInfoDesignatedRouterIP OBJECT-TYPE
    SYNTAX IpAddress
    MAX-ACCESS read-only
    STATUS current
    DESCRIPTION
        "The OSPF Designated Router IP (IP Address) for this OSPF interface."
    ::= { ospfLoopIfInfoEntry 9 }

ospfLoopIfInfoDesignatedRouterIpAddress OBJECT-TYPE
    SYNTAX IpAddress
    MAX-ACCESS read-only
    STATUS current
    DESCRIPTION
        "The OSPF Designated Router IP Address for this OSPF interface."
    ::= { ospfLoopIfInfoEntry 10 }

ospfLoopIfInfoBackupDesignatedRouterIP OBJECT-TYPE
    SYNTAX IpAddress
    MAX-ACCESS read-only
    STATUS current
    DESCRIPTION
        "The OSPF Backup Designated Router IP for this OSPF
         interface."
    ::= { ospfLoopIfInfoEntry 11 }

ospfLoopIfInfoBackupDesignatedRouterIpAddress OBJECT-TYPE
    SYNTAX IpAddress
    MAX-ACCESS read-only
    STATUS current
    DESCRIPTION
        "The OSPF Backup Designated Router Ip Address for this OSPF
         interface."
    ::= { ospfLoopIfInfoEntry 12 }

ospfLoopIfInfoHello  OBJECT-TYPE
    SYNTAX INTEGER (1..65535)
    MAX-ACCESS read-only
    STATUS current
    DESCRIPTION
        "The hello timer for this OSPF interface."
    ::= { ospfLoopIfInfoEntry 13 }

ospfLoopIfInfoHelloMS  OBJECT-TYPE
    SYNTAX  INTEGER {
        seconds(0),
        milliseconds(1)
        }
    MAX-ACCESS read-only
    STATUS current
    DESCRIPTION
        "Units of time measurement for Hello interval
        seconds(0),
        milliseconds(1)"
    ::= { ospfLoopIfInfoEntry 14 }

ospfLoopIfInfoDead   OBJECT-TYPE
   SYNTAX INTEGER (1..65535)
    MAX-ACCESS read-only
    STATUS current
    DESCRIPTION
        "The dead timer for this OSPF interface."
    ::= { ospfLoopIfInfoEntry 15 }

ospfLoopIfInfoDeadMS  OBJECT-TYPE
    SYNTAX  INTEGER {
        seconds(0),
        milliseconds(1)
        }
    MAX-ACCESS read-only
    STATUS current
    DESCRIPTION
        "Units of time measurement for Dead interval
        seconds(0),
        milliseconds(1)"
    ::= { ospfLoopIfInfoEntry 16 }

ospfLoopIfInfoWaitInterval OBJECT-TYPE
    SYNTAX Integer32
    MAX-ACCESS read-only
    STATUS current
    DESCRIPTION
        "The OSPF Wait interval for this OSPF interface."
    ::= { ospfLoopIfInfoEntry 17 }

ospfLoopIfInfoWaitIntervalMS  OBJECT-TYPE
    SYNTAX  INTEGER {
        seconds(0),
        milliseconds(1)
        }
    MAX-ACCESS read-only
    STATUS current
    DESCRIPTION
        "Units of time measurement for Wait interval
        seconds(0),
        milliseconds(1)"
    ::= { ospfLoopIfInfoEntry 18 }

ospfLoopIfInfoRetransmit OBJECT-TYPE
    SYNTAX INTEGER (1..3600)
    MAX-ACCESS read-only
    STATUS current
    DESCRIPTION
        "The retransmit interval for this OSPF interface."
    ::= { ospfLoopIfInfoEntry 19 }

ospfLoopIfInfoTransitDelay  OBJECT-TYPE
   SYNTAX INTEGER (1..3600)
    MAX-ACCESS read-only
    STATUS current
    DESCRIPTION
        "The transit delay for this OSPF interface."
    ::= { ospfLoopIfInfoEntry 20 }

ospfLoopIfInfoTotalNeighbours OBJECT-TYPE
    SYNTAX Integer32
    MAX-ACCESS read-only
    STATUS current
    DESCRIPTION
        "The Total number of neighbours for this OSPF interface."
    ::= { ospfLoopIfInfoEntry 21 }

ospfLoopIfInfoEvents OBJECT-TYPE
    SYNTAX Integer32
    MAX-ACCESS read-only
    STATUS current
    DESCRIPTION
        "The total number of events for this OSPF interface."
    ::= { ospfLoopIfInfoEntry 22 }

ospfLoopIfInfoAuthType OBJECT-TYPE
    SYNTAX  INTEGER {
        none(1),
        password(2),
        md5(3)
        }
    MAX-ACCESS  read-only
    STATUS  current
    DESCRIPTION
        "Type of authentication being used:
         none(1) - no authentication,
         password(2) - use password,
         md5(3) - use MD5 authentication."
    ::= { ospfLoopIfInfoEntry 23 }





-- Ospfv3 Information 

ospf3GeneralInfo  OBJECT IDENTIFIER ::= { ospf3Info 1 }

ospf3Version OBJECT-TYPE
    SYNTAX INTEGER {
        ospfVersion3(3)
        }
    MAX-ACCESS read-only
    STATUS current
    DESCRIPTION
        "OSPF version."
    ::= { ospf3GeneralInfo 1 }

ospf3RouterID OBJECT-TYPE
    SYNTAX IpAddress 
    MAX-ACCESS read-only
    STATUS current
    DESCRIPTION
    "The router ID of the switch." 
    ::= { ospf3GeneralInfo 2 }

ospf3StartTime OBJECT-TYPE   
    SYNTAX  Integer32 
    MAX-ACCESS  read-only   
    STATUS  current   
    DESCRIPTION   
        "The time when ospf has been started."   
    ::= { ospf3GeneralInfo 3 }

ospf3ProcessUptime OBJECT-TYPE   
    SYNTAX  Counter32 
    MAX-ACCESS  read-only   
    STATUS  current   
    DESCRIPTION   
        "The time since ospf has been started."   
    ::= { ospf3GeneralInfo 4 }

-- ospf3LsTypesSupported OBJECT-TYPE   
--     SYNTAX  Integer32 
--     MAX-ACCESS  read-only   
--     STATUS  current   
--     DESCRIPTION   
--         "The Link State Types that are supported."   
--     ::= { ospf3GeneralInfo 5 }

ospf3AreaBorderRouter OBJECT-TYPE   
    SYNTAX  INTEGER {
    yes(1),
    no(2)
    }
    MAX-ACCESS  read-only   
    STATUS  current   
    DESCRIPTION   
        "Area Border Router Role."
    ::= { ospf3GeneralInfo 5 }

ospf3ASBoundaryRouter OBJECT-TYPE   
    SYNTAX  INTEGER {
    yes(1),
    no(2)
    }
    MAX-ACCESS  read-only   
    STATUS  current   
    DESCRIPTION   
        "AS Boundary Router Role." 
    ::= { ospf3GeneralInfo 6 }


ospf3ExternalLsa OBJECT-TYPE   
    SYNTAX  Integer32 
    MAX-ACCESS  read-only   
    STATUS  current   
    DESCRIPTION   
        "The number of external LSAs." 
    ::= { ospf3GeneralInfo 7 }

ospf3IntfCountForRouter OBJECT-TYPE   
    SYNTAX  Integer32 
    MAX-ACCESS  read-only   
    STATUS  current   
    DESCRIPTION   
        "The number of interfaces for this router." 
    ::= { ospf3GeneralInfo 8 }

ospf3VlinkCountForRouter OBJECT-TYPE   
    SYNTAX  Integer32 
    MAX-ACCESS  read-only   
    STATUS  current   
    DESCRIPTION   
        "The number of virtual links for this router." 
    ::= { ospf3GeneralInfo 9 }

ospf3NewLsaReceived OBJECT-TYPE   
    SYNTAX  Integer32 
    MAX-ACCESS  read-only   
    STATUS  current   
    DESCRIPTION   
        "The number of new LSAs reveived." 
    ::= { ospf3GeneralInfo 10 }

ospf3TotalLsaOriginated OBJECT-TYPE   
    SYNTAX  Integer32 
    MAX-ACCESS  read-only   
    STATUS  current   
    DESCRIPTION   
        "The number of LSAs originated." 
    ::= { ospf3GeneralInfo 11 }

ospf3TotalNumberOfAsScopeLsas OBJECT-TYPE
    SYNTAX Integer32
    MAX-ACCESS read-only
    STATUS current
    DESCRIPTION
    "Total number of entries in the  Link State Database." 
    ::= { ospf3GeneralInfo 12 }

ospf3TotalNeighbours OBJECT-TYPE   
    SYNTAX  Integer32 
    MAX-ACCESS  read-only   
    STATUS  current   
    DESCRIPTION   
        "The total number of OSPF neighbours." 
    ::= { ospf3GeneralInfo 13 }

ospf3NbrInXchgOrLoadState OBJECT-TYPE   
    SYNTAX  Integer32 
    MAX-ACCESS  read-only   
    STATUS  current   
    DESCRIPTION   
        "The number of neighbours in the exchange or loading state." 
    ::= { ospf3GeneralInfo 14 }

-- ospf3NbrInExchState OBJECT-TYPE   
--     SYNTAX  Integer32 
--     MAX-ACCESS  read-only   
--     STATUS  current   
--     DESCRIPTION   
--         "The number of neighbours in the exchange state." 
--     ::= { ospf3GeneralInfo 16 }
-- 
-- ospf3NbrInFullState OBJECT-TYPE   
--     SYNTAX  Integer32 
--     MAX-ACCESS  read-only   
--     STATUS  current   
--     DESCRIPTION   
--         "The number of neighbours in the Full state of exchange." 
--     ::= { ospf3GeneralInfo 17 }

ospf3TotalAreas OBJECT-TYPE   
    SYNTAX  Integer32 
    MAX-ACCESS  read-only   
    STATUS  current   
    DESCRIPTION   
        "The Total number of areas." 
    ::= { ospf3GeneralInfo 15 }

-- ospf3TotalTransitAreas OBJECT-TYPE   
--     SYNTAX  Integer32 
--     MAX-ACCESS  read-only   
--     STATUS  current   
--     DESCRIPTION   
--         "The Total number of Transit areas." 
--     ::= { ospf3GeneralInfo 16 }

ospf3TotalActiveAreas OBJECT-TYPE   
    SYNTAX  Integer32 
    MAX-ACCESS  read-only   
    STATUS  current   
    DESCRIPTION   
        "The Total number of areas containing active interfaces." 
    ::= { ospf3GeneralInfo 16 }

ospf3TotalNssaAreas OBJECT-TYPE   
    SYNTAX  Integer32 
    MAX-ACCESS  read-only   
    STATUS  current   
    DESCRIPTION   
        "The Total number of NSSA areas." 
    ::= { ospf3GeneralInfo 17 }

-- ospf3TotalStubAreas OBJECT-TYPE
--     SYNTAX  Integer32
--     MAX-ACCESS  read-only
--     STATUS  current
--     DESCRIPTION
--         "The Total number of STUB areas."
--     ::= { ospf3GeneralInfo 19 }

   ospf3OverFlowState OBJECT-TYPE
       SYNTAX      INTEGER { true(1), false(2) }
       MAX-ACCESS  read-only
       STATUS      current
       DESCRIPTION
           "Indicates whether router is in overflow state or not."
       DEFVAL { false }
       ::=  { ospf3GeneralInfo 18 }

   ospf3SpfDelay OBJECT-TYPE
        SYNTAX       Integer32 (0..65535)
        MAX-ACCESS   read-only
        STATUS       current
        DESCRIPTION
            " The Delay at which routing calculation is carried after a
            topology change."
        DEFVAL {5}
        ::= { ospf3GeneralInfo 19 }

   ospf3SpfHoldTime OBJECT-TYPE
        SYNTAX       Integer32 (0..65535)
        MAX-ACCESS   read-only
        STATUS       current
        DESCRIPTION
            " The minimum time between two consecutive SPF calculations."
        DEFVAL {10}
        ::= { ospf3GeneralInfo 20 }

   ospf3ABRType OBJECT-TYPE
       SYNTAX   INTEGER    {
                    standardABR (1),
                    ciscoABR (2),
                    ibmABR (3)
                  }
       MAX-ACCESS  read-only
       STATUS      current
       DESCRIPTION
           "Different Types of ABRs supported"
       REFERENCE
           "RFC-3509 -- Alternative Implementations of OSPF Area Border 
                    Routers"
       DEFVAL { standardABR }
         ::= { ospf3GeneralInfo 21 }

   ospf3NssaAsbrDefRtTrans OBJECT-TYPE
       SYNTAX      INTEGER {
                             enabled (1) ,
                             disabled (2)
                           }
       MAX-ACCESS  read-only
       STATUS      current
       DESCRIPTION
           "Specifies the P-Bit setting for the default Type-7
            LSA generated by ASBR(which is not ABR).When 
            disabled, P-Bit is clear in the generated default Lsa.
            When enabled, P-Bit is set in the generated
            Type-7 default Lsa. "
       DEFVAL { disabled }
         ::= { ospf3GeneralInfo 22 }

ospf3AreaInfoTable OBJECT-TYPE
    SYNTAX SEQUENCE OF Ospf3AreaInfoEntry
    MAX-ACCESS not-accessible
    STATUS current
    DESCRIPTION
      "The table of OSPFv3 Area information."
    ::= { ospf3Info 2 }

ospf3AreaInfoEntry OBJECT-TYPE
    SYNTAX Ospf3AreaInfoEntry
    MAX-ACCESS not-accessible
    STATUS current
    DESCRIPTION
      "Information about a OSPFv3 area."
    INDEX { ospf3AreaInfoIndex }
    ::= { ospf3AreaInfoTable 1 }
 
Ospf3AreaInfoEntry ::= SEQUENCE {
    ospf3AreaInfoIndex                 Integer32,
    ospf3AreaInfoId                    IpAddress,
    ospf3AreaInfoStatus                INTEGER,
    ospf3TotalNumberOfInterfaces       Integer32,
    ospf3NumberOfInterfacesUp          Integer32,
--    ospf3AreaInfoAuthType              INTEGER,
    ospf3AreaInfoSPF                   Integer32,
    ospf3NumberOfLsdbEntries           Integer32,
    ospf3AreaInfoAreaBorderRouter      Integer32,
    ospf3AreaInfoASBoundaryRouter      Integer32,
    ospf3AreaInfoNeighborsFULLstate    Integer32,
    ospf3AreaInfoVirtNeighborsFULLstate    Integer32
    }
 
ospf3AreaInfoIndex OBJECT-TYPE
    SYNTAX Integer32
    MAX-ACCESS read-only
    STATUS current
    DESCRIPTION
    "The OSPFv3 area number for which the OSPFv3 info table is related."
    ::= { ospf3AreaInfoEntry 1 } 

ospf3AreaInfoId OBJECT-TYPE
    SYNTAX IpAddress
    MAX-ACCESS read-only
    STATUS current
    DESCRIPTION
        "The IP address of the OSPFv3 area." 
    ::= { ospf3AreaInfoEntry 2 }

ospf3AreaInfoStatus OBJECT-TYPE
    SYNTAX  INTEGER {
                     -- the following two values are states:
                     -- these values may be read or written
                     active(1),
                     notInService(2),
                     -- the following value is a state:
                     -- this value may be read, but not written
                     notReady(3),
                     -- the following three values are
                     -- actions: these values may be written,
                     --   but are never read
                     createAndGo(4),
                     createAndWait(5),
                     destroy(6)
                 }
    MAX-ACCESS  read-only
    STATUS  current
    DESCRIPTION
        "Area Status:
           active(1), notInService(2), notReady(3)."
    ::= { ospf3AreaInfoEntry 3 }

ospf3TotalNumberOfInterfaces OBJECT-TYPE
    SYNTAX Integer32
    MAX-ACCESS read-only
    STATUS current
    DESCRIPTION
    "The total number of interfaces for this OSPFv3 area." 
    ::= { ospf3AreaInfoEntry 4 }

ospf3NumberOfInterfacesUp OBJECT-TYPE
    SYNTAX Integer32
    MAX-ACCESS read-only
    STATUS current
    DESCRIPTION
    "The number of interfaces UP in area." 
    ::= { ospf3AreaInfoEntry 5 }

-- ospf3AreaInfoAuthType OBJECT-TYPE
--     SYNTAX  INTEGER {
--         none(1),
--         password(2),
--         md5(3)
--         }
--     MAX-ACCESS  read-only
--     STATUS  current
--     DESCRIPTION
--         "Type of authentication being used:
--          none(1) - no authentication
--          password(2) - use password
--          md5(3) - use MD5 authentication."
--     ::= { ospf3AreaInfoEntry 6 }

ospf3AreaInfoSPF OBJECT-TYPE
    SYNTAX Integer32
    MAX-ACCESS read-only
    STATUS current
    DESCRIPTION
        "The number of times SPF ran."
    ::= { ospf3AreaInfoEntry 6 }

ospf3NumberOfLsdbEntries OBJECT-TYPE
    SYNTAX Integer32
    MAX-ACCESS read-only
    STATUS current
    DESCRIPTION
        "The total number of Area-scope link state
         advertisements in this area's link state
         database."
    ::= { ospf3AreaInfoEntry 7 }

ospf3AreaInfoAreaBorderRouter OBJECT-TYPE
    SYNTAX Integer32
    MAX-ACCESS read-only
    STATUS current
    DESCRIPTION
        "The Area Border Router count."
    ::= { ospf3AreaInfoEntry 8 }

ospf3AreaInfoASBoundaryRouter OBJECT-TYPE
    SYNTAX Integer32
    MAX-ACCESS read-only
    STATUS current
    DESCRIPTION
        "The AS Boundary Router count."
    ::= { ospf3AreaInfoEntry 9 }

-- ospf3AreaInfoTotalNeighbours OBJECT-TYPE   
--     SYNTAX  Integer32 
--     MAX-ACCESS  read-only   
--     STATUS  current   
--     DESCRIPTION   
--         "The total number of OSPFv3 neighbors." 
--     ::= { ospf3AreaInfoEntry 11 }
-- 
--  ospf3AreaInfoNeighborsINITstate OBJECT-TYPE
--     SYNTAX Integer32
--     MAX-ACCESS read-only
--     STATUS current
--     DESCRIPTION
--         "Total neighbors in INIT state."
--     ::= { ospf3AreaInfoEntry 12 }
-- 
-- ospf3AreaInfoNeighborsEXCHstate OBJECT-TYPE
--     SYNTAX Integer32
--     MAX-ACCESS read-only
--     STATUS current
--     DESCRIPTION
--         "Total neighbors in EXCH state."
--     ::= { ospf3AreaInfoEntry 13 }

ospf3AreaInfoNeighborsFULLstate OBJECT-TYPE
    SYNTAX Integer32
    MAX-ACCESS read-only
    STATUS current
    DESCRIPTION
        "Total neighbors in FULL state."
    ::= { ospf3AreaInfoEntry 10 }

ospf3AreaInfoVirtNeighborsFULLstate OBJECT-TYPE
    SYNTAX Integer32
    MAX-ACCESS read-only
    STATUS current
    DESCRIPTION
        "Total neighbors in FULL state."
    ::= { ospf3AreaInfoEntry 11 }


ospf3IntfInfoTable OBJECT-TYPE
    SYNTAX SEQUENCE OF Ospf3IntfInfoEntry
    MAX-ACCESS not-accessible
    STATUS current
    DESCRIPTION
      "The table of OSPFv3 Interface information."
    ::= { ospf3Info 3 }

ospf3IntfInfoEntry OBJECT-TYPE
    SYNTAX Ospf3IntfInfoEntry
    MAX-ACCESS not-accessible
    STATUS current
    DESCRIPTION
      "Information about a OSPFv3 interface."
    INDEX { ospf3IfInfoIndex }
    ::= { ospf3IntfInfoTable 1 }

Ospf3IntfInfoEntry ::= SEQUENCE {
    ospf3IfInfoIndex                                     Integer32,
    ospf3IfInfoInstanceID                                Unsigned32,
    ospf3IfInfoLLocalAddress                             DisplayString,
    ospf3IfInfoAreaID                                    IpAddress,
    ospf3IfInfoAdminStatus                               INTEGER,
    ospf3IfInfoPassive                                   INTEGER,
    ospf3IfInfoNetworkType                               INTEGER,
    ospf3IfInfoState                                     INTEGER,
    ospf3IfInfoPriority                                  INTEGER,
    ospf3IfInfoDesignatedRouterID                        IpAddress,
    ospf3IfInfoBackupDesignatedRouterID                  IpAddress,
    ospf3IfInfoHello                                     INTEGER,
    ospf3IfInfoDead                                      INTEGER,
    ospf3IfInfoPoll                                      Integer32,
    ospf3IfInfoRetransmit                                INTEGER,
    ospf3IfInfoTransitDelay                              INTEGER,
    ospf3IfInfoTotalNeighbours                           Integer32,
    ospf3IfInfoEvents                                    Integer32,
    ospf3IfInfoMetricCost                                Integer32
    ,
    ospf3IfInfoAuthSpi                                   Unsigned32,
    ospf3IfInfoAuthEnable                                INTEGER,
    ospf3IfInfoAuthType                                  INTEGER,
    ospf3IfInfoAuthKey                                   OCTET STRING,
    ospf3IfInfoEncrySpi                                  Unsigned32,
    ospf3IfInfoEncryEnable                               INTEGER,
    ospf3IfInfoEncryType                                 INTEGER,
    ospf3IfInfoEncryKey                                  OCTET STRING,
    ospf3IfInfoEncryAuthType                             INTEGER,
    ospf3IfInfoEncryAuthKey                              OCTET STRING
    ,
    ospf3IfInfoLsaSupress                                INTEGER
    }
 
ospf3IfInfoIndex OBJECT-TYPE
    SYNTAX Integer32
    MAX-ACCESS read-only
    STATUS current
    DESCRIPTION
        "The OSPFv3 interface number for which the OSPFv3 info table is related."
    ::= { ospf3IntfInfoEntry 1 }

ospf3IfInfoInstanceID OBJECT-TYPE
    SYNTAX Unsigned32
    MAX-ACCESS read-only
    STATUS current
    DESCRIPTION
        "The OSPFv3 interface instance id."
    ::= { ospf3IntfInfoEntry 2 }

ospf3IfInfoLLocalAddress OBJECT-TYPE
    SYNTAX DisplayString
    MAX-ACCESS read-only
    STATUS current
    DESCRIPTION
        "The IP address of the OSPFv3 interface." 
    ::= { ospf3IntfInfoEntry 3 }

ospf3IfInfoAreaID OBJECT-TYPE
    SYNTAX IpAddress 
    MAX-ACCESS read-only
    STATUS current
    DESCRIPTION
        "The AreaID of the area that the interface belongs." 
    ::= { ospf3IntfInfoEntry 4 }

ospf3IfInfoAdminStatus  OBJECT-TYPE
    SYNTAX  INTEGER {
        down(0),
        up(1)
        }
    MAX-ACCESS read-only
    STATUS current
    DESCRIPTION
        "Admin Status of the interface:
        down(0), up(1)." 
    ::= { ospf3IntfInfoEntry 5 }

ospf3IfInfoPassive  OBJECT-TYPE
    SYNTAX  INTEGER {
        disabled(0),
        enabled(1)
        }
    MAX-ACCESS read-only
    STATUS current
    DESCRIPTION
        "Passive status of the interface:
        disabled(0), enabled(1)." 
    ::= { ospf3IntfInfoEntry 6 }

ospf3IfInfoNetworkType  OBJECT-TYPE
    SYNTAX  INTEGER {
                            broadcast(1),
                            nbma(2),
                            pointToPoint(3),
                            pointToMultipoint(5)
                            }
    MAX-ACCESS read-only
    STATUS current
    DESCRIPTION
        "Network type of the interface:
        broadcast(1),nbma(2),pointToPoint(3),pointToMultipoint(5)." 
    ::= { ospf3IntfInfoEntry 7 }

ospf3IfInfoState  OBJECT-TYPE
    SYNTAX  INTEGER {
                            down(1),
                            loopback(2),
                            waiting(3),
                            pointToPoint(4),
                            designatedRouter(5),
                            backupDesignatedRouter(6),
                            otherDesignatedRouter(7),
                            standby(8)
                            }
    MAX-ACCESS read-only
    STATUS current
    DESCRIPTION
        "The state of the interface:
        Down(0), Loopback(1),
        Waiting(2), P to P(3),
        DR(4), BackuDR(5),
        DR Other(6)." 
    ::= { ospf3IntfInfoEntry 8 }

ospf3IfInfoPriority   OBJECT-TYPE
   SYNTAX INTEGER (1..255) 
    MAX-ACCESS read-only
    STATUS current 
    DESCRIPTION
        "Interface router priority" 
    ::= { ospf3IntfInfoEntry 9 }

ospf3IfInfoDesignatedRouterID OBJECT-TYPE
    SYNTAX IpAddress
    MAX-ACCESS read-only
    STATUS current
    DESCRIPTION
        "The OSPFv3 Designated Router ID for this OSPFv3 interface." 
    ::= { ospf3IntfInfoEntry 10 }

ospf3IfInfoBackupDesignatedRouterID OBJECT-TYPE
    SYNTAX IpAddress
    MAX-ACCESS read-only
    STATUS current
    DESCRIPTION
        "The OSPFv3 Backup Designated Router ID for this OSPFv3
         interface." 
    ::= { ospf3IntfInfoEntry 11 }

ospf3IfInfoHello  OBJECT-TYPE 
    SYNTAX INTEGER (1..65535) 
    MAX-ACCESS read-only
    STATUS current
    DESCRIPTION
        "The hello timer for this OSPF3 interface." 
    ::= { ospf3IntfInfoEntry 12 }

ospf3IfInfoDead   OBJECT-TYPE
   SYNTAX INTEGER (1..65535) 
    MAX-ACCESS read-only
    STATUS current 
    DESCRIPTION
        "The dead timer for this OSPFv3 interface." 
    ::= { ospf3IntfInfoEntry 13 }

ospf3IfInfoPoll OBJECT-TYPE
    SYNTAX Integer32
    MAX-ACCESS read-only
    STATUS current
    DESCRIPTION
        "The OSPFv3 Poll interval for this OSPFv3 interface." 
    ::= { ospf3IntfInfoEntry 14 }

ospf3IfInfoRetransmit OBJECT-TYPE
    SYNTAX INTEGER (1..3600) 
    MAX-ACCESS read-only
    STATUS current
    DESCRIPTION
        "The retransmit interval for this OSPFv3 interface." 
    ::= { ospf3IntfInfoEntry 15 }

ospf3IfInfoTransitDelay  OBJECT-TYPE
   SYNTAX INTEGER (1..3600) 
    MAX-ACCESS read-only
    STATUS current
    DESCRIPTION
        "The transit delay for this OSPFv3 interface." 
    ::= { ospf3IntfInfoEntry 16 }
        
ospf3IfInfoTotalNeighbours OBJECT-TYPE
    SYNTAX Integer32
    MAX-ACCESS read-only
    STATUS current
    DESCRIPTION
        "The total number of neighbours for this OSPFv3 interface." 
    ::= { ospf3IntfInfoEntry 17 }

ospf3IfInfoEvents OBJECT-TYPE
    SYNTAX Integer32
    MAX-ACCESS read-only
    STATUS current
    DESCRIPTION
        "The total number of events for this OSPF3 interface." 
    ::= { ospf3IntfInfoEntry 18 }

ospf3IfInfoMetricCost OBJECT-TYPE
    SYNTAX Integer32
    MAX-ACCESS read-only
    STATUS current
    DESCRIPTION
        "The cost of this OSPF3 interface." 
    ::= { ospf3IntfInfoEntry 19 }

ospf3IfInfoAuthSpi  OBJECT-TYPE
    SYNTAX Unsigned32 (256..4294967295)
    MAX-ACCESS read-only
    STATUS current
    DESCRIPTION
        "Authentication Spi Id(256 - 4294967295)"
    ::= { ospf3IntfInfoEntry 20 }

ospf3IfInfoAuthEnable OBJECT-TYPE
    SYNTAX  INTEGER {
        disabled(0),
        enabled(1)
        }
    MAX-ACCESS read-only
    STATUS current
    DESCRIPTION
    "Authentication Status
        disabled(0),
        enabled(1)" 
    ::= { ospf3IntfInfoEntry 21 }

ospf3IfInfoAuthType  OBJECT-TYPE 
    SYNTAX  INTEGER {
        none(0),
        md5(2),
        sha1(1)
        } 
    MAX-ACCESS read-only
    STATUS current
    DESCRIPTION
    "Authentication Type
        none(0),
        md5(2),
        sha1(1)" 
    ::= { ospf3IntfInfoEntry 22 }

ospf3IfInfoAuthKey   OBJECT-TYPE
    SYNTAX OCTET STRING (SIZE(4..40)) 
    MAX-ACCESS read-only
    STATUS current 
    DESCRIPTION
    "Authentication Key
    Hex-string MD5 key - 32 chars (128 bits)
    Hex-string SHA-1 key - 40 chars (160 bits)" 
    ::= { ospf3IntfInfoEntry 23 }

ospf3IfInfoEncrySpi  OBJECT-TYPE
    SYNTAX Unsigned32 (256..4294967295)
    MAX-ACCESS read-only
    STATUS current
    DESCRIPTION
        "Encryption Spi Id(256 - 4294967295)"
    ::= { ospf3IntfInfoEntry 24 }

ospf3IfInfoEncryEnable OBJECT-TYPE
    SYNTAX  INTEGER {
        disabled(0),
        enabled(1)
        }
    MAX-ACCESS read-only
    STATUS current
    DESCRIPTION
    "Encryption Status
        disabled(0),
        enabled(1)" 
    ::= { ospf3IntfInfoEntry 25 }

ospf3IfInfoEncryType  OBJECT-TYPE 
    SYNTAX  INTEGER {
        null(0),
        tripledes(2),
        aes(3)
        } 
    MAX-ACCESS read-only
    STATUS current
    DESCRIPTION
    "Encryption Authentication Type
        null(0),
        3des(2),
        aes(3)"
   ::= { ospf3IntfInfoEntry 26 }

ospf3IfInfoEncryKey   OBJECT-TYPE
    SYNTAX OCTET STRING (SIZE(4..48)) 
    MAX-ACCESS read-only
    STATUS current 
    DESCRIPTION
    "Encryption Key
    Hex-string AES key - 32 chars (128 bits)
    Hex-string 3DES key - 48 chars (192 bits)" 
    ::= { ospf3IntfInfoEntry 27 }


ospf3IfInfoEncryAuthType  OBJECT-TYPE 
    SYNTAX  INTEGER {
        none(0),
        md5(2),
        sha1(1)
        }
    MAX-ACCESS read-only
    STATUS current
    DESCRIPTION
    "Encryption Authentication Type
        none(0),
        md5(2),
        sha1(1)"
    ::= { ospf3IntfInfoEntry 28 }

ospf3IfInfoEncryAuthKey   OBJECT-TYPE
    SYNTAX OCTET STRING (SIZE(4..40)) 
    MAX-ACCESS read-only
    STATUS current 
    DESCRIPTION
    "Encryption Authentication Key
    Hex-string MD5 key - 32 chars (128 bits)
    Hex-string SHA-1 key - 40 chars (160 bits)" 
    ::= { ospf3IntfInfoEntry 29 }

ospf3IfInfoLsaSupress  OBJECT-TYPE
    SYNTAX  INTEGER {
        disabled(0),
        enabled(1)
        }
    MAX-ACCESS read-only
    STATUS current
    DESCRIPTION
        "Lsa supression status of the interface:
        disabled(0), enabled(1)."
    ::= { ospf3IntfInfoEntry 30 }

-- OSPFv3 Virtual Interface Table
    ospf3VirtIntfInfoTable OBJECT-TYPE
            SYNTAX          SEQUENCE OF Ospf3VirtIntfInfoEntry
            MAX-ACCESS      not-accessible
            STATUS          current
            DESCRIPTION
           "The table of OSPFv3 Virtual Interface information."
            ::= { ospf3Info 4 }

    ospf3VirtIntfInfoEntry OBJECT-TYPE
            SYNTAX          Ospf3VirtIntfInfoEntry
            MAX-ACCESS      not-accessible
            STATUS          current
            DESCRIPTION
                "Information about a single virtual interface."
        INDEX { ospf3VirtIfInfoIndex }
         ::= { ospf3VirtIntfInfoTable 1 }


    Ospf3VirtIntfInfoEntry ::= SEQUENCE {
            ospf3VirtIfInfoIndex          Integer32,
            ospf3VirtIfInfoAreaId            IpAddress,
            ospf3VirtIfInfoNeighbor          IpAddress,
            ospf3VirtIfInfoTransitDelay      INTEGER,
            ospf3VirtIfInfoRetransInterval   INTEGER,
            ospf3VirtIfInfoHelloInterval     INTEGER,
            ospf3VirtIfInfoRtrDeadInterval   INTEGER,
            ospf3VirtIfInfoState             INTEGER,
            ospf3VirtIfInfoEvents            INTEGER,
            ospf3VirtIfInfoStatus         INTEGER,
            ospf3VirtIfInfoLinkScopeLsaCount INTEGER,
            ospf3VirtIfInfoLinkLsaCksumSum   INTEGER
            }

    ospf3VirtIfInfoIndex OBJECT-TYPE
            SYNTAX          Integer32
            MAX-ACCESS      read-only
            STATUS          current
            DESCRIPTION
            "The OSPFv3 virtual interface number for which the OSPFv3
             info table is related."
            ::= { ospf3VirtIntfInfoEntry 1 }

    ospf3VirtIfInfoAreaId OBJECT-TYPE
            SYNTAX          IpAddress
            MAX-ACCESS      read-only
            STATUS          current
            DESCRIPTION
                "The transit area that the virtual link
                traverses.  By definition, this is not
                Area 0."
            ::= { ospf3VirtIntfInfoEntry 2 }

    ospf3VirtIfInfoNeighbor OBJECT-TYPE
            SYNTAX          IpAddress
            MAX-ACCESS      read-only
            STATUS          current
            DESCRIPTION
                "The Router ID of the virtual neighbor."
            ::= { ospf3VirtIntfInfoEntry 3 }

    ospf3VirtIfInfoTransitDelay OBJECT-TYPE
            SYNTAX          INTEGER
            UNITS           "seconds"
            MAX-ACCESS      read-only
            STATUS          current
            DESCRIPTION
                "The estimated number of seconds it takes to
                transmit a Link State Update packet over this
                interface."
            DEFVAL          { 1 }

            ::= { ospf3VirtIntfInfoEntry 5 }

    ospf3VirtIfInfoRetransInterval OBJECT-TYPE
            SYNTAX          INTEGER
            UNITS           "seconds"
            MAX-ACCESS      read-only
            STATUS          current
            DESCRIPTION
                "The number of seconds between link state
                advertisement retransmissions for adjacencies
                belonging to this interface.  This value is
                also used when retransmitting database
                description and Link State Request packets.  This
                value should be well over the expected
                round-trip time."
            DEFVAL          { 5 }
            ::= { ospf3VirtIntfInfoEntry 6 }

    ospf3VirtIfInfoHelloInterval OBJECT-TYPE
            SYNTAX          INTEGER
            UNITS           "seconds"
            MAX-ACCESS      read-only
            STATUS          current
            DESCRIPTION
                "The length of time, in seconds, between the
                Hello packets that the router sends on the
                interface.  This value must be the same for the
                virtual neighbor."
            DEFVAL          { 10 }
            ::= { ospf3VirtIntfInfoEntry 7 }

    ospf3VirtIfInfoRtrDeadInterval OBJECT-TYPE
            SYNTAX          INTEGER
            UNITS           "seconds"
            MAX-ACCESS      read-only
            STATUS          current
            DESCRIPTION
                "The number of seconds that a router's Hello
                packets have not been seen before its
                neighbors declare the router down.  This should
                be some multiple of the Hello interval.  This
                value must be the same for the virtual
                neighbor."
            DEFVAL          { 60 }
            ::= { ospf3VirtIntfInfoEntry 8 }

    ospf3VirtIfInfoState OBJECT-TYPE
            SYNTAX          INTEGER {
                            down(1),
                            pointToPoint(4)
                            }
            MAX-ACCESS      read-only
            STATUS          current
            DESCRIPTION
                "OSPF virtual interface states."
            ::= { ospf3VirtIntfInfoEntry 9 }

    ospf3VirtIfInfoEvents OBJECT-TYPE
            SYNTAX          INTEGER
            MAX-ACCESS      read-only
            STATUS          current
            DESCRIPTION
                "The number of state changes or error events on
                this virtual link.

                Discontinuities in the value of this counter
                can occur at re-initialization of the management
                system and at other times as indicated by the
                value of ospfv3DiscontinuityTime."
            ::= { ospf3VirtIntfInfoEntry 10 }

    ospf3VirtIfInfoStatus OBJECT-TYPE
            SYNTAX          INTEGER
            MAX-ACCESS      read-only
            STATUS          current
            DESCRIPTION
                "This object permits management of the table by
                facilitating actions such as row creation,
                construction, and destruction.

                The value of this object has no effect on
                whether other objects in this conceptual row can be
                modified."
            ::= { ospf3VirtIntfInfoEntry 11 }

    ospf3VirtIfInfoLinkScopeLsaCount OBJECT-TYPE
            SYNTAX          INTEGER
            MAX-ACCESS      read-only
            STATUS          current
            DESCRIPTION
                "The total number of Link-scope link state
                advertisements in this virtual link's link state
                database."

            ::= { ospf3VirtIntfInfoEntry 12 }

    ospf3VirtIfInfoLinkLsaCksumSum OBJECT-TYPE
            SYNTAX          INTEGER
            MAX-ACCESS      read-only
            STATUS          current
            DESCRIPTION
                "The 32-bit unsigned sum of the Link-scope link state
                advertisements' LS checksums contained in this
                virtual link's link state database.  The sum can be used
                to determine if there has been a change in a
                router's link state database or to compare the
                link state database of two routers."
            ::= { ospf3VirtIntfInfoEntry 13 }

-- OSPF3 Interface/Nbr Info Table

ospf3IfNbrTable OBJECT-TYPE
    SYNTAX SEQUENCE OF Ospf3IfNbrEntry
    MAX-ACCESS not-accessible
    STATUS current
    DESCRIPTION
      "The table of OSPFv3 Interface Neighbor information."
    ::= { ospf3Info 5 }

ospf3IfNbrEntry OBJECT-TYPE
    SYNTAX Ospf3IfNbrEntry
    MAX-ACCESS not-accessible
    STATUS current
    DESCRIPTION
      "Information about a OSPFv3 interface, neighbor pair."
    INDEX { ospf3IfNbrInfoIndex }
    ::= { ospf3IfNbrTable 1 }
 
Ospf3IfNbrEntry ::= SEQUENCE {
    ospf3IfNbrInfoIndex               Integer32,
    ospf3IfNbrIntfIndex               Integer32,
    ospf3IfNbrIntfInstanceID          Unsigned32,
    ospf3IfNbrRtrID                   IpAddress,
    ospf3IfNbrIpAddress               DisplayString,
    ospf3IfNbrPriority                Integer32,
    ospf3IfNbrState                   INTEGER,
    ospf3IfNbrEvents                  Integer32
    }
    
ospf3IfNbrInfoIndex OBJECT-TYPE
    SYNTAX Integer32
    MAX-ACCESS read-only
    STATUS current
    DESCRIPTION
        "The OSPFv3 neighbor table entry index for which 
          this table is related."
    ::= { ospf3IfNbrEntry 1}

ospf3IfNbrIntfIndex OBJECT-TYPE
    SYNTAX Integer32
    MAX-ACCESS read-only
    STATUS current
    DESCRIPTION
    "The OSPFv3 Interface number for which this Nbr table is 
         related."
    ::= { ospf3IfNbrEntry 2}

ospf3IfNbrIntfInstanceID OBJECT-TYPE
    SYNTAX Unsigned32
    MAX-ACCESS read-only
    STATUS current
    DESCRIPTION
    "The OSPFv3 Interface instance id for which this Nbr table is 
         related."
    ::= { ospf3IfNbrEntry 3}
    
ospf3IfNbrRtrID OBJECT-TYPE
    SYNTAX IpAddress 
    MAX-ACCESS read-only
    STATUS current
    DESCRIPTION
       "A 32-bit unsigned integer uniquely identifying the
        neighboring router in the Autonomous System."
    ::= { ospf3IfNbrEntry 4 }
    
ospf3IfNbrIpAddress OBJECT-TYPE
    SYNTAX DisplayString 
    MAX-ACCESS read-only
    STATUS current
    DESCRIPTION
       "The IPv6 address of the neighbor associated with
         the local link." 
    ::= { ospf3IfNbrEntry 5 }

ospf3IfNbrPriority OBJECT-TYPE
    SYNTAX Integer32
    MAX-ACCESS read-only
    STATUS current
    DESCRIPTION
    "The priority of the OSPFv3 neighbor."
    ::= { ospf3IfNbrEntry 6 }

ospf3IfNbrState OBJECT-TYPE
    SYNTAX  INTEGER {
                            down(1),
                            attempt(2),
                            init(3),
                            twoWay(4),
                            exchangeStart(5),
                            exchange(6),
                            loading(7),
                            full(8)
                            }
    MAX-ACCESS read-only
    STATUS current
    DESCRIPTION
      "The state of the relationship with this
       neighbor."
    ::= { ospf3IfNbrEntry 7 }

ospf3IfNbrEvents OBJECT-TYPE
    SYNTAX Integer32
    MAX-ACCESS read-only
    STATUS current
    DESCRIPTION
     "The number of times this neighbor relationship
      has changed state or an error has occurred."
    ::= { ospf3IfNbrEntry 8 }


-- OSPFv3 Interface/Routes Table

ospf3RoutesInfoTable OBJECT-TYPE
    SYNTAX SEQUENCE OF Ospf3RoutesInfoEntry
    MAX-ACCESS not-accessible
    STATUS current
    DESCRIPTION
      "The table of OSPFv3 routes information."
    ::= { ospf3Info 6 }

ospf3RoutesInfoEntry OBJECT-TYPE
    SYNTAX Ospf3RoutesInfoEntry
    MAX-ACCESS not-accessible
    STATUS current
    DESCRIPTION
      "OSPFv3 routes information."
    INDEX { ospf3RoutesInfoIndex }
    ::= { ospf3RoutesInfoTable 1 }

Ospf3RoutesInfoEntry ::= SEQUENCE {
    ospf3RoutesInfoIndex            Integer32,
    ospf3RoutesInfoDestination      DisplayString,
    ospf3RoutesInfoPrefixLen        INTEGER,
    ospf3RoutesInfoNextHop          DisplayString,
    ospf3RoutesInfoType             INTEGER,
    ospf3RoutesInfoAreaId           IpAddress,
    ospf3RoutesInfoCost             INTEGER,
    ospf3RoutesInfoType2Cost        INTEGER,
    ospf3RoutesInfoInterfaceIndex   Integer32
    }

ospf3RoutesInfoIndex OBJECT-TYPE
    SYNTAX Integer32
    MAX-ACCESS read-only
    STATUS current
    DESCRIPTION
        "The OSPFv3 route table entry index for which 
          this table is related."
    ::= { ospf3RoutesInfoEntry 1 }

ospf3RoutesInfoDestination OBJECT-TYPE
    SYNTAX DisplayString
    MAX-ACCESS read-only
    STATUS current
    DESCRIPTION
        " The Destination IPv6 Address of this route."
    ::= { ospf3RoutesInfoEntry 2 }

ospf3RoutesInfoPrefixLen OBJECT-TYPE
    SYNTAX INTEGER (1..128)
    MAX-ACCESS read-only
    STATUS current
    DESCRIPTION
        " Indicates the prefix length of the destination Address."
    ::= { ospf3RoutesInfoEntry 3 }

ospf3RoutesInfoNextHop OBJECT-TYPE
    SYNTAX DisplayString
    MAX-ACCESS read-only
    STATUS current
    DESCRIPTION
        "Next Hop IPv6 Address for this route. For direct routes it has the
           value ::0."
    ::= { ospf3RoutesInfoEntry 4 }

   ospf3RoutesInfoType OBJECT-TYPE
       SYNTAX      INTEGER {
                    intraArea (1), 
                    interArea (2), 
                    type1External (3), 
                    type2External (4)
                    }
       MAX-ACCESS  read-only
       STATUS      current
       DESCRIPTION
           "Type of the route"
       ::=  { ospf3RoutesInfoEntry 5 }

   ospf3RoutesInfoAreaId OBJECT-TYPE
       SYNTAX      IpAddress
       MAX-ACCESS  read-only
       STATUS      current
       DESCRIPTION
           " Area ID associated with the route "
       ::=  { ospf3RoutesInfoEntry 6 }
   
   ospf3RoutesInfoCost OBJECT-TYPE
       SYNTAX INTEGER (1..'FFFFFF'h)
       MAX-ACCESS  read-only
       STATUS      current
       DESCRIPTION
          " It is a Type 1 external metrics which is 
        expressed in the same units as OSPF interface
        cost ie. in terms of the OSPF link state metric. 
        If Type1 and Type2 cost are present, Type1 external
        metrics always take precedence."
       ::=  { ospf3RoutesInfoEntry 7 }
   
   ospf3RoutesInfoType2Cost OBJECT-TYPE
       SYNTAX INTEGER (1..'FFFFFF'h)
       MAX-ACCESS  read-only
       STATUS      current
       DESCRIPTION
           " Type 2 external metrics are configured with  
         the cost greater than any path internal to the AS. 
         Use of Type 2 external metrics assumes that routing 
         between AS is the major cost of routing a packet, and
             eliminates the need for conversion of external costs to
         internal link state metrics."
       ::=  { ospf3RoutesInfoEntry 8 }
   
   ospf3RoutesInfoInterfaceIndex OBJECT-TYPE
       SYNTAX Integer32 (0..2147483647)
       MAX-ACCESS  read-only
       STATUS      current
       DESCRIPTION
           " Interface Index associated with the route"
       ::=  { ospf3RoutesInfoEntry 9 }




-- Gateway Information
gatewayInfoTable OBJECT-TYPE
    SYNTAX  SEQUENCE OF GatewayInfoEntry
    MAX-ACCESS  not-accessible
    STATUS  current
    DESCRIPTION
        "The table containing information for the default gateways."
    ::= { gatewayInfo 1 }

gatewayInfoEntry OBJECT-TYPE
    SYNTAX  GatewayInfoEntry
    MAX-ACCESS  not-accessible
    STATUS  current
    DESCRIPTION
        "A row in the gateway information table"
    INDEX   { gatewayInfoIndex }
    ::= { gatewayInfoTable 1 }

GatewayInfoEntry ::= SEQUENCE {
    gatewayInfoIndex         Integer32,
    gatewayInfoAddr          IpAddress,
    gatewayInfoStatus        INTEGER
    }

gatewayInfoIndex OBJECT-TYPE
    SYNTAX  Integer32
    MAX-ACCESS  read-only
    STATUS  current
    DESCRIPTION
        "The gateway number for which the information is related."
    ::= { gatewayInfoEntry 1}

gatewayInfoAddr OBJECT-TYPE
    SYNTAX  IpAddress
    MAX-ACCESS  read-only
    STATUS  current
    DESCRIPTION
        "The IP address of the default gateway."
    ::= { gatewayInfoEntry 2 }


gatewayInfoStatus OBJECT-TYPE
    SYNTAX  INTEGER {
        up(1),
        failed(2)
    }  
    MAX-ACCESS  read-only
    STATUS  current
    DESCRIPTION
        "The status of the default gateway."
    ::= { gatewayInfoEntry 4 }

ipInfoBootpRelayState OBJECT-TYPE
    SYNTAX  INTEGER {
        enabled(2),
        disabled(3)
    }   
    MAX-ACCESS  read-only
    STATUS  current
    DESCRIPTION
        "The state of BOOTP relay."
    ::= { ipInfo 4 }

ipInfoBootpRelayAddr OBJECT-TYPE
    SYNTAX  IpAddress
    MAX-ACCESS  read-only
    STATUS  current
    DESCRIPTION
        "The IP address of BOOTP server."
    ::= { ipInfo 5 }

ipInfoBootpRelayAddr2 OBJECT-TYPE
    SYNTAX  IpAddress
    MAX-ACCESS  read-only
    STATUS  current
    DESCRIPTION
        "The IP address of second BOOTP server."
    ::= { ipInfo 6 }


ipInfoFwdState OBJECT-TYPE
    SYNTAX  INTEGER { 
    on(1),
    off(2)
    }   
    MAX-ACCESS  read-only
    STATUS  current
    DESCRIPTION
        "IP forwarding global state." 
    ::= { ipInfo 7 }

ipInfoFwdDirectedBcast OBJECT-TYPE
    SYNTAX  INTEGER { 
        enabled(2),
        disabled(3)
    }   
    MAX-ACCESS  read-only
    STATUS  current
    DESCRIPTION
        "The state of forwarding directed broadcasts."
    ::= { ipInfo 8 }

-- igmp snooping info table
igmpInfoTable OBJECT-TYPE
    SYNTAX SEQUENCE OF IgmpInfoEntry
    MAX-ACCESS not-accessible
    STATUS current
    DESCRIPTION
      "The table of IGMP group membership information."
    ::= { igmpInfo 1 }

igmpInfoEntry OBJECT-TYPE
    SYNTAX IgmpInfoEntry
    MAX-ACCESS not-accessible
    STATUS current
    DESCRIPTION
      "Information about an IGMP group member ."
    INDEX { igmpInfoIndex }
    ::= { igmpInfoTable 1 }
 
IgmpInfoEntry ::= SEQUENCE {
    igmpInfoIndex             INTEGER,
    igmpInfoGroupId           IpAddress,
    igmpInfoVlanId            INTEGER,
    igmpInfoSrcTrunk          Unsigned32,
    igmpInfoSrcPort           PortNumber,
    igmpInfoVersion           INTEGER,
    igmpInfoExpires           DisplayString,
    igmpInfoMode              INTEGER,
    igmpInfoSourceIp          IpAddress,
    igmpInfoFwd               INTEGER,
    igmpInfoGrpExpires        DisplayString
    }
 
igmpInfoIndex OBJECT-TYPE
    SYNTAX INTEGER
    MAX-ACCESS read-only
    STATUS current
    DESCRIPTION
    "The igmp group number for which the IGMP info table is related."
    ::= { igmpInfoEntry 1}

igmpInfoGroupId OBJECT-TYPE
    SYNTAX IpAddress
    MAX-ACCESS read-only
    STATUS current
    DESCRIPTION
    "The IP address of the IGMP group." 
    ::= { igmpInfoEntry 2}

igmpInfoVlanId OBJECT-TYPE
    SYNTAX INTEGER
    MAX-ACCESS read-only
    STATUS current
    DESCRIPTION
    "The VLAN ID for this IGMP group." 
    ::= { igmpInfoEntry 3}

igmpInfoSrcTrunk OBJECT-TYPE
    SYNTAX Unsigned32
    MAX-ACCESS read-only
    STATUS current
    DESCRIPTION
        "The downstream trunk number."
    ::= { igmpInfoEntry 4}

igmpInfoSrcPort OBJECT-TYPE
    SYNTAX PortNumber
    MAX-ACCESS read-only
    STATUS current
    DESCRIPTION
        "The downstream port number."
    ::= { igmpInfoEntry 5}

igmpInfoVersion OBJECT-TYPE
    SYNTAX INTEGER { 
        v3(1),
        v2(2),
        v1(3)
    }
    MAX-ACCESS read-only
    STATUS current
    DESCRIPTION
    "The Version of IGMP host." 
    ::= { igmpInfoEntry 6}

igmpInfoExpires OBJECT-TYPE
    SYNTAX DisplayString 
    MAX-ACCESS read-only
    STATUS current
    DESCRIPTION
    "The expiration time for this host." 
    ::= { igmpInfoEntry 7 }


igmpInfoMode OBJECT-TYPE
    SYNTAX INTEGER { 
        exclude(1),
        include(2),
        na(3)
    }
    MAX-ACCESS read-only
    STATUS current
    DESCRIPTION
    "The IGMPv3 filter-mode for this host.
         Returned values: 
        exclude(1) - the IGMPv3 filter-mode is exclude. 
        include(2) - the IGMPv3 filter-mode is include. 
        na(3)      - not applicable(v1 and v2)." 
    ::= { igmpInfoEntry 8 }

igmpInfoSourceIp OBJECT-TYPE 
    SYNTAX IpAddress
    MAX-ACCESS read-only
    STATUS current
    DESCRIPTION
    "The source IP address of the IGMP group." 
    ::= { igmpInfoEntry 9 }

igmpInfoFwd OBJECT-TYPE
    SYNTAX INTEGER { 
        yes(1),
        no(2)
    }
    MAX-ACCESS read-only
    STATUS current
    DESCRIPTION
    "The IGMPv3 forwarding for this source/group IP for this host." 
    ::= { igmpInfoEntry 10 }

igmpInfoGrpExpires OBJECT-TYPE
    SYNTAX DisplayString 
    MAX-ACCESS read-only
    STATUS current
    DESCRIPTION
    "The expiration time for the group." 
    ::= { igmpInfoEntry 11 }



igmpMrtrInfoTable OBJECT-TYPE
    SYNTAX SEQUENCE OF IgmpMrtrInfoEntry
    MAX-ACCESS not-accessible
    STATUS current
    DESCRIPTION
      "The table of IGMP mrouters."
    ::= { igmpInfo 2 }

igmpMrtrInfoEntry OBJECT-TYPE
    SYNTAX IgmpMrtrInfoEntry
    MAX-ACCESS not-accessible
    STATUS current
    DESCRIPTION
      "Information about an IGMP mrouter."
    INDEX { igmpMrtrInfoIndex }
    ::= { igmpMrtrInfoTable 1 }
 
IgmpMrtrInfoEntry ::= SEQUENCE {
    igmpMrtrInfoIndex         INTEGER,
    igmpMrtrInfoVlanId        INTEGER,
    igmpMrtrInfoPortId        DisplayString,
    igmpMrtrInfoVersion       INTEGER,
    igmpMrtrInfoExpires       DisplayString,
    igmpMrtrInfoMrt           Integer32,
    igmpMrtrInfoQrv           INTEGER,
    igmpMrtrInfoQqic          INTEGER,
    igmpMrtrInfoSrcIp         IpAddress
    }
 
igmpMrtrInfoIndex OBJECT-TYPE
    SYNTAX INTEGER
    MAX-ACCESS read-only
    STATUS current
    DESCRIPTION
    "The mrouter number for which the IGMP mrouter info table is related."
    ::= { igmpMrtrInfoEntry 1}

igmpMrtrInfoVlanId OBJECT-TYPE
    SYNTAX INTEGER
    MAX-ACCESS read-only
    STATUS current
    DESCRIPTION
    "The VLAN ID on which this IGMP mrouter is attached." 
    ::= { igmpMrtrInfoEntry 2}

igmpMrtrInfoPortId OBJECT-TYPE
    SYNTAX DisplayString
    MAX-ACCESS read-only
    STATUS current
    DESCRIPTION
    "The port/portchannel alias on which this IGMP mrouter is attached." 
    ::= { igmpMrtrInfoEntry 3}

igmpMrtrInfoVersion OBJECT-TYPE
    SYNTAX INTEGER {
    v1(1),
    v2(2),
    v3(3),
    pim(4)
    }
    MAX-ACCESS read-only
    STATUS current
    DESCRIPTION
    "The version of this IGMP mrouter." 
    ::= { igmpMrtrInfoEntry 4}

igmpMrtrInfoExpires OBJECT-TYPE
    SYNTAX DisplayString 
    MAX-ACCESS read-only
    STATUS current
    DESCRIPTION
    "The expiration time for this mrouter." 
    ::= { igmpMrtrInfoEntry 5 }

igmpMrtrInfoMrt OBJECT-TYPE
    SYNTAX Integer32
    MAX-ACCESS read-only
    STATUS current
    DESCRIPTION
    "The Maximum Query Response time of this IGMP mrouter." 
    ::= { igmpMrtrInfoEntry 6 }

igmpMrtrInfoQrv OBJECT-TYPE
    SYNTAX INTEGER
    MAX-ACCESS read-only
    STATUS current
    DESCRIPTION
    "The Querier Robustness value of this IGMP mrouter." 
    ::= { igmpMrtrInfoEntry 7 }

igmpMrtrInfoQqic OBJECT-TYPE
    SYNTAX INTEGER
    MAX-ACCESS read-only
    STATUS current
    DESCRIPTION
    "The Querier query interval code of this IGMP mrouter." 
    ::= { igmpMrtrInfoEntry 8 }

igmpMrtrInfoSrcIp OBJECT-TYPE
    SYNTAX IpAddress
    MAX-ACCESS read-only
    STATUS current
    DESCRIPTION
        "The Source IP of this IGMP mrouter."
    ::= { igmpMrtrInfoEntry 10 }


igmpClearTables OBJECT-TYPE
    SYNTAX INTEGER {
        ok(0),
        clearGroups(1),
        clearMrouters(2),
        clearAll(3)
    }
    MAX-ACCESS read-write
    STATUS current
    DESCRIPTION
        "Clear the IGMP tables. When setting clearGroups(1), the dynamic
         groups are removed, when setting clearMrouters(2), the mrouter tables
         are removed and when setting clearAll(3), both the dynamic groups
         and the mrouter tables are removed.
         When read, ok(0) is always returned."
    ::= { igmpInfo 3 }


-- nbr Info Table
nbrInfoTable OBJECT-TYPE
    SYNTAX SEQUENCE OF NbrInfoEntry
    MAX-ACCESS not-accessible
    STATUS current
    DESCRIPTION
        "The table of nbrcache information."
    ::= { nbrInfo 1 }

nbrInfoEntry OBJECT-TYPE
    SYNTAX NbrInfoEntry
    MAX-ACCESS not-accessible
    STATUS current
    DESCRIPTION
        "Information about neighbor discovery protocol."
    INDEX { nbrInfoIndex }
    ::= { nbrInfoTable 1 }

NbrInfoEntry ::= SEQUENCE {
    nbrInfoIndex         Integer32,
    nbrInfoDestIp        DisplayString,
    nbrInfoState         INTEGER,
    nbrInfoMacAddr       PhysAddress,
    nbrInfoVlanId        Integer32,
    nbrInfoPortNum       Integer32,
    nbrInfoAge           Integer32,
    nbrInfoInterface     Integer32
    }

nbrInfoIndex  OBJECT-TYPE
    SYNTAX  Integer32
    MAX-ACCESS  read-only
    STATUS  current
    DESCRIPTION
        "The index of the nbrcache entry."
    ::= { nbrInfoEntry 1 }

nbrInfoDestIp OBJECT-TYPE
    SYNTAX   DisplayString 
    MAX-ACCESS  read-only
    STATUS  current
    DESCRIPTION
        "The destination IP address of the nbrcache entry."
    ::= { nbrInfoEntry 2 }

nbrInfoState  OBJECT-TYPE
    SYNTAX  INTEGER  {
        static(1),
        reach(2),
        incomplete(3),
        stale(4),
        delay(5),
        probe(6),
        unknown(7)
    }
    MAX-ACCESS  read-only
    STATUS  current
    DESCRIPTION
        "The state of the nbrcache entry."
    ::= { nbrInfoEntry 3 }

nbrInfoMacAddr OBJECT-TYPE
    SYNTAX  PhysAddress
    MAX-ACCESS  read-only
    STATUS  current
    DESCRIPTION
        "The MAC address for the nbrcache entry."
    ::= { nbrInfoEntry 4 }

nbrInfoVlanId  OBJECT-TYPE 
    SYNTAX  Integer32 
    MAX-ACCESS  read-only 
    STATUS  current 
    DESCRIPTION 
        "The VLAN identifier for the nbrcache entry." 
    ::= { nbrInfoEntry 5 }

nbrInfoPortNum   OBJECT-TYPE
    SYNTAX  Integer32
    MAX-ACCESS  read-only
    STATUS  current
    DESCRIPTION
        "The  port number on which this entry's equivalence is effective."  
    ::= { nbrInfoEntry 6 }

nbrInfoAge   OBJECT-TYPE
    SYNTAX  Integer32
    MAX-ACCESS  read-only
    STATUS  current
    DESCRIPTION
        "The used time for the nbrcache entry."  
    ::= { nbrInfoEntry 7 }

nbrInfoInterface  OBJECT-TYPE
    SYNTAX  Integer32
    MAX-ACCESS  read-only
    STATUS  current
    DESCRIPTION
        "The interface number for which the destination address is applicable."  
    ::= { nbrInfoEntry 8 }


nbrClear OBJECT-TYPE
    SYNTAX  INTEGER {
        ok(1),
        clear(2)
        }
    MAX-ACCESS  read-write
    STATUS  current 
    DESCRIPTION
        "Setting this value to clear(2) clears the Nbr cache,
         When read ok(1) is  returned."
    ::= { nbrInfo 2 }
    
-- ipv6 PMTU Info Table
ipv6PmtuInfoTable OBJECT-TYPE
    SYNTAX SEQUENCE OF Ipv6PmtuInfoEntry
    MAX-ACCESS  not-accessible
    STATUS   current
    DESCRIPTION
        "The table of Ipv6 PMTU entries."
    ::={ ipv6PmtuInfo 1 }

ipv6PmtuInfoEntry OBJECT-TYPE
    SYNTAX  Ipv6PmtuInfoEntry
    MAX-ACCESS  not-accessible
    STATUS  current
    DESCRIPTION
       "A row in the ipv6 PMTU entries table."
    INDEX   { ipv6PmtuInfoIndx }
    ::= { ipv6PmtuInfoTable 1 }
    
Ipv6PmtuInfoEntry ::= SEQUENCE {
    ipv6PmtuInfoIndx            Integer32,
    ipv6PmtuInfoDestIp          DisplayString,
    ipv6PmtuInfoSinceTime       DisplayString,
    ipv6PmtuInfoValue           Integer32
    }

ipv6PmtuInfoIndx OBJECT-TYPE
    SYNTAX  Integer32
    MAX-ACCESS  read-only
    STATUS  current
    DESCRIPTION
        "The index of this ipv6 PMTU table entries."
    ::= { ipv6PmtuInfoEntry 1 }

ipv6PmtuInfoDestIp OBJECT-TYPE
    SYNTAX  DisplayString
    MAX-ACCESS  read-only
    STATUS  current
    DESCRIPTION
        "The destination of the pMTU."
    ::= { ipv6PmtuInfoEntry 2 }

ipv6PmtuInfoSinceTime OBJECT-TYPE
    SYNTAX  DisplayString
    MAX-ACCESS  read-only
    STATUS  current
    DESCRIPTION
        "The addubt time of the pMTU."
    ::= { ipv6PmtuInfoEntry 3 }

ipv6PmtuInfoValue OBJECT-TYPE
    SYNTAX  Integer32
    MAX-ACCESS  read-only
    STATUS  current
    DESCRIPTION
        "The vlaue of this ipv6 PMTU table entries."
    ::= { ipv6PmtuInfoEntry 4 }



-- route6 Info Table
ipRoute6InfoTable OBJECT-TYPE
    SYNTAX  SEQUENCE OF IpRoute6InfoEntry
    MAX-ACCESS  not-accessible
    STATUS  current
    DESCRIPTION
        "The table of run-time IP6 routes."
    ::= { ipRoute6Info 1 }

ipRoute6InfoEntry OBJECT-TYPE
    SYNTAX  IpRoute6InfoEntry
    MAX-ACCESS  not-accessible
    STATUS  current
    DESCRIPTION
        "A row in the run-time IP6 route table."
    INDEX   { ipRoute6InfoIndx }
    ::= { ipRoute6InfoTable 1 }

IpRoute6InfoEntry ::= SEQUENCE {
    ipRoute6InfoIndx            Integer32,
    ipRoute6InfoDestIp          DisplayString,
    ipRoute6InfoPrefLen         INTEGER,
    ipRoute6InfoInterface       Integer32,
    ipRoute6InfoNextHop         DisplayString,
    ipRoute6InfoProto           INTEGER
    }

ipRoute6InfoIndx OBJECT-TYPE
    SYNTAX  Integer32
    MAX-ACCESS  read-only
    STATUS  current
    DESCRIPTION
        "The index of this route6 table."
    ::= { ipRoute6InfoEntry 1 }

ipRoute6InfoDestIp OBJECT-TYPE
    SYNTAX  DisplayString
    MAX-ACCESS  read-only
    STATUS  current
    DESCRIPTION
        "The destination of the route."
    ::= { ipRoute6InfoEntry 2 }

ipRoute6InfoPrefLen OBJECT-TYPE 
    SYNTAX  INTEGER (1..128)
    MAX-ACCESS  read-only 
    STATUS  current 
    DESCRIPTION 
        "The destination prefix length of the route."
    ::= { ipRoute6InfoEntry 3}

ipRoute6InfoInterface OBJECT-TYPE
    SYNTAX  Integer32
    MAX-ACCESS  read-only
    STATUS  current
    DESCRIPTION
        "The interface of the route."
    ::= { ipRoute6InfoEntry 4 }

ipRoute6InfoNextHop  OBJECT-TYPE
    SYNTAX  DisplayString
    MAX-ACCESS  read-only
    STATUS  current
    DESCRIPTION
        "The next hop of the route."
    ::= { ipRoute6InfoEntry 5 }

ipRoute6InfoProto  OBJECT-TYPE
    SYNTAX  INTEGER {
        local(2),
        static(3),
        nbrdis(4),
        ripng(5),
        ospf(6),
        intmgmt(10),
        extmgmt(11),
        intmgmtND(12),
        extmgmtND(13)
        }
    MAX-ACCESS  read-only
    STATUS  current
    DESCRIPTION
        "The protocol type of the route."
    ::= { ipRoute6InfoEntry 6 }

-- IPv6 Gateway Info

gatewayIPv6InfoTable OBJECT-TYPE
    SYNTAX  SEQUENCE OF GatewayIPv6InfoEntry
    MAX-ACCESS  not-accessible
    STATUS  current
    DESCRIPTION
        "The table containing information for the IPv6 default gateways."
    ::= { gatewayIPv6Info 1 }

gatewayIPv6InfoEntry OBJECT-TYPE
    SYNTAX  GatewayIPv6InfoEntry
    MAX-ACCESS  not-accessible
    STATUS  current
    DESCRIPTION
        "A row in the IPv6 gateway information table"
    INDEX   { ipGatewayIPv6InfoIndex }
    ::= { gatewayIPv6InfoTable 1 }

GatewayIPv6InfoEntry ::= SEQUENCE {
    ipGatewayIPv6InfoIndex   Integer32,
    ipGatewayIPv6InfoAddr    IpAddress,
    ipGatewayIPv6InfoState   INTEGER
    }

ipGatewayIPv6InfoIndex OBJECT-TYPE
    SYNTAX  Integer32
    MAX-ACCESS  read-only
    STATUS  current
    DESCRIPTION
        "The IPv6 gateway number for which the information is related."
    ::= { gatewayIPv6InfoEntry 1}

ipGatewayIPv6InfoAddr OBJECT-TYPE
    SYNTAX  IpAddress
    MAX-ACCESS  read-only
    STATUS  current
    DESCRIPTION
        "The IP address for the IPv6 default gateway."
    ::= { gatewayIPv6InfoEntry 2 }

ipGatewayIPv6InfoState   OBJECT-TYPE
    SYNTAX  INTEGER {
        enable(1),
        disable(2)
        }
    MAX-ACCESS  read-only
    STATUS  current
    DESCRIPTION
        "The state for the IPv6 Default Gateway."
    ::= { gatewayIPv6InfoEntry 3 }

-- nbrcache Info Table


rip2GeneralInfo OBJECT IDENTIFIER ::= { rip2Info 1 }

ripInfoState OBJECT-TYPE
    SYNTAX INTEGER {
        on(1),
        off(2)
        }
    MAX-ACCESS read-only
    STATUS current
    DESCRIPTION
    "RIP global state."
    ::= { rip2GeneralInfo 1 }

ripInfoUpdatePeriod OBJECT-TYPE
    SYNTAX  INTEGER  (1..120)
    MAX-ACCESS  read-only
    STATUS  current
    DESCRIPTION
        "Update Period in seconds."
    ::= { rip2GeneralInfo 2 }


rip2InfoIntfTable OBJECT-TYPE
    SYNTAX SEQUENCE OF RipInfoIntfEntry
    MAX-ACCESS not-accessible
    STATUS current
    DESCRIPTION
      "The information table of RIP."
    ::= { rip2Info 2 }

ripInfoIntfEntry OBJECT-TYPE
    SYNTAX RipInfoIntfEntry
    MAX-ACCESS not-accessible
    STATUS current
    DESCRIPTION
      "Information about  RIP on IP interface."
    INDEX { ripInfoIntfIndex }
    ::= { rip2InfoIntfTable 1 }
 
RipInfoIntfEntry ::= SEQUENCE {
    ripInfoIntfIndex          Integer32,
    ripInfoIntfVersion        INTEGER,
    ripInfoIntfAddress        IpAddress,
    ripInfoIntfState          INTEGER,
    ripInfoIntfListen         INTEGER,
    ripInfoIntfTrigUpdate     INTEGER,
    ripInfoIntfMcastUpdate    INTEGER,
    ripInfoIntfPoisonReverse  INTEGER,
    ripInfoIntfSupply         INTEGER,
    ripInfoIntfMetric         INTEGER, 
    ripInfoIntfAuth           INTEGER, 
    ripInfoIntfKey            DisplayString,
    ripInfoIntfDefault        INTEGER
    }
 
ripInfoIntfIndex OBJECT-TYPE
    SYNTAX Integer32
    MAX-ACCESS read-only
    STATUS current
    DESCRIPTION
    "The interface number for which the RIP information is related."
    ::= { ripInfoIntfEntry 1 }

ripInfoIntfVersion OBJECT-TYPE
    SYNTAX INTEGER {
        ripVersion1(1),
        ripVersion2(2),
        ripVersionBoth(3)
        }
    MAX-ACCESS read-only
    STATUS current
    DESCRIPTION
        "RIP version."
    ::= { ripInfoIntfEntry 2 }

ripInfoIntfAddress OBJECT-TYPE
    SYNTAX  IpAddress 
    MAX-ACCESS read-only
    STATUS current
    DESCRIPTION
        "The interface address."
    ::= { ripInfoIntfEntry 3 } 

ripInfoIntfState OBJECT-TYPE
    SYNTAX INTEGER {
        enabled(1),
        disabled(2)
        }
    MAX-ACCESS read-only
    STATUS current
    DESCRIPTION
        "The status of RIP protocol."
    ::= { ripInfoIntfEntry 4 }

ripInfoIntfListen OBJECT-TYPE
    SYNTAX INTEGER {
        enabled(1),
        disabled(2)
        }
    MAX-ACCESS read-only
    STATUS current
    DESCRIPTION
        "The status of listening to route updates."
    ::= { ripInfoIntfEntry 5 }
 
ripInfoIntfTrigUpdate OBJECT-TYPE
    SYNTAX INTEGER {
        enabled(1),
        disabled(2)
        }
    MAX-ACCESS read-only
    STATUS current
    DESCRIPTION
    "The status of triggered updates."
    ::= { ripInfoIntfEntry 6 }

ripInfoIntfMcastUpdate OBJECT-TYPE
    SYNTAX INTEGER {
        enabled(1),
        disabled(2)
        }
    MAX-ACCESS read-only
    STATUS current
    DESCRIPTION
    "The status of multicast updates."
    ::= { ripInfoIntfEntry 7 }

ripInfoIntfPoisonReverse OBJECT-TYPE
    SYNTAX  INTEGER {
        enabled(1),
        disabled(2)
        }
    MAX-ACCESS read-only
    STATUS current
    DESCRIPTION
    "The status of RIP poison reverse."
    ::= { ripInfoIntfEntry 8 }

ripInfoIntfSupply OBJECT-TYPE
    SYNTAX INTEGER {
        enabled(1),
        disabled(2)
        }
    MAX-ACCESS read-only
    STATUS current
    DESCRIPTION
        "The status of supplying route updates."
    ::= { ripInfoIntfEntry 9 }

ripInfoIntfMetric OBJECT-TYPE
    SYNTAX  INTEGER (1..15)
    MAX-ACCESS read-only
    STATUS current
    DESCRIPTION
        "RIP route metric for this interface."
    ::= { ripInfoIntfEntry 10 }

ripInfoIntfAuth OBJECT-TYPE
    SYNTAX INTEGER {
        none(1),
        password(2)
        }
    MAX-ACCESS read-only
    STATUS current
    DESCRIPTION
        "The type of Authentication used on this interface."
    ::= { ripInfoIntfEntry 11 }

ripInfoIntfKey OBJECT-TYPE
    SYNTAX  DisplayString (SIZE(0..16))
    MAX-ACCESS  read-only
    STATUS  current
    DESCRIPTION
        "RIP update authentication password."
    ::= { ripInfoIntfEntry 12 }

ripInfoIntfDefault OBJECT-TYPE
    SYNTAX  INTEGER {
        both(1),
        listen(2),
        supply(3),
        none(4)
        }
    MAX-ACCESS read-only
    STATUS current
    DESCRIPTION
    "Specifies what RIP does with default routes."
    ::= { ripInfoIntfEntry 13 }

rip2InfoRtrTable OBJECT-TYPE
    SYNTAX SEQUENCE OF RipInfoRtrEntry
    MAX-ACCESS not-accessible
    STATUS current
    DESCRIPTION
      "The routing information table of RIP."
    ::= { rip2Info 3 }

ripInfoRtrEntry OBJECT-TYPE
    SYNTAX RipInfoRtrEntry
    MAX-ACCESS not-accessible
    STATUS current
    DESCRIPTION
      "Information about RIP routes."
    INDEX { ripInfoRtrIndex }
    ::= { rip2InfoRtrTable 1 }

RipInfoRtrEntry ::= SEQUENCE {
    ripInfoRtrIndex          Integer32,
    ripInfoRtrDestIp         IpAddress,
    ripInfoRtrMask           IpAddress,
    ripInfoRtrGateway        IpAddress,
    ripInfoRtrMetric         Integer32
    }

ripInfoRtrIndex OBJECT-TYPE
    SYNTAX Integer32
    MAX-ACCESS read-only
    STATUS current
    DESCRIPTION
        "The index number of RIP route."
    ::= { ripInfoRtrEntry 1 }

ripInfoRtrDestIp OBJECT-TYPE
    SYNTAX  IpAddress
    MAX-ACCESS read-only
    STATUS current
    DESCRIPTION
        "The destination ip address of this route."
    ::= { ripInfoRtrEntry 2 }

ripInfoRtrMask OBJECT-TYPE
    SYNTAX  IpAddress
    MAX-ACCESS read-only
    STATUS current
    DESCRIPTION
        "The destination ip mask of this route."
    ::= { ripInfoRtrEntry 3 }

ripInfoRtrGateway OBJECT-TYPE
    SYNTAX  IpAddress
    MAX-ACCESS read-only
    STATUS current
    DESCRIPTION
        "The next-hop router address for this route."
    ::= { ripInfoRtrEntry 4 }


ripInfoRtrMetric OBJECT-TYPE
    SYNTAX  Integer32
    MAX-ACCESS read-only
    STATUS current
    DESCRIPTION
        "The metric for this route."
    ::= { ripInfoRtrEntry 10 }


-- L3 BGP Info

bgpInfoPeerTable OBJECT-TYPE
    SYNTAX SEQUENCE OF BgpInfoPeerEntry
    MAX-ACCESS not-accessible
    STATUS current
    DESCRIPTION
      "The table of BGP peer in the current configuration block."
    ::= { bgpInfo 1 }

bgpInfoPeerEntry OBJECT-TYPE
    SYNTAX BgpInfoPeerEntry
    MAX-ACCESS not-accessible
    STATUS current
    DESCRIPTION
      "Information about a BGP peer."
    INDEX { bgpInfoPeerIndex }
    ::= { bgpInfoPeerTable 1 }

BgpInfoPeerEntry ::= SEQUENCE {
    bgpInfoPeerIndex               Integer32,
    bgpInfoPeerRemoteAddr          IpAddress,
    bgpInfoPeerVersion             Integer32,
    bgpInfoPeerTtl                 Integer32,
    bgpInfoPeerRemoteAs            Integer32,
    bgpInfoPeerRouterId            IpAddress,
    bgpInfoPeerState               INTEGER,
    bgpInfoPeerLastState           INTEGER,
    bgpInfoTotalReceivedPackets    Integer32,
    bgpInfoTotalSentPackets        Integer32,
    bgpInfoReceivedUpdates         Integer32,
    bgpInfoSentUpdates             Integer32,
    bgpInfoKeepalive               Integer32,
    bgpInfoHoldtime                Integer32,
    bgpInfoMinAdvTime              Integer32,
    bgpInfoLastErrorCode           Integer32,
    bgpInfoLastErrorSubCode        Integer32,
    bgpInfoEstTransitions          Integer32
   }

bgpInfoPeerIndex OBJECT-TYPE
    SYNTAX Integer32
    MAX-ACCESS read-only
    STATUS current
    DESCRIPTION
        "The BGP peer number for which the BGP peer table is related."
    ::= { bgpInfoPeerEntry 1 }

bgpInfoPeerRemoteAddr OBJECT-TYPE
    SYNTAX IpAddress
    MAX-ACCESS read-only
    STATUS current
    DESCRIPTION
        "The remote IP address of the BGP peer."
    ::= { bgpInfoPeerEntry 2 }

bgpInfoPeerVersion OBJECT-TYPE
    SYNTAX Integer32
    MAX-ACCESS read-only
    STATUS current
    DESCRIPTION
        "The version negotiated by the BGP peer."
    ::= { bgpInfoPeerEntry 3 }

bgpInfoPeerTtl OBJECT-TYPE
    SYNTAX Integer32
    MAX-ACCESS read-only
    STATUS current
    DESCRIPTION
        "The time-to-live value of the BGP peer IP datagram."
    ::= { bgpInfoPeerEntry 4 }

bgpInfoPeerRemoteAs OBJECT-TYPE
    SYNTAX Integer32
    MAX-ACCESS read-only
    STATUS current
    DESCRIPTION
        "The remote IP address of the BGP peer."
    ::= { bgpInfoPeerEntry 5 }

bgpInfoPeerRouterId OBJECT-TYPE
    SYNTAX IpAddress
    MAX-ACCESS read-only
    STATUS current
    DESCRIPTION
        "The router IP address."
    ::= { bgpInfoPeerEntry 6 }

bgpInfoPeerState OBJECT-TYPE
    SYNTAX INTEGER {
        idle(1),
        connect(2),
        active(3),
        openSent(4),
        openConfirm(5),
        established(6)
        }
    MAX-ACCESS read-only
    STATUS current
    DESCRIPTION
        "The BGP status."
    ::= { bgpInfoPeerEntry 7 }

bgpInfoPeerLastState OBJECT-TYPE
    SYNTAX INTEGER {
        idle(1),
        connect(2),
        active(3),
        openSent(4),
        openConfirm(5),
        established(6)
        }
    MAX-ACCESS read-only
    STATUS current
    DESCRIPTION
        "The BGP old status."
    ::= { bgpInfoPeerEntry 8 }

bgpInfoTotalReceivedPackets OBJECT-TYPE
    SYNTAX Integer32
    MAX-ACCESS read-only
    STATUS current
    DESCRIPTION
        "The total number of received packets."
    ::= { bgpInfoPeerEntry 9 }

bgpInfoTotalSentPackets OBJECT-TYPE
    SYNTAX Integer32
    MAX-ACCESS read-only
    STATUS current
    DESCRIPTION
        "The total number of sent packets."
    ::= { bgpInfoPeerEntry 10 }

bgpInfoReceivedUpdates OBJECT-TYPE
    SYNTAX Integer32
    MAX-ACCESS read-only
    STATUS current
    DESCRIPTION
        "The number of received updates."
    ::= { bgpInfoPeerEntry 11 }

bgpInfoSentUpdates OBJECT-TYPE
    SYNTAX Integer32
    MAX-ACCESS read-only
    STATUS current
    DESCRIPTION
        "The number of sent updates."
    ::= { bgpInfoPeerEntry 12 }

bgpInfoKeepalive OBJECT-TYPE
    SYNTAX Integer32
    MAX-ACCESS read-only
    STATUS current
    DESCRIPTION
        "The keep alive time."
    ::= { bgpInfoPeerEntry 13 }

bgpInfoHoldtime OBJECT-TYPE
    SYNTAX Integer32
    MAX-ACCESS read-only
    STATUS current
    DESCRIPTION
        "The hold time."
    ::= { bgpInfoPeerEntry 14 }

bgpInfoMinAdvTime OBJECT-TYPE
    SYNTAX Integer32
    MAX-ACCESS read-only
    STATUS current
    DESCRIPTION
        "The MinAdvTime."
    ::= { bgpInfoPeerEntry 15 }

bgpInfoLastErrorCode OBJECT-TYPE
    SYNTAX Integer32
    MAX-ACCESS read-only
    STATUS current
    DESCRIPTION
        "The last error code."
    ::= { bgpInfoPeerEntry 16 }

bgpInfoLastErrorSubCode OBJECT-TYPE
    SYNTAX Integer32
    MAX-ACCESS read-only
    STATUS current
    DESCRIPTION
        "The last error subcode."
    ::= { bgpInfoPeerEntry 17 }

bgpInfoEstTransitions OBJECT-TYPE
    SYNTAX Integer32
    MAX-ACCESS read-only
    STATUS current
    DESCRIPTION
        "The  established state transitions."
    ::= { bgpInfoPeerEntry 18 }

bgpInfoSummaryTable OBJECT-TYPE
    SYNTAX SEQUENCE OF BgpInfoSummaryEntry
    MAX-ACCESS not-accessible
    STATUS current
    DESCRIPTION
      "The table of BGP Peer Information."
    ::= { bgpInfo 2 }

bgpInfoSummaryEntry OBJECT-TYPE
    SYNTAX BgpInfoSummaryEntry
    MAX-ACCESS not-accessible
    STATUS current
    DESCRIPTION
      "Information about a BGP Peer."
    INDEX { bgpInfoSummaryIndex }
    ::= { bgpInfoSummaryTable 1 }

BgpInfoSummaryEntry ::= SEQUENCE {
    bgpInfoSummaryIndex                  Integer32,
    bgpInfoSummaryRemoteAddr             IpAddress,
    bgpInfoSummaryVersion                Integer32,
    bgpInfoSummaryRemoteAs               Integer32,
    bgpInfoSummaryState                  INTEGER,
    bgpInfoSummaryTotalReceivedPackets   Integer32,
    bgpInfoSummaryTotalSentPackets       Integer32
    }

bgpInfoSummaryIndex OBJECT-TYPE
    SYNTAX Integer32
    MAX-ACCESS read-only
    STATUS current
    DESCRIPTION
        "The BGP Peer number for which the BGP Peer table is related."
    ::= { bgpInfoSummaryEntry 1 }

bgpInfoSummaryRemoteAddr OBJECT-TYPE
    SYNTAX IpAddress
    MAX-ACCESS read-only
    STATUS current
    DESCRIPTION
        "The remote IP address of the BGP Peer."
    ::= { bgpInfoSummaryEntry 2 }

bgpInfoSummaryVersion OBJECT-TYPE
    SYNTAX Integer32
    MAX-ACCESS read-only
    STATUS current
    DESCRIPTION
        "The version negotiated by the BGP Peer."
    ::= { bgpInfoSummaryEntry 3 }

bgpInfoSummaryRemoteAs OBJECT-TYPE
    SYNTAX Integer32
    MAX-ACCESS read-only
    STATUS current
    DESCRIPTION
        "The Remote AS."
    ::= { bgpInfoSummaryEntry 4 }

bgpInfoSummaryState OBJECT-TYPE
    SYNTAX INTEGER {
        idle(1),
        connect(2),
        active(3),
        openSent(4),
        openConfirm(5),
        established(6)
        }
    MAX-ACCESS read-only
    STATUS current
    DESCRIPTION
        "The BGP status."
    ::= { bgpInfoSummaryEntry 5 }

bgpInfoSummaryTotalReceivedPackets OBJECT-TYPE
    SYNTAX Integer32
    MAX-ACCESS read-only
    STATUS current
    DESCRIPTION
        "The total number of received packets."
    ::= { bgpInfoSummaryEntry 6 }

bgpInfoSummaryTotalSentPackets OBJECT-TYPE
    SYNTAX Integer32
    MAX-ACCESS read-only
    STATUS current
    DESCRIPTION
        "The total number of sent packets."
    ::= { bgpInfoSummaryEntry 7 }

bgpInfoRtrTable OBJECT-TYPE
    SYNTAX  SEQUENCE OF BgpInfoRtrTableEntry
    MAX-ACCESS  not-accessible
    STATUS  current
    DESCRIPTION
        "The table of BGP router run-time information"
    ::= { bgpInfo 3 }

bgpInfoRtrTableEntry OBJECT-TYPE
    SYNTAX  BgpInfoRtrTableEntry
    MAX-ACCESS  not-accessible
    STATUS  current
    DESCRIPTION
        "The run-time information about a BGP router"
    INDEX   { bgpInfoIndex }
    ::= { bgpInfoRtrTable 1 }

BgpInfoRtrTableEntry ::= SEQUENCE {
    bgpInfoIndex        IpAddress,
    bgpInfoNetwork      IpAddress,
    bgpInfoNextHop      DisplayString,
    bgpInfoMetr         DisplayString,
    bgpInfoLcPrf        DisplayString,
    bgpInfoWght         DisplayString,
    bgpInfoPath         DisplayString,
    bgpInfoOrigin       DisplayString,
    bgpInfoMask         DisplayString
    }

bgpInfoIndex OBJECT-TYPE
    SYNTAX  IpAddress
    MAX-ACCESS  read-only
    STATUS  current
    DESCRIPTION
        "The BGP router index which is the network address."
    ::= { bgpInfoRtrTableEntry 1 }

bgpInfoNetwork OBJECT-TYPE
    SYNTAX  IpAddress
    MAX-ACCESS  read-only
    STATUS  current
    DESCRIPTION
        "The BGP network address."
    ::= { bgpInfoRtrTableEntry 2 }

bgpInfoNextHop OBJECT-TYPE
    SYNTAX  DisplayString 
    MAX-ACCESS  read-only
    STATUS  current
    DESCRIPTION
        "The BGPs NextHop addresses from a network."
    ::= { bgpInfoRtrTableEntry 3 }

bgpInfoMetr OBJECT-TYPE
    SYNTAX  DisplayString 
    MAX-ACCESS  read-only
    STATUS  current
    DESCRIPTION
        "The BGPs metric from a network."
    ::= { bgpInfoRtrTableEntry 4 }

bgpInfoLcPrf OBJECT-TYPE
    SYNTAX  DisplayString
    MAX-ACCESS  read-only
    STATUS  current
    DESCRIPTION
        "The BGPs local preference from a network."
    ::= { bgpInfoRtrTableEntry 5 }

bgpInfoWght OBJECT-TYPE
    SYNTAX  DisplayString
    MAX-ACCESS  read-only
    STATUS  current
    DESCRIPTION
        "Total weight of AS paths from a network."
    ::= { bgpInfoRtrTableEntry 6 }

bgpInfoPath  OBJECT-TYPE
    SYNTAX  DisplayString
    MAX-ACCESS  read-only
    STATUS  current
    DESCRIPTION
        "The AS paths from a network."
    ::= { bgpInfoRtrTableEntry 7 }

bgpInfoOrigin OBJECT-TYPE
    SYNTAX  DisplayString
    MAX-ACCESS  read-only
    STATUS  current
    DESCRIPTION
        "The BGPs route origin from a network"
    ::= { bgpInfoRtrTableEntry 8 }

bgpInfoMask OBJECT-TYPE
    SYNTAX  DisplayString
    MAX-ACCESS  read-only
    STATUS  current
    DESCRIPTION
        "The BGP router subnet mask."
    ::= { bgpInfoRtrTableEntry 9 }



-- L3 Operational commands

vrrpOperVirtRtrTable OBJECT-TYPE
    SYNTAX  SEQUENCE OF VrrpOperVirtRtrEntry
    MAX-ACCESS  not-accessible
    STATUS  current
    DESCRIPTION
        "An entry in the table of virtual routers."
    ::= { vrrpOper 1 }

vrrpOperVirtRtrEntry OBJECT-TYPE
    SYNTAX  VrrpOperVirtRtrEntry
    MAX-ACCESS  not-accessible
    STATUS  current
    DESCRIPTION
        "A row in the vrrpOperVirtRtrTable "
    INDEX   { vrrpOperVirtRtrIndex }
    ::= { vrrpOperVirtRtrTable 1 }

VrrpOperVirtRtrEntry ::= SEQUENCE {
    vrrpOperVirtRtrIndex              Integer32,
    vrrpOperVirtRtrBackup             INTEGER
    }

vrrpOperVirtRtrIndex OBJECT-TYPE
    SYNTAX  Integer32
    MAX-ACCESS  read-only
    STATUS  current
    DESCRIPTION
        "The index for the  VRRP virtual router." 
    ::= { vrrpOperVirtRtrEntry 1 }

vrrpOperVirtRtrBackup OBJECT-TYPE
    SYNTAX  INTEGER {
    ok(1),
    backup(2)
    }
    MAX-ACCESS  read-write
    STATUS  current
    DESCRIPTION
        "When set to a value of 'backup(2)' it forces the specified
         master virtual router into backup mode.
         'ok(1)' is returned when the object is read."
    ::= { vrrpOperVirtRtrEntry 2 }

vrrpOperVirtRtrGroupBackup OBJECT-TYPE
    SYNTAX  INTEGER {
    ok(1),
    backup(2)
    }
    MAX-ACCESS  read-write
    STATUS  current
    DESCRIPTION
        "When set to a value of 'backup(2)' it forces the specified 
         master virtual router group into backup mode.
         'ok(1)' is returned when the object os read."
    ::= { vrrpOper 2 }



-- ----------------------------------------------------------------------------
-- { INSERT:  ipsec
-- ----------------------------------------------------------------------------

--  ipsecCfg       OBJECT IDENTIFIER ::= { layer3Configs 32 }
--  ipsecStats     OBJECT IDENTIFIER ::= { layer3Stats 24 }
--  ipsecInfo      OBJECT IDENTIFIER ::= { layer3Info 23 }

    IPsecKeyString ::= TEXTUAL-CONVENTION
        DISPLAY-HINT "1024a"
        STATUS       current
        DESCRIPTION            "Represents textual information taken from the NVT ASCII
                character set, as defined in pages 4, 10-11 of RFC 854.

                To summarize RFC 854, the NVT ASCII repertoire specifies:

                  - the use of character codes 0-127 (decimal)

                  - the graphics characters (32-126) are interpreted as
                    US ASCII

                  - NUL, LF, CR, BEL, BS, HT, VT and FF have the special
                    meanings specified in RFC 854

                  - the other 25 codes have no standard interpretation

                  - the sequence 'CR LF' means newline

                  - the sequence 'CR NUL' means carriage-return

                  - an 'LF' not preceded by a 'CR' means moving to the
                    same column on the next line.

                  - the sequence 'CR x' for any x other than LF or NUL is
                    illegal.  (Note that this also means that a string may
                    end with either 'CR LF' or 'CR NUL', but not with CR.)

                Any object defined using this syntax may not exceed 255
                characters in length.
    "
        SYNTAX       OCTET STRING (SIZE (0..1024))

-- IKEv2 Configuration
    ikeGroup        OBJECT IDENTIFIER ::= { ipsecCfg 1 }
    
    ikeCurCfgProposal     OBJECT IDENTIFIER ::= { ikeGroup 1 }
    
    ikeCurCfgPropCipher     OBJECT-TYPE
        SYNTAX INTEGER {
            des(1),
            triple-des(2),
            aes-cbc(3)
            }
        MAX-ACCESS read-only
        STATUS current
        DESCRIPTION
            "Current encription algorithm used by IKEv2"
        ::= { ikeCurCfgProposal 1 }

    ikeCurCfgPropAuth   OBJECT-TYPE
        SYNTAX INTEGER {
            sha1(1),
            md5(2)
            }
        MAX-ACCESS read-only
        STATUS current
        DESCRIPTION
            "Current authentication algorithm used by IKEv2"
        ::= { ikeCurCfgProposal 2 }  
 
    ikeCurCfgPropGroup OBJECT-TYPE
        SYNTAX INTEGER {
            dhGroup1(1),
            dhGroup2(2),
            dhGroup5(3),    
            dhGroup14(4),
            dhGroup24(5)       
            }
        MAX-ACCESS read-only
        STATUS current
        DESCRIPTION
            "Current Diffie-Hellman groups used by IKEv2"        
        ::= { ikeCurCfgProposal 3 }  
 
    ikeNewCfgProposal     OBJECT IDENTIFIER ::= { ikeGroup 2 }
    
    ikeNewCfgPropCipher     OBJECT-TYPE
        SYNTAX INTEGER {
            des(1),
            triple-des(2),
            aes-cbc(3)
            }
        MAX-ACCESS read-write
        STATUS current
        DESCRIPTION
            "New encription algorithm used by IKEv2"
        ::= { ikeNewCfgProposal 1 }

    ikeNewCfgPropAuth   OBJECT-TYPE
        SYNTAX INTEGER {
            sha1(1),
            md5(2)
            }
        MAX-ACCESS read-write
        STATUS current
        DESCRIPTION
            "New authentication algorithm used by IKEv2"
        ::= { ikeNewCfgProposal 2 }  
 
    ikeNewCfgPropGroup OBJECT-TYPE
        SYNTAX INTEGER {
            dhGroup1(1),
            dhGroup2(2),
            dhGroup5(3),    
            dhGroup14(4),
            dhGroup24(5)       
            }
        MAX-ACCESS read-write
        STATUS current
        DESCRIPTION
            "New Diffie-Hellman groups used by IKEv2"        
        ::= { ikeNewCfgProposal 3 }  
 
    ikeCurCfgPsk     OBJECT IDENTIFIER ::= { ikeGroup 3 }
    
    ikeCurCfgPskLocalKey OBJECT-TYPE
       SYNTAX     IPsecKeyString (SIZE (1..256))       
       MAX-ACCESS read-only
       STATUS     current
       DESCRIPTION
               "Current local pre-shared key."
       ::= { ikeCurCfgPsk 1 } 

    ikeCurCfgPskRemoteTable OBJECT-TYPE
        SYNTAX SEQUENCE OF IkeCurCfgPskRemoteEntry
        MAX-ACCESS not-accessible
        STATUS current
        DESCRIPTION
          "The (conceptual) table listing the remote pre-shared key by peer address used by IKEv2."
        ::= { ikeCurCfgPsk 2 }
        
    ikeCurCfgPskRemoteEntry OBJECT-TYPE
        SYNTAX     IkeCurCfgPskRemoteEntry
        MAX-ACCESS not-accessible
        STATUS     current
        DESCRIPTION
               "An entry (conceptual row) representing a remote pre-shared key for a peer address."
        INDEX      { ikeCurCfgPskRemoteIndex }
        ::= { ikeCurCfgPskRemoteTable 1 }

    IkeCurCfgPskRemoteEntry ::= SEQUENCE {
        ikeCurCfgPskRemoteIndex           Unsigned32,
        ikeCurCfgPskRemoteAddr            OCTET STRING,
        ikeCurCfgPskRemoteKey             IPsecKeyString,
        ikeCurCfgPskRemoteDelete          INTEGER
    }
    
    ikeCurCfgPskRemoteIndex OBJECT-TYPE
       SYNTAX     Unsigned32 (1..10)
       MAX-ACCESS read-only
       STATUS     current
       DESCRIPTION
               "The index of ikeCurCfgPskRemoteTable."
       ::= { ikeCurCfgPskRemoteEntry 1 }
       
    ikeCurCfgPskRemoteAddr OBJECT-TYPE
       SYNTAX     OCTET STRING (SIZE (16))
       MAX-ACCESS read-only
       STATUS     current
       DESCRIPTION
               "Current IPv6 address of peer."
       ::= { ikeCurCfgPskRemoteEntry 2 }

    ikeCurCfgPskRemoteKey OBJECT-TYPE
       SYNTAX     IPsecKeyString (SIZE (1..256))       
       MAX-ACCESS read-only
       STATUS     current
       DESCRIPTION
               "Current remote pre-shared key."
       ::= { ikeCurCfgPskRemoteEntry 3 }       

    ikeCurCfgPskRemoteDelete OBJECT-TYPE
       SYNTAX     INTEGER {
            other(1),
            delete(2)
            }
       MAX-ACCESS read-only
       STATUS     current
       DESCRIPTION
               "Set a value of delete(2) for this object will delete the entry,  A value of
                other(1) is always returned when this object is read."
       ::= { ikeCurCfgPskRemoteEntry 4 }   
       
    ikeNewCfgPsk     OBJECT IDENTIFIER ::= { ikeGroup 4 }

   
    ikeNewCfgPskLocalKey OBJECT-TYPE
       SYNTAX     IPsecKeyString (SIZE (1..256))  
       MAX-ACCESS read-write
       STATUS     current
       DESCRIPTION
               "New local pre-shared key."
       ::= { ikeNewCfgPsk 1 } 

    ikeNewCfgPskRemoteTable OBJECT-TYPE
        SYNTAX SEQUENCE OF IkeNewCfgPskRemoteEntry
        MAX-ACCESS not-accessible
        STATUS current
        DESCRIPTION
          "The (conceptual) table listing the remote pre-shared key by peer address used by IKEv2."
        ::= { ikeNewCfgPsk 2 }
        
    ikeNewCfgPskRemoteEntry OBJECT-TYPE
        SYNTAX     IkeNewCfgPskRemoteEntry
        MAX-ACCESS not-accessible
        STATUS     current
        DESCRIPTION
               "An entry (conceptual row) representing a remote pre-shared key for a peer address."
        INDEX      { ikeNewCfgPskRemoteIndex }
        ::= { ikeNewCfgPskRemoteTable 1 }

    IkeNewCfgPskRemoteEntry ::= SEQUENCE {
        ikeNewCfgPskRemoteIndex           Unsigned32,
        ikeNewCfgPskRemoteAddr            OCTET STRING,
        ikeNewCfgPskRemoteKey             IPsecKeyString,
        ikeNewCfgPskRemoteDelete          INTEGER
    }

    ikeNewCfgPskRemoteIndex OBJECT-TYPE
       SYNTAX     Unsigned32 (1..10)
       MAX-ACCESS read-only
       STATUS     current
       DESCRIPTION
               "The index of ikeNewCfgPskRemoteTable."
       ::= { ikeNewCfgPskRemoteEntry 1 }
       
    ikeNewCfgPskRemoteAddr OBJECT-TYPE
       SYNTAX     OCTET STRING (SIZE (16))
       MAX-ACCESS read-create
       STATUS     current
       DESCRIPTION
               "New IPv6 address of peer."
       ::= { ikeNewCfgPskRemoteEntry 2 }

    ikeNewCfgPskRemoteKey OBJECT-TYPE
       SYNTAX     IPsecKeyString (SIZE (1..256))   
       MAX-ACCESS read-create
       STATUS     current
       DESCRIPTION
               "New remote pre-shared key."
       ::= { ikeNewCfgPskRemoteEntry 3 }       

    ikeNewCfgPskRemoteDelete OBJECT-TYPE
       SYNTAX     INTEGER {
            other(1),
            delete(2)
            }
       MAX-ACCESS read-write
       STATUS     current
       DESCRIPTION
               "Set a value of delete(2) for this object will delete the entry,  A value of
                other(1) is always returned when this object is read."
       ::= { ikeNewCfgPskRemoteEntry 4 }  

    ikeCurCfgIdentity     OBJECT IDENTIFIER ::= { ikeGroup 5 }
    
     ikeCurCfgIdType OBJECT-TYPE
       SYNTAX     INTEGER {
            ipv6-addr(0),
            fqdn(1),
            email(2)
            }
       MAX-ACCESS read-only
       STATUS     current
       DESCRIPTION
               "Specifies the type of Identification being used."
       ::= { ikeCurCfgIdentity 1 }
       
     ikeCurCfgIdData OBJECT-TYPE
       SYNTAX     DisplayString (SIZE (1..100))
       MAX-ACCESS read-only
       STATUS     current
       DESCRIPTION
               "Value as indicated by the Identification Type. 
                It can be a fully-qualified domain name string 
                (example.com) or a fully-qualified email address 
                string (jsmith@example.com)."
       ::= { ikeCurCfgIdentity 2 }
              
    ikeNewCfgIdentity     OBJECT IDENTIFIER ::= { ikeGroup 6 }
    
     ikeNewCfgIdType OBJECT-TYPE
       SYNTAX     INTEGER {
            ipv6-addr(0),
            fqdn(1),
            email(2)
            }
       MAX-ACCESS read-write
       STATUS     current
       DESCRIPTION
               "Specifies the type of Identification being used."
       ::= { ikeNewCfgIdentity 1 }
       
     ikeNewCfgIdData OBJECT-TYPE
       SYNTAX     DisplayString (SIZE (1..100))
       MAX-ACCESS read-write
       STATUS     current
       DESCRIPTION
               "Value as indicated by the Identification Type. 
                It can be a fully-qualified domain name string 
                (example.com) or a fully-qualified email address 
                string (jsmith@example.com)."
       ::= { ikeNewCfgIdentity 2 }   
           
    ikeCurCfgTxTimeout OBJECT-TYPE
        SYNTAX Unsigned32 (1..15)
        MAX-ACCESS read-only
        STATUS current
        DESCRIPTION
            "The value of this object specify the IKEv2 PDU retransmission timeout in seconds."
        ::= { ikeGroup 7 }        
        
    ikeNewCfgTxTimeout OBJECT-TYPE
        SYNTAX Unsigned32 (1..15)
        MAX-ACCESS read-write
        STATUS current
        DESCRIPTION
            "The value of this object specify the new IKEv2 PDU retransmission timeout."
        ::= { ikeGroup 8 }       

    ikeCurCfgCookie OBJECT-TYPE
       SYNTAX     INTEGER {
            disable(1),
            enable(2)
            }
       MAX-ACCESS read-only
       STATUS     current
       DESCRIPTION
               "Globally enable/disable IKEv2 cookie notify."
       ::= { ikeGroup 9 }    

    ikeNewCfgCookie OBJECT-TYPE
       SYNTAX     INTEGER {
            disable(1),
            enable(2)
            }
       MAX-ACCESS read-write
       STATUS     current
       DESCRIPTION
               "Globally enable/disable IKEv2 cookie notify."
       ::= { ikeGroup 10 }
       
-- IPsec Configuration       
    ipsecGroup      OBJECT IDENTIFIER ::= { ipsecCfg 2 }

    ipsecCurCfgState OBJECT-TYPE
       SYNTAX     INTEGER {
            disable(1),
            enable(2)
            }
       MAX-ACCESS read-only
       STATUS     current
       DESCRIPTION
               "Globally enable/disable IPsec."
       ::= { ipsecGroup 1 }    

    ipsecNewCfgState OBJECT-TYPE
       SYNTAX     INTEGER {
            disable(1),
            enable(2)
            }
       MAX-ACCESS read-write
       STATUS     current
       DESCRIPTION
               "Globally enable/disable IPsec."
       ::= { ipsecGroup 2 }    
       
    ipsecCurCfgTxformTable OBJECT-TYPE
        SYNTAX SEQUENCE OF IpsecCurCfgTxformEntry
        MAX-ACCESS not-accessible
        STATUS current
        DESCRIPTION
          "The (conceptual) table listing all of the IPsec transform-set."
        ::= { ipsecGroup 3 }
    
    ipsecCurCfgTxformEntry OBJECT-TYPE
        SYNTAX     IpsecCurCfgTxformEntry
        MAX-ACCESS not-accessible
        STATUS     current
        DESCRIPTION
               "An entry (conceptual row) representing a IPsec transform-set."
        INDEX      { ipsecCurCfgTxformIndex }
        ::= { ipsecCurCfgTxformTable 1 }

    IpsecCurCfgTxformEntry ::= SEQUENCE {
        ipsecCurCfgTxformIndex          Unsigned32,
        ipsecCurCfgTxformAuth           INTEGER,
        ipsecCurCfgTxformCipher         INTEGER,
        ipsecCurCfgTxformIntegrity        INTEGER,
        ipsecCurCfgTxformMode           INTEGER,
        ipsecCurCfgTxformDelete          INTEGER
    }

    ipsecCurCfgTxformIndex OBJECT-TYPE
       SYNTAX     Unsigned32 (1..10)
       MAX-ACCESS read-only
       STATUS     current
       DESCRIPTION
               "The index of ipsecCurCfgTxformTable."
       ::= { ipsecCurCfgTxformEntry 1 }

    ipsecCurCfgTxformAuth OBJECT-TYPE
        SYNTAX INTEGER {
            none(0),
            ah-sha1(1),
            ah-md5(2)
            }
        MAX-ACCESS read-only
        STATUS current
        DESCRIPTION
            "The authentication algorithm of the IPsec transform-set"
        ::= { ipsecCurCfgTxformEntry 2 }
        
    ipsecCurCfgTxformCipher OBJECT-TYPE
        SYNTAX INTEGER {
            esp-null(0),
            esp-des(1),
            esp-3des(2),
            esp-aes-cbc(3),
            unspecified(4)
            }
        MAX-ACCESS read-only
        STATUS current
        DESCRIPTION
            "The encryption algorithm of the IPsec transform-set"
        ::= { ipsecCurCfgTxformEntry 3 }

    ipsecCurCfgTxformIntegrity OBJECT-TYPE
        SYNTAX INTEGER {
            none(0),
            esp-sha1(1),
            esp-md5(2)
            }
        MAX-ACCESS read-only
        STATUS current
        DESCRIPTION
            "The interity algorithm of the IPsec transform-set"
        ::= { ipsecCurCfgTxformEntry 4 }

    ipsecCurCfgTxformMode OBJECT-TYPE
        SYNTAX INTEGER {
            transport(1),
            tunnel(2)
            }
        MAX-ACCESS read-only
        STATUS current
        DESCRIPTION
            "The tunnel/transport mode of the IPsec transform-set"
        ::= { ipsecCurCfgTxformEntry 5 }

    ipsecCurCfgTxformDelete OBJECT-TYPE
       SYNTAX     INTEGER {
            other(1),
            delete(2)
            }
       MAX-ACCESS read-only
       STATUS     current
       DESCRIPTION
               "Set a value of delete(2) for this object will delete the entry,  A value of
                other(1) is always returned when this object is read."
       ::= { ipsecCurCfgTxformEntry 6 }    
        
    ipsecNewCfgTxformTable OBJECT-TYPE
        SYNTAX SEQUENCE OF IpsecNewCfgTxformEntry
        MAX-ACCESS not-accessible
        STATUS current
        DESCRIPTION
          "The (conceptual) table listing all of the new IPsec transform-set to be apply."
        ::= { ipsecGroup 4 }
    
    ipsecNewCfgTxformEntry OBJECT-TYPE
        SYNTAX     IpsecNewCfgTxformEntry
        MAX-ACCESS not-accessible
        STATUS     current
        DESCRIPTION
               "An entry (conceptual row) representing a IPsec transform-set."
        INDEX      { ipsecNewCfgTxformIndex }
        ::= { ipsecNewCfgTxformTable 1 }

    IpsecNewCfgTxformEntry ::= SEQUENCE {
        ipsecNewCfgTxformIndex          Unsigned32,
        ipsecNewCfgTxformAuth           INTEGER,
        ipsecNewCfgTxformCipher         INTEGER,
        ipsecNewCfgTxformIntegrity        INTEGER,
        ipsecNewCfgTxformMode           INTEGER,
        ipsecNewCfgTxformDelete          INTEGER
    }

    ipsecNewCfgTxformIndex OBJECT-TYPE
       SYNTAX     Unsigned32 (1..10)
       MAX-ACCESS read-only
       STATUS     current
       DESCRIPTION
               "The index of ipsecNewCfgTxformTable."
       ::= { ipsecNewCfgTxformEntry 1 }

    ipsecNewCfgTxformAuth OBJECT-TYPE
        SYNTAX INTEGER {
            none(0),
            ah-sha1(1),
            ah-md5(2)
            }
        MAX-ACCESS read-create
        STATUS current
        DESCRIPTION
            "The authentication algorithm of the IPsec transform-set"
        ::= { ipsecNewCfgTxformEntry 2 }
        
    ipsecNewCfgTxformCipher OBJECT-TYPE
        SYNTAX INTEGER {
            esp-null(0),
            esp-des(1),
            esp-3des(2),
            esp-aes-cbc(3),
            unspecified(4)
            }
        MAX-ACCESS read-create
        STATUS current
        DESCRIPTION
            "The encryption algorithm of the IPsec transform-set"
        ::= { ipsecNewCfgTxformEntry 3 }

    ipsecNewCfgTxformIntegrity OBJECT-TYPE
        SYNTAX INTEGER {
            none(0),
            esp-sha1(1),
            esp-md5(2)
            }
        MAX-ACCESS read-create
        STATUS current
        DESCRIPTION
            "The interity algorithm of the IPsec transform-set"
        ::= { ipsecNewCfgTxformEntry 4 }

    ipsecNewCfgTxformMode OBJECT-TYPE
        SYNTAX INTEGER {
            transport(1),
            tunnel(2)
            }
        MAX-ACCESS read-create
        STATUS current
        DESCRIPTION
            "The tunnel/transport mode of the IPsec transform-set"
        ::= { ipsecNewCfgTxformEntry 5 }
        
    ipsecNewCfgTxformDelete OBJECT-TYPE
       SYNTAX     INTEGER {
            other(1),
            delete(2)
            }
       MAX-ACCESS read-write
       STATUS     current
       DESCRIPTION
               "Set a value of delete(2) for this object will delete the entry,  A value of
                other(1) is always returned when this object is read."
       ::= { ipsecNewCfgTxformEntry 6 }    
       
    ipsecCurCfgSelectorTable OBJECT-TYPE
        SYNTAX SEQUENCE OF IpsecCurCfgSelectorEntry
        MAX-ACCESS not-accessible
        STATUS current
        DESCRIPTION
          "The (conceptual) table listing all of the IPsec selector."
        ::= { ipsecGroup 5 }
    
    ipsecCurCfgSelectorEntry OBJECT-TYPE
        SYNTAX     IpsecCurCfgSelectorEntry
        MAX-ACCESS not-accessible
        STATUS     current
        DESCRIPTION
               "An entry (conceptual row) representing a IPsec selector."
        INDEX      { ipsecCurCfgSelectorIndex }
        ::= { ipsecCurCfgSelectorTable 1 }

    IpsecCurCfgSelectorEntry ::= SEQUENCE {
        ipsecCurCfgSelectorIndex          Unsigned32,
        ipsecCurCfgSelectorAction         INTEGER,
        ipsecCurCfgSelectorProto          INTEGER,
        ipsecCurCfgSelectorIcmpType       Unsigned32,
        ipsecCurCfgSelectorDst            OCTET STRING,
        ipsecCurCfgSelectorDstPrefix      Unsigned32,
        ipsecCurCfgSelectorSrc            OCTET STRING,
        ipsecCurCfgSelectorDelete         INTEGER
    }

    ipsecCurCfgSelectorIndex OBJECT-TYPE
       SYNTAX     Unsigned32 (1..10)
       MAX-ACCESS read-only
       STATUS     current
       DESCRIPTION
               "The index of ipsecCurCfgSelectorTable."
       ::= { ipsecCurCfgSelectorEntry 1 }

    ipsecCurCfgSelectorAction OBJECT-TYPE
        SYNTAX INTEGER {
            unspecified(0),
            permit(1),
            deny(2)
            }
        MAX-ACCESS read-only
        STATUS current
        DESCRIPTION
            "The action of the IPsec selector"
        ::= { ipsecCurCfgSelectorEntry 2 }

    ipsecCurCfgSelectorProto OBJECT-TYPE
        SYNTAX INTEGER {
            unspecified(0),
            tcp(1),
            icmp(2),
            any(3)
            }
        MAX-ACCESS read-only
        STATUS current
        DESCRIPTION
            "The protocol of the IPsec selector"
        ::= { ipsecCurCfgSelectorEntry 3 }
        
    ipsecCurCfgSelectorIcmpType OBJECT-TYPE
        SYNTAX Unsigned32 (0..255)
        MAX-ACCESS read-only
        STATUS current
        DESCRIPTION
            "When the protocol of the IPsec selector is icmp(2), This object specify
             the ICMP type for the traffic selector. 0 = any."
        ::= { ipsecCurCfgSelectorEntry 4 }

    ipsecCurCfgSelectorDst OBJECT-TYPE
        SYNTAX     OCTET STRING (SIZE (16))
        MAX-ACCESS read-only
        STATUS current
        DESCRIPTION
            "The destination ip address of the IPsec selector"
        ::= { ipsecCurCfgSelectorEntry 6 }
        
    ipsecCurCfgSelectorDstPrefix OBJECT-TYPE
       SYNTAX     Unsigned32 (1..128)
       MAX-ACCESS read-only
       STATUS     current
       DESCRIPTION
               "The destination ipv6 address prefix length of the IPsec selector"
       ::= { ipsecCurCfgSelectorEntry 7 }
        
    ipsecCurCfgSelectorSrc OBJECT-TYPE
        SYNTAX     OCTET STRING (SIZE (16))
        MAX-ACCESS read-only
        STATUS current
        DESCRIPTION
            "The source ip address of the IPsec selector"
        ::= { ipsecCurCfgSelectorEntry 8 }
        
    ipsecCurCfgSelectorDelete OBJECT-TYPE
       SYNTAX     INTEGER {
            other(1),
            delete(2)
            }
       MAX-ACCESS read-only
       STATUS     current
       DESCRIPTION
               "Set a value of delete(2) for this object will delete the entry,  A value of
                other(1) is always returned when this object is read."
       ::= { ipsecCurCfgSelectorEntry 9 }    
        
    ipsecNewCfgSelectorTable OBJECT-TYPE
        SYNTAX SEQUENCE OF IpsecNewCfgSelectorEntry
        MAX-ACCESS not-accessible
        STATUS current
        DESCRIPTION
          "The (conceptual) table listing all of the IPsec selector."
        ::= { ipsecGroup 6 }
    
    ipsecNewCfgSelectorEntry OBJECT-TYPE
        SYNTAX     IpsecNewCfgSelectorEntry
        MAX-ACCESS not-accessible
        STATUS     current
        DESCRIPTION
               "An entry (conceptual row) representing a IPsec selector."
        INDEX      { ipsecNewCfgSelectorIndex }
        ::= { ipsecNewCfgSelectorTable 1 }

    IpsecNewCfgSelectorEntry ::= SEQUENCE {
        ipsecNewCfgSelectorIndex          Unsigned32,
        ipsecNewCfgSelectorAction         INTEGER,
        ipsecNewCfgSelectorProto          INTEGER,
        ipsecNewCfgSelectorIcmpType       Unsigned32,
        ipsecNewCfgSelectorDst            OCTET STRING,
        ipsecNewCfgSelectorDstPrefix      Unsigned32,
        ipsecNewCfgSelectorSrc            OCTET STRING,
        ipsecNewCfgSelectorDelete         INTEGER
    }

    ipsecNewCfgSelectorIndex OBJECT-TYPE
       SYNTAX     Unsigned32 (1..10)
       MAX-ACCESS read-only
       STATUS     current
       DESCRIPTION
               "The index of ipsecNewCfgSelectorTable."
       ::= { ipsecNewCfgSelectorEntry 1 }

    ipsecNewCfgSelectorAction OBJECT-TYPE
        SYNTAX INTEGER {
            unspecified(0),
            permit(1),
            deny(2)
            }
        MAX-ACCESS read-create
        STATUS current
        DESCRIPTION
            "The action of the IPsec selector"
        ::= { ipsecNewCfgSelectorEntry 2 }

    ipsecNewCfgSelectorProto OBJECT-TYPE
        SYNTAX INTEGER {
            unspecified(0),
            tcp(1),
            icmp(2),
            any(3)
            }
        MAX-ACCESS read-create
        STATUS current
        DESCRIPTION
            "The protocol of the IPsec selector"
        ::= { ipsecNewCfgSelectorEntry 3 }
        
    ipsecNewCfgSelectorIcmpType OBJECT-TYPE
        SYNTAX Unsigned32 (0..255)
        MAX-ACCESS read-create
        STATUS current
        DESCRIPTION
            "When the protocol of the IPsec selector is icmp(2), This object specify
             the ICMP type for the traffic selector. 0 = any."
        ::= { ipsecNewCfgSelectorEntry 4 }
        
    ipsecNewCfgSelectorDst OBJECT-TYPE
        SYNTAX     OCTET STRING (SIZE (16))
        MAX-ACCESS read-create
        STATUS current
        DESCRIPTION
            "The destination ipv6 address of the IPsec selector"
        ::= { ipsecNewCfgSelectorEntry 6 }

    ipsecNewCfgSelectorDstPrefix OBJECT-TYPE
       SYNTAX     Unsigned32 (1..128)
       MAX-ACCESS read-create
       STATUS     current
       DESCRIPTION
               "The destination ipv6 address prefix length of the IPsec selector"
       ::= { ipsecNewCfgSelectorEntry 7 }
       
    ipsecNewCfgSelectorSrc OBJECT-TYPE
        SYNTAX     OCTET STRING (SIZE (16))
        MAX-ACCESS read-create
        STATUS current
        DESCRIPTION
            "The source ip address of the IPsec selector"
        ::= { ipsecNewCfgSelectorEntry 8 }
        
    ipsecNewCfgSelectorDelete OBJECT-TYPE
       SYNTAX     INTEGER {
            other(1),
            delete(2)
            }
       MAX-ACCESS read-write
       STATUS     current
       DESCRIPTION
               "Set a value of delete(2) for this object will delete the entry,  A value of
                other(1) is always returned when this object is read."
       ::= { ipsecNewCfgSelectorEntry 9 }    
        
    ipsecCurCfgDynamicPolicyTable OBJECT-TYPE
        SYNTAX SEQUENCE OF IpsecCurCfgDynamicPolicyEntry
        MAX-ACCESS not-accessible
        STATUS current
        DESCRIPTION
          "The (conceptual) table listing all of the IPsec dynamic policies."
        ::= { ipsecGroup 7 }
    
    ipsecCurCfgDynamicPolicyEntry OBJECT-TYPE
        SYNTAX     IpsecCurCfgDynamicPolicyEntry
        MAX-ACCESS not-accessible
        STATUS     current
        DESCRIPTION
               "An entry (conceptual row) representing a IPsec dynamic policy."
        INDEX      { ipsecCurCfgDynamicPolicyIndex }
        ::= { ipsecCurCfgDynamicPolicyTable 1 }

    IpsecCurCfgDynamicPolicyEntry ::= SEQUENCE {
        ipsecCurCfgDynamicPolicyIndex       Unsigned32,
        ipsecCurCfgDynamicPolicyPeer        OCTET STRING,
        ipsecCurCfgDynamicPolicySelector    Unsigned32,
        ipsecCurCfgDynamicPolicyTxform      Unsigned32,
        ipsecCurCfgDynamicPolicyLifetime    Unsigned32,
        ipsecCurCfgDynamicPolicyPfs         INTEGER,
        ipsecCurCfgDynamicPolicyDelete      INTEGER
    }

    ipsecCurCfgDynamicPolicyIndex OBJECT-TYPE
       SYNTAX     Unsigned32 (1..10)
       MAX-ACCESS read-only
       STATUS     current
       DESCRIPTION
               "The index of ipsecCurCfgDynamicPolicyTable."
       ::= { ipsecCurCfgDynamicPolicyEntry 1 }

    ipsecCurCfgDynamicPolicyPeer OBJECT-TYPE
        SYNTAX    OCTET STRING (SIZE (16)) 
        MAX-ACCESS read-only
        STATUS current
        DESCRIPTION
            "The remote peer ip address."
        ::= { ipsecCurCfgDynamicPolicyEntry 2 }

    ipsecCurCfgDynamicPolicySelector OBJECT-TYPE
        SYNTAX    Unsigned32 (1..10)
        MAX-ACCESS read-only
        STATUS current
        DESCRIPTION
            "The traffic selector index for IPsec policy to refer an entry in ipsecCurCfgSelectorTable. 0 = unspecified."
        ::= { ipsecCurCfgDynamicPolicyEntry 3 }

    ipsecCurCfgDynamicPolicyTxform OBJECT-TYPE
        SYNTAX     Unsigned32 (1..10)
        MAX-ACCESS read-only
        STATUS current
        DESCRIPTION
            "The transform set index for IPSec policy to refer an entry in ipsecCurCfgTxformTable. 0 = unspecified."
        ::= { ipsecCurCfgDynamicPolicyEntry 4 }

    ipsecCurCfgDynamicPolicyLifetime OBJECT-TYPE
       SYNTAX     Unsigned32 (120..86400)
       MAX-ACCESS read-only
       STATUS     current
       DESCRIPTION
               "The SA lifetime for an IPsec policy."
       ::= { ipsecCurCfgDynamicPolicyEntry 5 }

    ipsecCurCfgDynamicPolicyPfs OBJECT-TYPE
       SYNTAX     INTEGER {
            disable(1),
            enable(2)
            }
       MAX-ACCESS read-only
       STATUS     current
       DESCRIPTION
               "Enable/disable perfect forward security."
       ::= { ipsecCurCfgDynamicPolicyEntry 6 }

    ipsecCurCfgDynamicPolicyDelete OBJECT-TYPE
       SYNTAX     INTEGER {
            other(1),
            delete(2)
            }
       MAX-ACCESS read-only
       STATUS     current
       DESCRIPTION
               "Set a value of delete(2) for this object will delete the entry,  A value of
                other(1) is always returned when this object is read."
       ::= { ipsecCurCfgDynamicPolicyEntry 7 }    
        
    ipsecNewCfgDynamicPolicyTable OBJECT-TYPE
        SYNTAX SEQUENCE OF IpsecNewCfgDynamicPolicyEntry
        MAX-ACCESS not-accessible
        STATUS current
        DESCRIPTION
          "The (conceptual) table listing all of the IPsec dynamic policies."
        ::= { ipsecGroup 8 }
    
    ipsecNewCfgDynamicPolicyEntry OBJECT-TYPE
        SYNTAX     IpsecNewCfgDynamicPolicyEntry
        MAX-ACCESS not-accessible
        STATUS     current
        DESCRIPTION
               "An entry (conceptual row) representing a IPsec dynamic policy."
        INDEX      { ipsecNewCfgDynamicPolicyIndex }
        ::= { ipsecNewCfgDynamicPolicyTable 1 }

    IpsecNewCfgDynamicPolicyEntry ::= SEQUENCE {
        ipsecNewCfgDynamicPolicyIndex       Unsigned32,
        ipsecNewCfgDynamicPolicyPeer        OCTET STRING,
        ipsecNewCfgDynamicPolicySelector    Unsigned32,
        ipsecNewCfgDynamicPolicyTxform      Unsigned32,
        ipsecNewCfgDynamicPolicyLifetime    Unsigned32,
        ipsecNewCfgDynamicPolicyPfs         INTEGER,
        ipsecNewCfgDynamicPolicyDelete       INTEGER
    }

    ipsecNewCfgDynamicPolicyIndex OBJECT-TYPE
       SYNTAX     Unsigned32 (1..10)
       MAX-ACCESS read-only
       STATUS     current
       DESCRIPTION
               "The index of ipsecNewCfgDynamicPolicyTable."
       ::= { ipsecNewCfgDynamicPolicyEntry 1 }

    ipsecNewCfgDynamicPolicyPeer OBJECT-TYPE
        SYNTAX    OCTET STRING (SIZE (16))
        MAX-ACCESS read-create
        STATUS current
        DESCRIPTION
            "The remote peer ip address."
        ::= { ipsecNewCfgDynamicPolicyEntry 2 }

    ipsecNewCfgDynamicPolicySelector OBJECT-TYPE
        SYNTAX     Unsigned32 (1..10)
        MAX-ACCESS read-create
        STATUS current
        DESCRIPTION
            "The traffic selector index for IPsec policy to refer an entry in ipsecNewCfgSelectorTable. 0 = unspecified."
        ::= { ipsecNewCfgDynamicPolicyEntry 3 }

    ipsecNewCfgDynamicPolicyTxform OBJECT-TYPE
        SYNTAX     Unsigned32 (1..10)
        MAX-ACCESS read-create
        STATUS current
        DESCRIPTION
            "The transform set index for IPSec policy to refer an entry in ipsecNewCfgTxformTable. 0 = unspecified."
        ::= { ipsecNewCfgDynamicPolicyEntry 4 }

    ipsecNewCfgDynamicPolicyLifetime OBJECT-TYPE
       SYNTAX     Unsigned32 (120..86400)
       MAX-ACCESS read-create
       STATUS     current
       DESCRIPTION
               "The SA lifetime for an IPsec policy."
       ::= { ipsecNewCfgDynamicPolicyEntry 5 }

    ipsecNewCfgDynamicPolicyPfs OBJECT-TYPE
       SYNTAX     INTEGER {
            disable(1),
            enable(2)
            }
       MAX-ACCESS read-create
       STATUS     current
       DESCRIPTION
               "Enable/disable perfect forward security."
       ::= { ipsecNewCfgDynamicPolicyEntry 6 }

    ipsecNewCfgDynamicPolicyDelete OBJECT-TYPE
       SYNTAX     INTEGER {
            other(1),
            delete(2)
            }
       MAX-ACCESS read-write
       STATUS     current
       DESCRIPTION
               "Set a value of delete(2) for this object will delete the entry,  A value of
                other(1) is always returned when this object is read."
       ::= { ipsecNewCfgDynamicPolicyEntry 7 }    
        
    ipsecCurCfgManualPolicyTable OBJECT-TYPE
        SYNTAX SEQUENCE OF IpsecCurCfgManualPolicyEntry
        MAX-ACCESS not-accessible
        STATUS current
        DESCRIPTION
          "The (conceptual) table listing all of the IPsec manual policies."
        ::= { ipsecGroup 9 }
    
    ipsecCurCfgManualPolicyEntry OBJECT-TYPE
        SYNTAX     IpsecCurCfgManualPolicyEntry
        MAX-ACCESS not-accessible
        STATUS     current
        DESCRIPTION
               "An entry (conceptual row) representing a IPsec manual policy."
        INDEX      { ipsecCurCfgManualPolicyIndex }
        ::= { ipsecCurCfgManualPolicyTable 1 }

    IpsecCurCfgManualPolicyEntry ::= SEQUENCE {
        ipsecCurCfgManualPolicyIndex            Unsigned32,
        ipsecCurCfgManualPolicyPeer             OCTET STRING,
        ipsecCurCfgManualPolicySelector         Unsigned32,
        ipsecCurCfgManualPolicyTxform           Unsigned32,
        ipsecCurCfgManualPolicyInAhKey          OCTET STRING,
        ipsecCurCfgManualPolicyInAhSpi          Unsigned32,
        ipsecCurCfgManualPolicyOutAhKey         OCTET STRING,
        ipsecCurCfgManualPolicyOutAhSpi         Unsigned32,      
        ipsecCurCfgManualPolicyInEspEncKey      OCTET STRING,
        ipsecCurCfgManualPolicyInEspAuthKey     OCTET STRING,
        ipsecCurCfgManualPolicyInEspSpi         Unsigned32,
        ipsecCurCfgManualPolicyOutEspEncKey     OCTET STRING,
        ipsecCurCfgManualPolicyOutEspAuthKey    OCTET STRING,
        ipsecCurCfgManualPolicyOutEspSpi        Unsigned32,    
        ipsecCurCfgManualPolicyDelete            INTEGER
    }

    ipsecCurCfgManualPolicyIndex OBJECT-TYPE
       SYNTAX     Unsigned32 (1..10)
       MAX-ACCESS read-only
       STATUS     current
       DESCRIPTION
               "The index of ipsecCurCfgManualPolicyTable."
       ::= { ipsecCurCfgManualPolicyEntry 1 }

    ipsecCurCfgManualPolicyPeer OBJECT-TYPE
        SYNTAX    OCTET STRING (SIZE (16))
        MAX-ACCESS read-only
        STATUS current
        DESCRIPTION
            "The remote peer ip address."
        ::= { ipsecCurCfgManualPolicyEntry 2 }

    ipsecCurCfgManualPolicySelector OBJECT-TYPE
        SYNTAX    Unsigned32 (1..10)
        MAX-ACCESS read-only
        STATUS current
        DESCRIPTION
            "The traffic selector index for IPsec policy to refer an entry in ipsecCurCfgSelectorTable"
        ::= { ipsecCurCfgManualPolicyEntry 3 }

    ipsecCurCfgManualPolicyTxform OBJECT-TYPE
        SYNTAX     Unsigned32 (1..10)
        MAX-ACCESS read-only
        STATUS current
        DESCRIPTION
            "The transform set index for IPSec policy to refer an entry in ipsecCurCfgTxformTable"
        ::= { ipsecCurCfgManualPolicyEntry 4 }

    ipsecCurCfgManualPolicyInAhKey OBJECT-TYPE
       SYNTAX     OCTET STRING (SIZE (0..128))
       MAX-ACCESS read-only
       STATUS     current
       DESCRIPTION
               "The AH inbound session key for an IPsec policy."
       ::= { ipsecCurCfgManualPolicyEntry 5 }

    ipsecCurCfgManualPolicyInAhSpi OBJECT-TYPE
       SYNTAX     Unsigned32 (0 | 256..4294967295)
       MAX-ACCESS read-only
       STATUS     current
       DESCRIPTION
               "The AH inbound SPI for an IPsec policy."
       ::= { ipsecCurCfgManualPolicyEntry 6 }

    ipsecCurCfgManualPolicyOutAhKey OBJECT-TYPE
       SYNTAX     OCTET STRING (SIZE (0..128))
       MAX-ACCESS read-only
       STATUS     current
       DESCRIPTION
               "The AH outbound session key for an IPsec policy."
       ::= { ipsecCurCfgManualPolicyEntry 7 }

    ipsecCurCfgManualPolicyOutAhSpi OBJECT-TYPE
       SYNTAX     Unsigned32 (0 | 256..4294967295)
       MAX-ACCESS read-only
       STATUS     current
       DESCRIPTION
               "The AH outbound SPI for an IPsec policy."
       ::= { ipsecCurCfgManualPolicyEntry 8 }

    ipsecCurCfgManualPolicyInEspEncKey OBJECT-TYPE
       SYNTAX     OCTET STRING (SIZE (0..128))
       MAX-ACCESS read-only
       STATUS     current
       DESCRIPTION
               "The Esp inbound cipher key for an IPsec policy."
       ::= { ipsecCurCfgManualPolicyEntry 9 }

    ipsecCurCfgManualPolicyInEspAuthKey OBJECT-TYPE
       SYNTAX     OCTET STRING (SIZE (0..128))
       MAX-ACCESS read-only
       STATUS     current
       DESCRIPTION
               "The Esp inbound authenticator key for an IPsec policy."
       ::= { ipsecCurCfgManualPolicyEntry 10 }
       
    ipsecCurCfgManualPolicyInEspSpi OBJECT-TYPE
       SYNTAX     Unsigned32 (0 | 256..4294967295)
       MAX-ACCESS read-only
       STATUS     current
       DESCRIPTION
               "The Esp inbound SPI for an IPsec policy."
       ::= { ipsecCurCfgManualPolicyEntry 11 }

    ipsecCurCfgManualPolicyOutEspEncKey OBJECT-TYPE
       SYNTAX     OCTET STRING (SIZE (0..128))
       MAX-ACCESS read-only
       STATUS     current
       DESCRIPTION
               "The Esp outbound cipher key for an IPsec policy."
       ::= { ipsecCurCfgManualPolicyEntry 12 }

    ipsecCurCfgManualPolicyOutEspAuthKey OBJECT-TYPE
       SYNTAX     OCTET STRING (SIZE (0..128))
       MAX-ACCESS read-only
       STATUS     current
       DESCRIPTION
               "The Esp outbound authenticator key for an IPsec policy."
       ::= { ipsecCurCfgManualPolicyEntry 13 }
       
    ipsecCurCfgManualPolicyOutEspSpi OBJECT-TYPE
       SYNTAX     Unsigned32 (0 | 256..4294967295)
       MAX-ACCESS read-only
       STATUS     current
       DESCRIPTION
               "The Esp outbound SPI for an IPsec policy."
       ::= { ipsecCurCfgManualPolicyEntry 14 }

    ipsecCurCfgManualPolicyDelete OBJECT-TYPE
       SYNTAX     INTEGER {
            other(1),
            delete(2)
            }
       MAX-ACCESS read-only
       STATUS     current
       DESCRIPTION
               "Set a value of delete(2) for this object will delete the entry,  A value of
                other(1) is always returned when this object is read."
       ::= { ipsecCurCfgManualPolicyEntry 15 }    
       
    ipsecNewCfgManualPolicyTable OBJECT-TYPE
        SYNTAX SEQUENCE OF IpsecNewCfgManualPolicyEntry
        MAX-ACCESS not-accessible
        STATUS current
        DESCRIPTION
          "The (conceptual) table listing all of the IPsec manual policies."
        ::= { ipsecGroup 10 }
    
    ipsecNewCfgManualPolicyEntry OBJECT-TYPE
        SYNTAX     IpsecNewCfgManualPolicyEntry
        MAX-ACCESS not-accessible
        STATUS     current
        DESCRIPTION
               "An entry (conceptual row) representing a IPsec manual policy."
        INDEX      { ipsecNewCfgManualPolicyIndex }
        ::= { ipsecNewCfgManualPolicyTable 1 }

    IpsecNewCfgManualPolicyEntry ::= SEQUENCE {
        ipsecNewCfgManualPolicyIndex            Unsigned32,
        ipsecNewCfgManualPolicyPeer             OCTET STRING,
        ipsecNewCfgManualPolicySelector         Unsigned32,
        ipsecNewCfgManualPolicyTxform           Unsigned32,
        ipsecNewCfgManualPolicyInAhKey          OCTET STRING,
        ipsecNewCfgManualPolicyInAhSpi          Unsigned32,
        ipsecNewCfgManualPolicyOutAhKey         OCTET STRING,
        ipsecNewCfgManualPolicyOutAhSpi         Unsigned32,      
        ipsecNewCfgManualPolicyInEspEncKey      OCTET STRING,
        ipsecNewCfgManualPolicyInEspAuthKey     OCTET STRING,
        ipsecNewCfgManualPolicyInEspSpi         Unsigned32,
        ipsecNewCfgManualPolicyOutEspEncKey     OCTET STRING,
        ipsecNewCfgManualPolicyOutEspAuthKey    OCTET STRING,
        ipsecNewCfgManualPolicyOutEspSpi        Unsigned32, 
        ipsecNewCfgManualPolicyDelete            INTEGER
    }

    ipsecNewCfgManualPolicyIndex OBJECT-TYPE
       SYNTAX     Unsigned32 (1..10)
       MAX-ACCESS read-only
       STATUS     current
       DESCRIPTION
               "The index of ipsecNewCfgManualPolicyTable."
       ::= { ipsecNewCfgManualPolicyEntry 1 }

    ipsecNewCfgManualPolicyPeer OBJECT-TYPE
        SYNTAX    OCTET STRING (SIZE (16))
        MAX-ACCESS read-create
        STATUS current
        DESCRIPTION
            "The remote peer ip address."
        ::= { ipsecNewCfgManualPolicyEntry 2 }

    ipsecNewCfgManualPolicySelector OBJECT-TYPE
        SYNTAX    Unsigned32 (1..10)
        MAX-ACCESS read-create
        STATUS current
        DESCRIPTION
            "The traffic selector index for IPsec policy to refer an entry in ipsecNewCfgSelectorTable"
        ::= { ipsecNewCfgManualPolicyEntry 3 }

    ipsecNewCfgManualPolicyTxform OBJECT-TYPE
        SYNTAX     Unsigned32 (1..10)
        MAX-ACCESS read-create
        STATUS current
        DESCRIPTION
            "The transform set index for IPSec policy to refer an entry in ipsecNewCfgTxformTable"
        ::= { ipsecNewCfgManualPolicyEntry 4 }

    ipsecNewCfgManualPolicyInAhKey OBJECT-TYPE
       SYNTAX     OCTET STRING (SIZE (0..128))
       MAX-ACCESS read-create
       STATUS     current
       DESCRIPTION
               "The AH inbound session key for an IPsec policy."
       ::= { ipsecNewCfgManualPolicyEntry 5 }

    ipsecNewCfgManualPolicyInAhSpi OBJECT-TYPE
       SYNTAX     Unsigned32 (0 | 256..4294967295)
       MAX-ACCESS read-create
       STATUS     current
       DESCRIPTION
               "The AH inbound SPI for an IPsec policy."
       ::= { ipsecNewCfgManualPolicyEntry 6 }

    ipsecNewCfgManualPolicyOutAhKey OBJECT-TYPE
       SYNTAX     OCTET STRING (SIZE (0..128))
       MAX-ACCESS read-create
       STATUS     current
       DESCRIPTION
               "The AH outbound session key for an IPsec policy."
       ::= { ipsecNewCfgManualPolicyEntry 7 }

    ipsecNewCfgManualPolicyOutAhSpi OBJECT-TYPE
       SYNTAX     Unsigned32 (0 | 256..4294967295)
       MAX-ACCESS read-create
       STATUS     current
       DESCRIPTION
               "The AH outbound SPI for an IPsec policy."
       ::= { ipsecNewCfgManualPolicyEntry 8 }

    ipsecNewCfgManualPolicyInEspEncKey OBJECT-TYPE
       SYNTAX     OCTET STRING (SIZE (0..128))
       MAX-ACCESS read-create
       STATUS     current
       DESCRIPTION
               "The Esp inbound cipher key for an IPsec policy."
       ::= { ipsecNewCfgManualPolicyEntry 9 }

    ipsecNewCfgManualPolicyInEspAuthKey OBJECT-TYPE
       SYNTAX     OCTET STRING (SIZE (0..128))
       MAX-ACCESS read-create
       STATUS     current
       DESCRIPTION
               "The Esp inbound authenticator key for an IPsec policy."
       ::= { ipsecNewCfgManualPolicyEntry 10 }
       
    ipsecNewCfgManualPolicyInEspSpi OBJECT-TYPE
       SYNTAX     Unsigned32 (0 | 256..4294967295)
       MAX-ACCESS read-create
       STATUS     current
       DESCRIPTION
               "The Esp inbound SPI for an IPsec policy."
       ::= { ipsecNewCfgManualPolicyEntry 11 }

    ipsecNewCfgManualPolicyOutEspEncKey OBJECT-TYPE
       SYNTAX     OCTET STRING (SIZE (0..128))
       MAX-ACCESS read-create
       STATUS     current
       DESCRIPTION
               "The Esp outbound cipher key for an IPsec policy."
       ::= { ipsecNewCfgManualPolicyEntry 12 }

    ipsecNewCfgManualPolicyOutEspAuthKey OBJECT-TYPE
       SYNTAX     OCTET STRING (SIZE (0..128))
       MAX-ACCESS read-create
       STATUS     current
       DESCRIPTION
               "The Esp outbound authenticator key for an IPsec policy."
       ::= { ipsecNewCfgManualPolicyEntry 13 }
       
    ipsecNewCfgManualPolicyOutEspSpi OBJECT-TYPE
        SYNTAX     Unsigned32 (0 | 256..4294967295)
        MAX-ACCESS read-create
        STATUS     current
        DESCRIPTION
               "The Esp outbound SPI for an IPsec policy."
        ::= { ipsecNewCfgManualPolicyEntry 14 }

    ipsecNewCfgManualPolicyDelete OBJECT-TYPE
       SYNTAX     INTEGER {
            other(1),
            delete(2)
            }
       MAX-ACCESS read-write
       STATUS     current
       DESCRIPTION
               "Set a value of delete(2) for this object will delete the entry,  A value of
                other(1) is always returned when this object is read."
       ::= { ipsecNewCfgManualPolicyEntry 15 }    

    ipsecCurCfgIfTable OBJECT-TYPE
        SYNTAX SEQUENCE OF IpsecCurCfgIfEntry
        MAX-ACCESS not-accessible
        STATUS current
        DESCRIPTION
            "The table of interface IPsec policy configuration."
        ::= { ipsecGroup 11 }

    ipsecCurCfgIfEntry OBJECT-TYPE
        SYNTAX IpsecCurCfgIfEntry
        MAX-ACCESS not-accessible
        STATUS current
        DESCRIPTION
            "The table of interface IPsec policy configuration."
        INDEX { ipsecCurCfgIfIndex }
        ::= { ipsecCurCfgIfTable 1 }

    IpsecCurCfgIfEntry ::= SEQUENCE {
        ipsecCurCfgIfIndex              Unsigned32,
        ipsecCurCfgIfDynamicPolicyBmap  OCTET STRING,
        ipsecCurCfgIfManualPolicyBmap   OCTET STRING,
        ipsecCurCfgIfDelete              INTEGER
        }

    ipsecCurCfgIfIndex OBJECT-TYPE
        SYNTAX  Unsigned32
        MAX-ACCESS read-only
        STATUS current
        DESCRIPTION
            "The identifier of a particular interface."
        ::= { ipsecCurCfgIfEntry 1 }
        
    ipsecCurCfgIfDynamicPolicyBmap OBJECT-TYPE
        SYNTAX  OCTET STRING (SIZE(0..4))
        MAX-ACCESS  read-only
        STATUS  current
        DESCRIPTION
            "The IPsec dynamic policies applied to the IP interface.  The 
             policies are presented in bitmap format. This string 
             displays policy number from 1 to 32.

             in receiving order:

                 OCTET 1  OCTET 2  .....
                 xxxxxxxx xxxxxxxx .....
                 ||    || |_ policy 9
                 ||    ||
                 ||    ||___ policy 8
                 ||    |____ policy 7
                 ||      .    .   .
                 ||_________ policy 2
                 |__________ policy 1

             where x : 1 - The represented policy applied to the 
                           IP interface.
                       0 - The represented policy not applied to 
                           the IP interface."
        ::= { ipsecCurCfgIfEntry 2 }
         
    ipsecCurCfgIfManualPolicyBmap OBJECT-TYPE
        SYNTAX  OCTET STRING (SIZE(0..4))
        MAX-ACCESS  read-only
        STATUS  current
        DESCRIPTION
            "The manual policies applied to the IP interface.  The 
             policies are presented in bitmap format. This string 
             displays policy number from 1 to 32.

             in receiving order:

                 OCTET 1  OCTET 2  .....
                 xxxxxxxx xxxxxxxx .....
                 ||    || |_ policy 9
                 ||    ||
                 ||    ||___ policy 8
                 ||    |____ policy 7
                 ||      .    .   .
                 ||_________ policy 2
                 |__________ policy 1

             where x : 1 - The represented policy applied to the 
                           IP interface.
                       0 - The represented policy not applied to 
                           the IP interface."
        ::= { ipsecCurCfgIfEntry 5 }        

    ipsecCurCfgIfDelete OBJECT-TYPE
       SYNTAX     INTEGER {
            other(1),
            delete(2)
            }
       MAX-ACCESS read-only
       STATUS     current
       DESCRIPTION
               "Set a value of delete(2) for this object will delete the entry,  A value of
                other(1) is always returned when this object is read."
       ::= { ipsecCurCfgIfEntry 8 }    

    ipsecNewCfgIfTable OBJECT-TYPE
        SYNTAX SEQUENCE OF IpsecNewCfgIfEntry
        MAX-ACCESS not-accessible
        STATUS current
        DESCRIPTION
            "The table of interface IPsec policy configuration."
        ::= { ipsecGroup 12 }

    ipsecNewCfgIfEntry OBJECT-TYPE
        SYNTAX IpsecNewCfgIfEntry
        MAX-ACCESS not-accessible
        STATUS current
        DESCRIPTION
            "The table of interface IPsec policy configuration."
        INDEX { ipsecNewCfgIfIndex }
        ::= { ipsecNewCfgIfTable 1 }

    IpsecNewCfgIfEntry ::= SEQUENCE {
        ipsecNewCfgIfIndex              Unsigned32,
        ipsecNewCfgIfDynamicPolicyBmap  OCTET STRING,
        ipsecNewCfgIfAddDynamicPolicy   Unsigned32,
        ipsecNewCfgIfDelDynamicPolicy   Unsigned32,
        ipsecNewCfgIfManualPolicyBmap   OCTET STRING,
        ipsecNewCfgIfAddManualPolicy    Unsigned32,
        ipsecNewCfgIfDelManualPolicy    Unsigned32,
        ipsecNewCfgIfDelete              INTEGER
        }

    ipsecNewCfgIfIndex OBJECT-TYPE
        SYNTAX  Unsigned32
        MAX-ACCESS read-only
        STATUS current
        DESCRIPTION
            "The identifier of a particular interface."
        ::= { ipsecNewCfgIfEntry 1 }
        
    ipsecNewCfgIfDynamicPolicyBmap OBJECT-TYPE
        SYNTAX  OCTET STRING (SIZE(0..4))
        MAX-ACCESS  read-only
        STATUS  current
        DESCRIPTION
            "The dynamic policies applied to the IP interface.  The 
             policies are presented in bitmap format. This string 
             displays policy number from 1 to 32.

             in receiving order:

                 OCTET 1  OCTET 2  .....
                 xxxxxxxx xxxxxxxx .....
                 ||    || |_ policy 9
                 ||    ||
                 ||    ||___ policy 8
                 ||    |____ policy 7
                 ||      .    .   .
                 ||_________ policy 2
                 |__________ policy 1

             where x : 1 - The represented policy applied to the 
                           IP interface.
                       0 - The represented policy not applied to 
                           the IP interface."
        ::= { ipsecNewCfgIfEntry 2 }

    ipsecNewCfgIfAddDynamicPolicy OBJECT-TYPE
        SYNTAX  Unsigned32 (1..10)
        MAX-ACCESS read-create
        STATUS current
        DESCRIPTION
            "Set the value to a IPsec dynamic policy ID when add the 
             policy to IP interface. A value of 0 is always 
             returned when this object is read."
        ::= { ipsecNewCfgIfEntry 3 }
 
    ipsecNewCfgIfDelDynamicPolicy OBJECT-TYPE
        SYNTAX  Unsigned32 (1..10)
        MAX-ACCESS read-create
        STATUS current
        DESCRIPTION
            "Set the value to a IPsec dynamic policy ID when delete
             the policy to IP interface. A value of 0 is always 
             returned when this object is read."
        ::= { ipsecNewCfgIfEntry 4 }
        
    ipsecNewCfgIfManualPolicyBmap OBJECT-TYPE
        SYNTAX  OCTET STRING (SIZE(0..4))
        MAX-ACCESS  read-only
        STATUS  current
        DESCRIPTION
            "The manual policies applied to the IP interface.  The 
             policies are presented in bitmap format. This string 
             displays policy number from 1 to 32.

             in receiving order:

                 OCTET 1  OCTET 2  .....
                 xxxxxxxx xxxxxxxx .....
                 ||    || |_ policy 9
                 ||    ||
                 ||    ||___ policy 8
                 ||    |____ policy 7
                 ||      .    .   .
                 ||_________ policy 2
                 |__________ policy 1

             where x : 1 - The represented policy applied to the 
                           IP interface.
                       0 - The represented policy not applied to 
                           the IP interface."
        ::= { ipsecNewCfgIfEntry 5 }

    ipsecNewCfgIfAddManualPolicy OBJECT-TYPE
        SYNTAX  Unsigned32 (1..10)
        MAX-ACCESS read-create
        STATUS current
        DESCRIPTION
            "Set the value to a IPsec manual policy ID when add the 
             policy to IP interface. A value of 0 is always 
             returned when this object is read."
        ::= { ipsecNewCfgIfEntry 6 }
 
    ipsecNewCfgIfDelManualPolicy OBJECT-TYPE
        SYNTAX  Unsigned32 (1..10)
        MAX-ACCESS read-create
        STATUS current
        DESCRIPTION
            "Set the value to a IPsec manual policy ID when delete
             the policy to IP interface. A value of 0 is always 
             returned when this object is read."
        ::= { ipsecNewCfgIfEntry 7 }
        
    ipsecNewCfgIfDelete OBJECT-TYPE
       SYNTAX     INTEGER {
            other(1),
            delete(2)
            }
       MAX-ACCESS read-write
       STATUS     current
       DESCRIPTION
               "Set a value of delete(2) for this object will delete the entry,  A value of
                other(1) is always returned when this object is read."
       ::= { ipsecNewCfgIfEntry 8 }    
        
       
-- IPsec Statistics
    ipsecSaStatsTable OBJECT-TYPE
        SYNTAX SEQUENCE OF IpsecSaStatsEntry
        MAX-ACCESS not-accessible
        STATUS current
        DESCRIPTION
          "The (conceptual) table listing all of the IPsec SA statistics."
        ::= { ipsecStats 1 }
    
    ipsecSaStatsEntry OBJECT-TYPE
        SYNTAX     IpsecSaStatsEntry
        MAX-ACCESS not-accessible
        STATUS     current
        DESCRIPTION
               "An entry (conceptual row) representing a IPsec SA statistics."
        INDEX      { ipsecSaStatsIndex }
        ::= { ipsecSaStatsTable 1 }

    IpsecSaStatsEntry ::= SEQUENCE {
        ipsecSaStatsIndex               Unsigned32,
        ipsecSaStatsSpi                 Unsigned32,
        ipsecSaStatsProto                INTEGER,
        ipsecSaStatsDstAddr             OCTET STRING,
        ipsecSaStatsUsageTime           Unsigned32,
        ipsecSaStatsBytes               Unsigned32,
        ipsecSaStatsPkts                Unsigned32
    }

    ipsecSaStatsIndex OBJECT-TYPE
        SYNTAX  Unsigned32
        MAX-ACCESS read-only
        STATUS current
        DESCRIPTION
            "The index of ipsecSaStatsEntry."
        ::= { ipsecSaStatsEntry 1 }

    ipsecSaStatsSpi OBJECT-TYPE
        SYNTAX  Unsigned32
        MAX-ACCESS read-only
        STATUS current
        DESCRIPTION
            "The SPI used by the SA."
        ::= { ipsecSaStatsEntry 2 }

    ipsecSaStatsProto OBJECT-TYPE
       SYNTAX     INTEGER {
            any(0),
            ah(1),
            esp(2)
            }
       MAX-ACCESS read-only
       STATUS     current
       DESCRIPTION
               "The proto(AH,ESP,or Both) used by the SA."
       ::= { ipsecSaStatsEntry 3 }    

    ipsecSaStatsDstAddr OBJECT-TYPE
       SYNTAX     OCTET STRING (SIZE (16))
       MAX-ACCESS read-only
       STATUS     current
       DESCRIPTION
               "The destination IP address for the SA."
       ::= { ipsecSaStatsEntry 4 }    

    ipsecSaStatsUsageTime OBJECT-TYPE
        SYNTAX  Unsigned32
        MAX-ACCESS read-only
        STATUS current
        DESCRIPTION
            "The time (in seconds) since the SA was first used."
        ::= { ipsecSaStatsEntry 5 }
 
    ipsecSaStatsBytes OBJECT-TYPE
        SYNTAX  Unsigned32
        MAX-ACCESS read-only
        STATUS current
        DESCRIPTION
            "The count of bytes for the SA."
        ::= { ipsecSaStatsEntry 6 }
 
    ipsecSaStatsPkts OBJECT-TYPE
        SYNTAX  Unsigned32
        MAX-ACCESS read-only
        STATUS current
        DESCRIPTION
            "The number of packets sent or received for the SA."
        ::= { ipsecSaStatsEntry 7 }
        
-- IPsec Information
    ipsecSaInfoTable OBJECT-TYPE
        SYNTAX SEQUENCE OF IpsecSaInfoEntry
        MAX-ACCESS not-accessible
        STATUS current
        DESCRIPTION
          "The (conceptual) table listing all of the IPsec SA information."
        ::= { ipsecInfo 1 }
    
    ipsecSaInfoEntry OBJECT-TYPE
        SYNTAX     IpsecSaInfoEntry
        MAX-ACCESS not-accessible
        STATUS     current
        DESCRIPTION
               "An entry (conceptual row) representing a IPsec SA information."
        INDEX      { ipsecSaInfoIndex }
        ::= { ipsecSaInfoTable 1 }

    IpsecSaInfoEntry ::= SEQUENCE {
        ipsecSaInfoIndex                Unsigned32,
        ipsecSaInfoSpi                  Unsigned32,
        ipsecSaInfoProto                INTEGER,
        ipsecSaInfoDstAddr              OCTET STRING,
        ipsecSaInfoSrcAddr              OCTET STRING,
        ipsecSaInfoFlags                Unsigned32,    
        ipsecSaInfoUlp                  Unsigned32,
        ipsecSaInfoMode                 INTEGER,
        ipsecSaInfoAuthAlg              INTEGER,
        ipsecSaInfoAuthKey              OCTET STRING,
        ipsecSaInfoEncrAlg              INTEGER,
        ipsecSaInfoEncrKey              OCTET STRING
    }

    ipsecSaInfoIndex OBJECT-TYPE
        SYNTAX  Unsigned32
        MAX-ACCESS read-only
        STATUS current
        DESCRIPTION
            "The index of ipsecSaInfoEntry."
        ::= { ipsecSaInfoEntry 1 }

    ipsecSaInfoSpi OBJECT-TYPE
        SYNTAX  Unsigned32
        MAX-ACCESS read-only
        STATUS current
        DESCRIPTION
            "The SPI used by the SA."
        ::= { ipsecSaInfoEntry 2 }

    ipsecSaInfoProto OBJECT-TYPE
       SYNTAX     INTEGER {
            any(0),
            ah(51),
            esp(50)
            }
       MAX-ACCESS read-only
       STATUS     current
       DESCRIPTION
               "The proto(AH,ESP,or Both) used by the SA."
       ::= { ipsecSaInfoEntry 3 }    

    ipsecSaInfoDstAddr OBJECT-TYPE
       SYNTAX     OCTET STRING (SIZE (16))
       MAX-ACCESS read-only
       STATUS     current
       DESCRIPTION
               "The destination IP address for the SA."
       ::= { ipsecSaInfoEntry 4 }    

    ipsecSaInfoSrcAddr OBJECT-TYPE
       SYNTAX     OCTET STRING (SIZE (16))
       MAX-ACCESS read-only
       STATUS     current
       DESCRIPTION
               "The source IP address for the SA."
       ::= { ipsecSaInfoEntry 5 }    

    ipsecSaInfoFlags OBJECT-TYPE
        SYNTAX  Unsigned32
        MAX-ACCESS read-only
        STATUS current
        DESCRIPTION
            "The direction, initiator and etc for an SA; see flag constants below:
                SA_FLAG_INUSE         0x0001
                SA_FLAG_DELETED       0x0002
                SA_FLAG_INBOUND       0x0004
                SA_FLAG_INITIATOR     0x0008
                SA_FLAG_MATURE        0x0010

                SA_FLAG_MIRRORED      0x0100
                SA_FLAG_IP6           0x0200
                SA_FLAG_IKE2          0x0400
                SA_FLAG_PFS           0x0800
            "
        ::= { ipsecSaInfoEntry 6 }
 
    ipsecSaInfoUlp OBJECT-TYPE
        SYNTAX  Unsigned32
        MAX-ACCESS read-only
        STATUS current
        DESCRIPTION
            "The upper layer protocol for an SA; 0=any; see protocol constants below:
                ICMP    1
                IPv4    4
                TCP     6
                UDP     17
                ESP     50
                AH      51
                IPv6    41
                ICMPv6  58
                "
        ::= { ipsecSaInfoEntry 7 } 

    ipsecSaInfoMode OBJECT-TYPE
        SYNTAX     INTEGER {
            any(0),
            transport(1),
            tunnel(2)
            }
        MAX-ACCESS read-only
        STATUS     current
        DESCRIPTION
               "The mode for the SA."
        ::= { ipsecSaInfoEntry 8 }    
        
     ipsecSaInfoAuthAlg OBJECT-TYPE
        SYNTAX     INTEGER {
            any(0),
            md5(1),
            sha1(2)
            }
        MAX-ACCESS read-only
        STATUS     current
        DESCRIPTION
               "The authentication algorithm for the SA."
        ::= { ipsecSaInfoEntry 9 }    

    ipsecSaInfoAuthKey OBJECT-TYPE
       SYNTAX     OCTET STRING (SIZE (20..64))
       MAX-ACCESS read-only
       STATUS     current
       DESCRIPTION
               "The authentication key for the SA."
       ::= { ipsecSaInfoEntry 10 }    
        
     ipsecSaInfoEncrAlg OBJECT-TYPE
        SYNTAX INTEGER {
            any(0),
            des(1),
            triple-des(2),
            blowfish(3),
            aes(4)
            }
        MAX-ACCESS read-only
        STATUS     current
        DESCRIPTION
               "The encryption algorithm for the SA."
       ::= { ipsecSaInfoEntry 11 }    
    
    ipsecSaInfoEncrKey OBJECT-TYPE
       SYNTAX     OCTET STRING (SIZE (20..64))
       MAX-ACCESS read-only
       STATUS     current
       DESCRIPTION
               "The encryption key for the SA."
       ::= { ipsecSaInfoEntry 12 }    
 
    ipsecSpdInfoTable OBJECT-TYPE
        SYNTAX SEQUENCE OF IpsecSpdInfoEntry
        MAX-ACCESS not-accessible
        STATUS current
        DESCRIPTION
          "The (conceptual) table listing all of the IPsec security policy information."
        ::= { ipsecInfo 2 }
    
    ipsecSpdInfoEntry OBJECT-TYPE
        SYNTAX     IpsecSpdInfoEntry
        MAX-ACCESS not-accessible
        STATUS     current
        DESCRIPTION
               "An entry (conceptual row) representing a IPsec security policy information."
        INDEX      { ipsecSpdInfoIndex }
        ::= { ipsecSpdInfoTable 1 }

    IpsecSpdInfoEntry ::= SEQUENCE {
        ipsecSpdInfoIndex               Unsigned32,
        ipsecSpdInfoFlags               Unsigned32,  
        ipsecSpdInfoULP                    Unsigned32,  
        ipsecSpdInfoAction                INTEGER,
        ipsecSpdInfoDstAddr             OCTET STRING,
        ipsecSpdInfoSrcAddr             OCTET STRING,
        ipsecSpdInfoMode                INTEGER,
        ipsecSpdInfoSaSize              Unsigned32
    }

    ipsecSpdInfoIndex OBJECT-TYPE
        SYNTAX  Unsigned32
        MAX-ACCESS read-only
        STATUS current
        DESCRIPTION
            "The index of ipsecSpdInfoEntry."
        ::= { ipsecSpdInfoEntry 1 }

    ipsecSpdInfoFlags OBJECT-TYPE
        SYNTAX  Unsigned32
        MAX-ACCESS read-only
        STATUS current
        DESCRIPTION
            "The direction, initiator and etc for an SA; see flag constants below:
                SP_FLAG_INUSE         0x00000001
                SP_FLAG_DELETED       0x00000002
                SP_FLAG_INBOUND       0x00000004
                SP_FLAG_MIRRORED      0x00000008

                SP_FLAG_PFP_LADDR     0x00000100
                SP_FLAG_PFP_RADDR     0x00000200
                SP_FLAG_PFP_LPORT     0x00000400
                SP_FLAG_PFP_RPORT     0x00000800
                SP_FLAG_PFP_ULP       0x00001000
                SP_MASK_PFP           0x00001f00

                SP_FLAG_DF            0x00002000
                SP_FLAG_DF_BIT        0x00004000
                SP_MASK_DF            0x00006000

                SP_FLAG_DSCP          0x00008000
                SP_FLAG_ECN           0x00010000

                SP_FLAG_IP6           0x00000010
                SP_FLAG_IP6_TUNNEL    0x00000020
                SP_FLAG_INIT          0x00000040
            "
        ::= { ipsecSpdInfoEntry 2 }

    ipsecSpdInfoULP OBJECT-TYPE
       SYNTAX   Unsigned32
       MAX-ACCESS read-only
       STATUS     current
       DESCRIPTION
               "The transport layer protocol for the SA. 0 = any. see protocol constants below:
                ICMP    1
                IPv4    4
                TCP     6
                UDP     17
                ESP     50
                AH      51
                IPv6    41
                ICMPv6  58 "
       ::= { ipsecSpdInfoEntry 3 }    

    ipsecSpdInfoAction OBJECT-TYPE
       SYNTAX     INTEGER {
            drop(1),
            apply(2),
            permit(3),
            bypass(4)
            }
       MAX-ACCESS read-only
       STATUS     current
       DESCRIPTION
               "The IPsec action for the SA."
       ::= { ipsecSpdInfoEntry 4 }    

    ipsecSpdInfoDstAddr OBJECT-TYPE
       SYNTAX     OCTET STRING (SIZE (16))
       MAX-ACCESS read-only
       STATUS     current
       DESCRIPTION
               "The destination IP address for the SA."
       ::= { ipsecSpdInfoEntry 5 }    

    ipsecSpdInfoSrcAddr OBJECT-TYPE
       SYNTAX     OCTET STRING (SIZE (16))
       MAX-ACCESS read-only
       STATUS     current
       DESCRIPTION
               "The source IP address for the SA."
       ::= { ipsecSpdInfoEntry 6 }    

    ipsecSpdInfoMode OBJECT-TYPE
        SYNTAX     INTEGER {
            any(0),
            transport(1),
            tunnel(2)
            }
        MAX-ACCESS read-only
        STATUS     current
        DESCRIPTION
               "The mode for the SA."
        ::= { ipsecSpdInfoEntry 7 }    
 
    ipsecSpdInfoSaSize OBJECT-TYPE
        SYNTAX  Unsigned32
        MAX-ACCESS read-only
        STATUS current
        DESCRIPTION
            "The SA bundle size of an Security policy."
        ::= { ipsecSpdInfoEntry 8 }

    ipsecSpdInfoSaTable OBJECT-TYPE
        SYNTAX SEQUENCE OF IpsecSpdInfoSaEntry
        MAX-ACCESS not-accessible
        STATUS current
        DESCRIPTION
          "The (conceptual) table listing all information of the SA nested in an IPsec security policy."
        ::= { ipsecInfo 3 }
    
    ipsecSpdInfoSaEntry OBJECT-TYPE
        SYNTAX     IpsecSpdInfoSaEntry
        MAX-ACCESS not-accessible
        STATUS     current
        DESCRIPTION
               "An entry (conceptual row) representing a SA information netsted in an IPsec security policy."
        INDEX      { ipsecSpdInfoIndex, ipsecSpdInfoSaIndex }
        ::= { ipsecSpdInfoSaTable 1 }

    IpsecSpdInfoSaEntry ::= SEQUENCE {
        ipsecSpdInfoSaIndex             Unsigned32,
        ipsecSpdInfoSaSecuProto         INTEGER,
        ipsecSpdInfoSaAuthAlg            INTEGER,
        ipsecSpdInfoSaEncrAlg            INTEGER,
        ipsecSpdInfoSaEncrKeyLen        Unsigned32
    }
   
    ipsecSpdInfoSaIndex OBJECT-TYPE
        SYNTAX  Unsigned32
        MAX-ACCESS read-only
        STATUS current
        DESCRIPTION
            "The index that enumerates the IPsec nested SAs ."
        ::= { ipsecSpdInfoSaEntry 1 }

    ipsecSpdInfoSaSecuProto OBJECT-TYPE
        SYNTAX     INTEGER {
            ah(0),
            esp(1),
            esp-auth(2),
            esp-null(3)
            }
        MAX-ACCESS read-only
        STATUS     current
        DESCRIPTION
               "The security protocol for the SA."
        ::= { ipsecSpdInfoSaEntry 2 }    

    ipsecSpdInfoSaAuthAlg OBJECT-TYPE
        SYNTAX     INTEGER {
            any(0),
            md5(1),
            sha1(2)
            }
        MAX-ACCESS read-only
        STATUS     current
        DESCRIPTION
               "The hash algorithm used by the SA."
        ::= { ipsecSpdInfoSaEntry 3 }    

    ipsecSpdInfoSaEncrAlg OBJECT-TYPE
        SYNTAX INTEGER {
            any(0),
            des(1),
            triple-des(2),
            blowfish(3),
            aes(4)
            }
        MAX-ACCESS read-only
        STATUS     current
        DESCRIPTION
               "The encryption algorithm used by the SA."
        ::= { ipsecSpdInfoSaEntry 4 }        
   
    ipsecSpdInfoSaEncrKeyLen OBJECT-TYPE
        SYNTAX  Unsigned32
        MAX-ACCESS read-only
        STATUS current
        DESCRIPTION
            "The encryption key length of an nested SA."
        ::= { ipsecSpdInfoSaEntry 5 }
        

-- ----------------------------------------------------------------------------
-- } INSERT:  layer3
-- ----------------------------------------------------------------------------

traps   		OBJECT IDENTIFIER ::= { g8264T-mgmt 7 }
-- ----------------------------------------------------------------------------
-- { INSERT:  traps
-- ----------------------------------------------------------------------------

-- SECTION 2:  Temporary Object Definitions Used In traps
 
swTrapDisplayString OBJECT-TYPE
    SYNTAX      DisplayString (SIZE(0..255))
    MAX-ACCESS  read-only
    STATUS      current
    DESCRIPTION
        "Temporary string object used to store information being sent
         in a Switch trap."
    ::= { traps 1000 }


-- SECTION 3:  Trap Definitions

-- Many of the following traps include sysName, sysLocation and sysContact. 
-- These variables are all defined in the rfc1213 MIB.  
--
-- sysName is the administratively-assigned name for this managed node. By  
-- convention, this is the node's fully-qualified domain name. 
--
-- sysLocation is the physical location of this node (e.g., 'telephone closet, 
-- 3rd floor'). 
--
-- sysContact is textual identification of the contact person for this managed 
-- node, together with information on how to contact this person. 

--
-- SNMP v3 traps should be defined here.
--

ibmSNMPv2Notifications  OBJECT IDENTIFIER
    ::= { traps 0 }

swPrimaryPowerSupplyFailureNotify NOTIFICATION-TYPE
    OBJECTS    {
                  swTrapDisplayString,
                  sysName,
                  sysLocation,
                  sysContact
               }
    STATUS     current
    DESCRIPTION
                "A swPrimaryPowerSupplyFailure trap signifies that the
                 primary power supply failed."
   ::= { ibmSNMPv2Notifications 1 }

swPrimaryPowerSupplyFixedNotify NOTIFICATION-TYPE
    OBJECTS    {
                  swTrapDisplayString,
                  sysName,
                  sysLocation,
                  sysContact
               }
    STATUS     current
    DESCRIPTION
        "A swPrimaryPowerSupplyFixed trap signifies that the
        primary power supply has been restored."
   ::= { ibmSNMPv2Notifications 97 }


--
-- SNMP v1 traps should be defined here.
--
swPrimaryPowerSupplyFailure TRAP-TYPE
        ENTERPRISE      traps
    VARIABLES  { swTrapDisplayString,
                 sysName, sysLocation, sysContact }
        DESCRIPTION
                "A swPrimaryPowerSupplyFailure trap signifies that the
                 primary power supply failed."
        --#SEVERITY CRITICAL
        ::= 1   -- 0x01

swDefGwUp TRAP-TYPE
    ENTERPRISE traps
    VARIABLES  { swTrapDisplayString,
                 ipCurCfgGwIndex,
                 ipCurCfgGwAddr,
                 sysName, sysLocation, sysContact }
    DESCRIPTION
        "A swDefGwUp trap signifies that the default gateway is alive. 
         ipCurCfgGwIndex is the index of the Gateway in ipCurCfgGwTable.
         The range for ipCurCfgGwIndex is from 1 to ipGatewayTableMax.
         ipCurCfgGwAddr is the IP address of the default gateway."
    ::= 2   -- 0x02

swDefGwDown TRAP-TYPE
    ENTERPRISE traps
    VARIABLES  { swTrapDisplayString,
                 ipCurCfgGwIndex,
                 ipCurCfgGwAddr,
                 sysName, sysLocation, sysContact }
    DESCRIPTION
        "A swDefGwDown trap signifies that the default gateway is down.
         ipCurCfgGwIndex is the index of the Gateway in ipCurCfgGwTable. 
         The range for ipCurCfgGwIndex is from 1 to ipGatewayTableMax.
         ipCurCfgGwAddr is the IP address of the default gateway."
    ::= 3   -- 0x03

swDefGwInService TRAP-TYPE
    ENTERPRISE traps
    VARIABLES  { swTrapDisplayString,
                 ipCurCfgGwIndex,
                 ipCurCfgGwAddr,
                 sysName, sysLocation, sysContact }
    DESCRIPTION
         "A swDefGwInService trap signifies that the default gateway is
          up and in service. 
          ipCurCfgGwIndex is the index of the Gateway in ipCurCfgGwTable. 
          The range for ipCurCfgGwIndex is from 1 to ipGatewayTableMax. 
          ipCurCfgGwAddr is the IP address of the default gateway."
    ::= 4   -- 0x04

swDefGwNotInService TRAP-TYPE
    ENTERPRISE traps
    VARIABLES  { swTrapDisplayString,
                 ipCurCfgGwIndex,
                 ipCurCfgGwAddr,
                 sysName, sysLocation, sysContact }
    DESCRIPTION
        "A swDefGwNotInService trap signifies that the default gateway 
         is alive but not in service. 
         ipCurCfgGwIndex is the index of the Gateway in ipCurCfgGwTable. 
         The range for ipCurCfgGwIndex is from 1 to ipGatewayTableMax. 
         ipCurCfgGwAddr is the IP address of the default gateway."
    ::= 5   -- 0x05



swVrrpNewMaster TRAP-TYPE
    ENTERPRISE traps
    VARIABLES  { swTrapDisplayString,
                 vrrpCurCfgVirtRtrIndx,
                 vrrpCurCfgVirtRtrAddr,
                 sysName, sysLocation, sysContact }
    DESCRIPTION    
        "The swVrrpNewMaster trap indicates that the sending agent has 
         transitioned to 'Master' state.
         vrrpCurCfgVirtRtrIndx is the VRRP virtual router table index 
         referenced in vrrpCurCfgVirtRtrTable. The range is from 1 to 
         vrrpVirtRtrTableMaxSize.
         vrrpCurCfgVirtRtrAddr is the VRRP virtual router IP address."
    ::= 16 -- 0x10
 
swVrrpNewBackup TRAP-TYPE
    ENTERPRISE traps
    VARIABLES  { swTrapDisplayString,
                 vrrpCurCfgVirtRtrIndx,
                 vrrpCurCfgVirtRtrAddr,
                 sysName, sysLocation, sysContact }
    DESCRIPTION    
        "The swVrrpNewBackup trap indicates that the sending agent has 
         transitioned to 'Backup' state.
         vrrpCurCfgVirtRtrIndx is the VRRP virtual router table index 
         referenced in vrrpCurCfgVirtRtrTable. The range is from 1 to 
         vrrpVirtRtrTableMaxSize.
         vrrpCurCfgVirtRtrAddr is the VRRP virtual router IP address."
    ::= 17 -- 0x11
 
swVrrpAuthFailure TRAP-TYPE
    ENTERPRISE traps
    VARIABLES  { swTrapDisplayString,
                 vrrpCurCfgIfIndx,
                 vrrpCurCfgIfPasswd,
                 sysName, sysLocation, sysContact }
    DESCRIPTION    
        "A swVrrpAuthFailure trap signifies that a packet has been received
         from a router whose authentication key or authentication type 
         conflicts with this router's authentication key or authentication 
         type. Implementation of this trap is optional.
         vrrpCurCfgIfIndx is the VRRP interface index. This is equivalent to 
         ifIndex in RFC 1213 mib. The range is from 1 to vrrpIfTableMaxSize.
         vrrpCurCfgIfPasswd is the password for authentication. It is a
         DisplayString of 0 to 7 characters."
    ::= 18 -- 0x12

swLoginFailure TRAP-TYPE
    ENTERPRISE traps
    VARIABLES  { swTrapDisplayString,
                 sysName, sysLocation, sysContact }
    DESCRIPTION
        "A swLoginFailure trap signifies that someone failed to enter a 
         valid username/password combination. 
         swTrapDisplayString specifies whether the login attempt was from 
         CONSOLE or TELNET. In case of TELNET login it also specifies the IP 
         address of the host from which the attempt was made."
    ::= 19 -- 0x13


swTempExceedThreshold TRAP-TYPE
    ENTERPRISE traps
    VARIABLES  { swTrapDisplayString,
                 sysName, sysLocation, sysContact }
    DESCRIPTION
        "A swTempExceedThreshold trap signifies that the
         switch temperature has exceeded maximum safety limits." 
    ::= 22   -- 0x16


swFanFailure TRAP-TYPE
    ENTERPRISE traps
    VARIABLES  { swTrapDisplayString,
                 sysName, sysLocation, sysContact }
    DESCRIPTION
	"A swFanFailure trap signifies that the
	fan failure has been detected."
    ::= 24   -- 0x18

swValidLogin TRAP-TYPE
    ENTERPRISE traps
    VARIABLES  { swTrapDisplayString,
                 sysName, sysLocation, sysContact }
    DESCRIPTION
        "A swValidLogin trap signifies that a user login has occured."
    ::= 25   -- 0x19

swApplyComplete TRAP-TYPE
    ENTERPRISE traps
    VARIABLES  { swTrapDisplayString,
                 sysName, sysLocation, sysContact }
    DESCRIPTION
        "A swApplyComplete signifies that new configuration
		 has been applied." 
    ::= 27 -- 0x1B

swSaveComplete TRAP-TYPE
    ENTERPRISE traps
    VARIABLES  { swTrapDisplayString,
                 sysName, sysLocation, sysContact }
    DESCRIPTION
        "A swApplyComplete signifies that new configuration
         has been saved." 
    ::= 28 -- 0x1C

swFwDownloadSucess TRAP-TYPE
    ENTERPRISE traps
    VARIABLES  { swTrapDisplayString,
                 sysName, sysLocation, sysContact }
    DESCRIPTION
        "A swFwDownloadSuccess signifies that firmware
         has been downloaded to [image1|image2|boot image]." 
    ::= 29 -- 0x1D

swFwDownloadFailure TRAP-TYPE
    ENTERPRISE traps
    VARIABLES  { swTrapDisplayString,
                 sysName, sysLocation, sysContact }
    DESCRIPTION
        "A swFwDownloadFailure signifies that firmware 
         downloaded failed to [image1|image2|boot image]." 
    ::= 30 -- 0x1E

swFanFailureFixed TRAP-TYPE
    ENTERPRISE traps
    VARIABLES  { swTrapDisplayString,
                 sysName, sysLocation, sysContact }
    DESCRIPTION
	"A swFanFailureFixed trap signifies that the
	fan failure has been fixed."
    ::= 33   -- 0x21

swStgNewRoot TRAP-TYPE
        ENTERPRISE      traps
        VARIABLES       { swTrapDisplayString, stgCurCfgIndex,
                          sysName, sysLocation, sysContact }
        DESCRIPTION
                "A swStgNewRoot trap signifies that the bridge has become the new root of the STG."
        --#SEVERITY INFORMATIONAL
        ::= 42 -- 0x2A

swCistNewRoot TRAP-TYPE
        ENTERPRISE      traps
        VARIABLES       { swTrapDisplayString,
                          sysName, sysLocation, sysContact }
        DESCRIPTION
                "A swCistNewRoot trap signifies that the bridge has become the new root of the CIST."
        --#SEVERITY INFORMATIONAL
        ::= 43 -- 0x2B

swStgTopologyChanged TRAP-TYPE
        ENTERPRISE      traps
        VARIABLES       { swTrapDisplayString, stgCurCfgIndex,
                          sysName, sysLocation, sysContact }
        DESCRIPTION
                "A swStgTopologyChanged trap signifies that there was a STG topology change."
        --#SEVERITY INFORMATIONAL
        ::= 44 -- 0x2C

swCistTopologyChanged TRAP-TYPE
        ENTERPRISE      traps
        VARIABLES       { swTrapDisplayString,
                          sysName, sysLocation, sysContact }
        DESCRIPTION
                "A swCistTopologyChanged trap signifies that there was a CIST topology change."
        --#SEVERITY INFORMATIONAL
        ::= 45 -- 0x2D

swHotlinksMasterUp   TRAP-TYPE
    ENTERPRISE   traps
    VARIABLES    { swTrapDisplayString,
                   sysName, sysLocation, sysContact }
    DESCRIPTION  "A swHotlinksMasterUp trap signifies that the Master interface is active."
    ::= 46   -- 0x2E

swHotlinksMasterDn   TRAP-TYPE
    ENTERPRISE   traps
    VARIABLES    { swTrapDisplayString,
                   sysName, sysLocation, sysContact }
    DESCRIPTION  "A swHotlinksMasterDn trap signifies that the Master interface is not active."
    ::= 47   -- 0x2F

swHotlinksBackupUp   TRAP-TYPE
    ENTERPRISE   traps
    VARIABLES    { swTrapDisplayString,
                   sysName, sysLocation, sysContact }
    DESCRIPTION  "A swHotlinksBackupUp trap signifies that the Backup interface is active."
    ::= 48   -- 0x30

swHotlinksBackupDn   TRAP-TYPE
    ENTERPRISE   traps
    VARIABLES    { swTrapDisplayString,
                   sysName, sysLocation, sysContact }
    DESCRIPTION  "A swHotlinksBackupDn trap signifies that the Backup interface is not active."
    ::= 49   -- 0x31

swHotlinksNone       TRAP-TYPE
    ENTERPRISE   traps
    VARIABLES    { swTrapDisplayString,
                   sysName, sysLocation, sysContact }
    DESCRIPTION  "A swHotlinksNone trap signifies that there are no active interfaces."
    ::= 50   -- 0x32

  sfpInserted       TRAP-TYPE
      ENTERPRISE      traps
      VARIABLES       { swTrapDisplayString, ifIndex,
                        sysName, sysLocation, sysContact }
      DESCRIPTION     "A sfpInserted trap signifies that a SFP is inserted."
      --#SEVERITY INFORMATIONAL
      ::= 51 -- 0x33

  sfpRemoved       TRAP-TYPE
      ENTERPRISE      traps
      VARIABLES       { swTrapDisplayString, ifIndex,
                        sysName, sysLocation, sysContact }
      DESCRIPTION     "A sfpRemoved trap signifies that a SFP is removed."
      --#SEVERITY INFORMATIONAL
      ::= 52 -- 0x34

swNTPSyncFailed     TRAP-TYPE
    ENTERPRISE   traps
    VARIABLES    { swTrapDisplayString,
                   sysName, sysLocation, sysContact }
    DESCRIPTION  "A swNTPSyncFailed trap signifies that sync with NTP server failed."
    ::= 61   -- 0x3D

swNTPUpdateClock     TRAP-TYPE
    ENTERPRISE   traps
    VARIABLES    { swTrapDisplayString,
                   sysName, sysLocation, sysContact }
    DESCRIPTION  "A swNTPUpdateClock trap signifies that update system clock with NTP server."
    ::= 62   -- 0x3E

swValidLogout TRAP-TYPE
    ENTERPRISE traps
    VARIABLES  { swTrapDisplayString,
                 sysName, sysLocation, sysContact }
    DESCRIPTION
        "A swValidLogout trap signifies that a user logout has occured."
    ::= 63   -- 0x3F

swECMPGatewayUp      TRAP-TYPE
    ENTERPRISE   traps
    VARIABLES    { swTrapDisplayString,
                   sysName, sysLocation, sysContact }
    DESCRIPTION     "A swECMPGatewayUp trap signifies that the ECMP gateway is up."
    --#SEVERITY INFORMATIONAL
    ::= 65 -- 0x41

swECMPGatewayDown      TRAP-TYPE
    ENTERPRISE   traps
    VARIABLES    { swTrapDisplayString,
                   sysName, sysLocation, sysContact }
    DESCRIPTION     "A swECMPGatewayDown trap signifies that the ECMP gateway is down."
    --#SEVERITY INFORMATIONAL
    ::= 66 -- 0x42

swTeamingCtrlUp   TRAP-TYPE
    ENTERPRISE   traps
    VARIABLES    { swTrapDisplayString,
                   sysName, sysLocation, sysContact }
   DESCRIPTION   "A swTeamingCtrlUp trap signifies that the teaming is up."
   --#SEVERITY INFORMATIONAL
   ::= 67 -- 0x43

swTeamingCtrlDown   TRAP-TYPE
   ENTERPRISE    traps
   VARIABLES     { swTrapDisplayString,
                   sysName, sysLocation, sysContact }
   DESCRIPTION   "A swTeamingCtrlDown trap signifies that the teaming control is down."
   --#SEVERITY INFORMATIONAL
   ::= 68 -- 0x44

swTeamingCtrlDownTearDownBlked   TRAP-TYPE
   ENTERPRISE    traps
   VARIABLES     { swTrapDisplayString,
                   sysName, sysLocation, sysContact }
   DESCRIPTION   "A swTeamingCtrlDownTearDownBlked trap signifies that the
                  teaming control is down but teardown is blocked."
   --#SEVERITY INFORMATIONAL
   ::= 69 -- 0x45

swTeamingCtrlError   TRAP-TYPE
   ENTERPRISE    traps
   VARIABLES     { swTrapDisplayString,
                   sysName, sysLocation, sysContact }
   DESCRIPTION   "A swTeamingCtrlError trap signifies error, action is undefined." 
   --#SEVERITY INFORMATIONAL
   ::= 70 -- 0x46


swTempReturnThreshold TRAP-TYPE
    ENTERPRISE   traps
    VARIABLES    { swTrapDisplayString,
                   sysName, sysLocation, sysContact }
    DESCRIPTION  "A swTempReturnThreshold trap signifies that the switch
                  temperature has returned below maximum safety limits."
    --#SEVERITY INFORMATIONAL
    ::= 31 -- 0x1F

    swLACPPortBlocked    TRAP-TYPE                                                                                                      
    ENTERPRISE   traps                                                                                                              
    VARIABLES    { swTrapDisplayString,                                                                                             
        sysName, sysLocation, sysContact }                                                                               
    DESCRIPTION  "A swLACPPortBlocked trap signifies that LACP is
        operationally down on a port, and traffic is blocked on the port."
        --#SEVERITY INFORMATIONAL                                                                                                       
        ::= 71 -- 0x47                                                                                                                  

    swLACPPortUnblocked    TRAP-TYPE                                                                                                    
    ENTERPRISE   traps                                                                                                              
    VARIABLES    { swTrapDisplayString,                                                                                             
        sysName, sysLocation,
        sysContact }                                                                               
    DESCRIPTION  "A swLACPPortUnblocked trap signifies that LACP is
        operationally up on a port, and traffic is no longer blocked on
        the port."                                                                                                                          
        --#SEVERITY INFORMATIONAL                                                                                                       
        ::= 72 -- 0x48                                                                                                                  


swVMGroupVMotion TRAP-TYPE
    ENTERPRISE   traps
    VARIABLES    { swTrapDisplayString,
                   sysName, sysLocation, sysContact }
    DESCRIPTION  "A altVMGroupVMotion trap signifies that a virtual machine has moved from a port to another."
    --#SEVERITY INFORMATIONAL
    ::= 77 -- 0x4D

swVMGroupVMOnline TRAP-TYPE
    ENTERPRISE   traps
    VARIABLES    { swTrapDisplayString,
                   sysName, sysLocation, sysContact }
    DESCRIPTION  "A altVMGroupVMOnline trap signifies that a advance provisioned virtual machine has came online."
    --#SEVERITY INFORMATIONAL
    ::= 78 -- 0x4E

swVMGroupVMVlanChange TRAP-TYPE
    ENTERPRISE   traps
    VARIABLES    { swTrapDisplayString,
                   sysName, sysLocation, sysContact }
    DESCRIPTION  "A altVMGroupVMVlanChange trap signifies that a virtual machine has entered into a vlan, or changed the vlan."
    --#SEVERITY INFORMATIONAL
    ::= 79 -- 0x4F



swPrimaryPowerSupplyFixed TRAP-TYPE
    ENTERPRISE      traps
    VARIABLES  { swTrapDisplayString,
                 sysName, sysLocation, sysContact }
    DESCRIPTION
	"A swPrimaryPowerSupplyFixed trap signifies that the
	primary power supply has been restored."
    --#SEVERITY CRITICAL
	::= 97   -- 0x61

swLFDPortErrdisabled    TRAP-TYPE
    ENTERPRISE   traps
    VARIABLES    { swTrapDisplayString,
                   sysName, sysLocation, sysContact }
    DESCRIPTION  "An swLFDPortErrdisabled trap signifies that a port is 
                  error-disabled due to excessive link flaps."
    --#SEVERITY INFORMATIONAL
    ::= 103 -- 0x67

swVlagInstanceUp      TRAP-TYPE
    ENTERPRISE   traps
    VARIABLES    { swTrapDisplayString,
                   sysName, sysLocation, sysContact }
    DESCRIPTION  "A swVlagInstanceUp trap signifies that vLAG instance is 
                  up identified in the trap message."        
    --#SEVERITY INFORMATIONAL
    ::= 106 -- 0x6A

swVlagInstanceRemoteUp      TRAP-TYPE
    ENTERPRISE   traps
    VARIABLES    { swTrapDisplayString,
                   sysName, sysLocation, sysContact }
    DESCRIPTION  "A swVlagInstanceRemoteUp trap signifies that vLAG is down 
                  but remote instance is Up."
    --#SEVERITY INFORMATIONAL
    ::= 107 -- 0x6B
 
swVlagInstanceLocalUp      TRAP-TYPE
    ENTERPRISE   traps
    VARIABLES    { swTrapDisplayString,
                   sysName, sysLocation, sysContact }
    DESCRIPTION  "A swVlagInstanceLocalUp trap signifies that vLAG is down 
                  but local instance is Up."
    --#SEVERITY INFORMATIONAL
    ::= 108 -- 0x6C
    
swVlagInstanceDown      TRAP-TYPE
    ENTERPRISE   traps
    VARIABLES    { swTrapDisplayString,
                   sysName, sysLocation, sysContact }
    DESCRIPTION  "A swVlagInstanceDown trap signifies that vLAG instance is 
                  down identified in the trap message."        
    --#SEVERITY INFORMATIONAL
    ::= 109 -- 0x6D

swVlagIslUp      TRAP-TYPE
    ENTERPRISE   traps
    VARIABLES    { swTrapDisplayString,
                   sysName, sysLocation, sysContact }
    DESCRIPTION  "A swVlagIslUp trap signifies that connection between vLAG 
                  switches is up."
    --#SEVERITY INFORMATIONAL
    ::= 110 -- 0x6E

swVlagIslDown      TRAP-TYPE
    ENTERPRISE   traps
    VARIABLES    { swTrapDisplayString,
                   sysName, sysLocation, sysContact }
    DESCRIPTION  "A swVlagInstanceDown trap signifies that connection between
                  vLAG switches is down."
    --#SEVERITY INFORMATIONAL
    ::= 111 -- 0x6F


swOflowConnectControllerFailure TRAP-TYPE
    ENTERPRISE      traps
    VARIABLES  { swTrapDisplayString,
	sysName, sysLocation, sysContact }
    DESCRIPTION
	"A swOflowConnectControllerFailure trap signifies that the
	connection to openflow controller is broken."
    --#SEVERITY CRITICAL
	::= 144   -- 0x90

swOflowConnectControllerSuccess TRAP-TYPE
    ENTERPRISE      traps
    VARIABLES  { swTrapDisplayString,
	sysName, sysLocation, sysContact }
    DESCRIPTION
	"A swOflowConnectControllerSuccess trap signifies that the
	connection to openflow controller is successful."
    --#SEVERITY INFORMATIONAL
	::= 145   -- 0x91

swOflowEmergencyState TRAP-TYPE
    ENTERPRISE      traps
    VARIABLES  { swTrapDisplayString,
	sysName, sysLocation, sysContact }
    DESCRIPTION
	"A swOflowEmergencyState trap signifies that the
	openflow switch moving to emergency state."
    --#SEVERITY CRITICAL
	::= 146   -- 0x92

swOflowNoEmergencyState TRAP-TYPE
    ENTERPRISE      traps
    VARIABLES  { swTrapDisplayString,
	sysName, sysLocation, sysContact }
    DESCRIPTION
	"A swOflowNoEmergencyState trap signifies that the
	openflow switch came out of emergency state."
    --#SEVERITY INFORMATIONAL
	::= 147   -- 0x93

swOflowSwitchOflowMode TRAP-TYPE
    ENTERPRISE      traps
    VARIABLES  { swTrapDisplayString,
	sysName, sysLocation, sysContact }
    DESCRIPTION
	"A swOflowSwitchOflowMode trap signifies that the
	device working in openflow switch mode."
    --#SEVERITY INFORMATIONAL
	::= 148   -- 0x94

swOflowSwitcNormalMode TRAP-TYPE
    ENTERPRISE      traps
    VARIABLES  { swTrapDisplayString,
	sysName, sysLocation, sysContact }
    DESCRIPTION
	"A swOflowSwitcNormalMode trap signifies that the
	device working in normal switch mode."
    --#SEVERITY INFORMATIONAL
	::= 149   -- 0x95

swOflowSwitcFlowtableClr TRAP-TYPE
    ENTERPRISE      traps
    VARIABLES  { swTrapDisplayString,
	sysName, sysLocation, sysContact }
    DESCRIPTION
	"A swOflowSwitcFlowtableClr trap signifies that the
	flow table entries being cleared from the device."
    --#SEVERITY INFORMATIONAL
	::= 150   -- 0x96

swOflowSwitcStatsClr TRAP-TYPE
    ENTERPRISE      traps
    VARIABLES  { swTrapDisplayString,
	sysName, sysLocation, sysContact }
    DESCRIPTION
	"A swOflowSwitcStatsClr trap signifies that the
	openflow statistics being cleared from the device."
    --#SEVERITY INFORMATIONAL
	::= 151   -- 0x97

swOflowFlowtableEntryUnavail TRAP-TYPE
    ENTERPRISE      traps
    VARIABLES  { swTrapDisplayString,
	sysName, sysLocation, sysContact }
    DESCRIPTION
	"A swOflowFlowtableMemoryUnavail trap signifies that the device unable to 
	add flow entry in openflow due to unavailability of system resources."
    --#SEVERITY INFORMATIONAL
	::= 152   -- 0x98

swOflowFlowtableLimit TRAP-TYPE
    ENTERPRISE      traps
    VARIABLES  { swTrapDisplayString,
	sysName, sysLocation, sysContact }
    DESCRIPTION
	"A swOflowFlowtableLimit trap signifies that the
	device reaches its configured flow limit."
    --#SEVERITY INFORMATIONAL
	::= 153   -- 0x99

swOflowPortDownController TRAP-TYPE
    ENTERPRISE      traps
    VARIABLES  { swTrapDisplayString,
	sysName, sysLocation, sysContact }
    DESCRIPTION
	"A swOflowPortDownController trap signifies that the port operationally 
	down by openflow controller."
    --#SEVERITY INFORMATIONAL
	::= 154   -- 0x9a

swOflowPortUpController TRAP-TYPE
    ENTERPRISE      traps
    VARIABLES  { swTrapDisplayString,
	sysName, sysLocation, sysContact }
    DESCRIPTION
	"A swOflowPortUpController trap signifies that the port operationally 
	up by openflow controller."
    --#SEVERITY INFORMATIONAL
	::= 155   -- 0x9b

swOflowVersionNegotiationError TRAP-TYPE
    ENTERPRISE      traps
    VARIABLES  { swTrapDisplayString,
	sysName, sysLocation, sysContact }
    DESCRIPTION
	"A swOflowVersionNegotiationError trap signifies that the device unable to 
	connect to controller either due to bad version, or negotiation/hello failure." 
    --#SEVERITY INFORMATIONAL
	::= 156   -- 0x9c

sw8021x TRAP-TYPE
    ENTERPRISE traps
    VARIABLES  { swTrapDisplayString,
    sysName, sysLocation, sysContact }
    DESCRIPTION
        "A sw8021x trap is sent when dot1x feature is enabled."
    ::= 158   -- 0x9F

swDefAdminDisable      TRAP-TYPE
    ENTERPRISE   traps
    VARIABLES    { swTrapDisplayString,
                   sysName, sysLocation, sysContact }
    DESCRIPTION  "A swDefAdminDisable trap signifies that default admin account has been disabled."
    ::= 162   -- 0xA2

swAcntStrngPswdNotMet   TRAP-TYPE
    ENTERPRISE   traps
    VARIABLES    { swTrapDisplayString,
                   sysName, sysLocation, sysContact }
    DESCRIPTION  "A swAcntStrngPswdNotMet trap signifies that configured password does not match strong password complexity."
    ::= 163   -- 0xA3

swAcntLocked     TRAP-TYPE
    ENTERPRISE   traps
    VARIABLES    { swTrapDisplayString,
                   sysName, sysLocation, sysContact }
    DESCRIPTION  "A swAcntLocked trap signifies that account has been locked."
    ::= 164   -- 0xA4

swAcntUnlocked     TRAP-TYPE
    ENTERPRISE   traps
    VARIABLES    { swTrapDisplayString,
                   sysName, sysLocation, sysContact }
    DESCRIPTION  "A swAcntUnlocked trap signifies that account has been unlocked."
    ::= 165   -- 0xA5




swARPtablefull      TRAP-TYPE
    ENTERPRISE   traps
    VARIABLES    { swTrapDisplayString,
                 sysName, sysLocation, sysContact }
    DESCRIPTION  "A swARPtablefull trap signifies that ARP table is full."
    ::= 184   -- 0xB8


-- ----------------------------------------------------------------------------
-- ----------------------------------------------------------------------------
-- } INSERT:  traps
-- ----------------------------------------------------------------------------
qos                     OBJECT IDENTIFIER ::= { g8264T-mgmt 8 }
-- ----------------------------------------------------------------------------
-- { INSERT:  qos
-- ----------------------------------------------------------------------------

qosConfig      OBJECT IDENTIFIER ::= { qos 1 }
--Only show these objects when we have it in the CLI
--qosStats       OBJECT IDENTIFIER ::= { qos 2 }
--qosInfo        OBJECT IDENTIFIER ::= { qos 3 }
--qosOper        OBJECT IDENTIFIER ::= { qos 4 }

qos8021p   OBJECT IDENTIFIER ::= { qosConfig 1 }
qosdscp   OBJECT IDENTIFIER ::= { qosConfig 2 }
qoswredecn   OBJECT IDENTIFIER ::= { qosConfig 3 }

-- QOS Configuration 

qosCurCfgPortPriorityTable OBJECT-TYPE
    SYNTAX SEQUENCE OF QoSCurCfgPortPriorityEntry
    MAX-ACCESS not-accessible
    STATUS current
    DESCRIPTION
        "The table of QOS Port Priority configuration."
    ::= { qos8021p  1 }

qosCurCfgPortPriorityEntry OBJECT-TYPE
    SYNTAX QoSCurCfgPortPriorityEntry
    MAX-ACCESS not-accessible
    STATUS current
    DESCRIPTION
        "Information about a particular QOS Port Priority configuration."
    INDEX { qosCurCfgPortIndex }
    ::= { qosCurCfgPortPriorityTable 1 }

QoSCurCfgPortPriorityEntry ::= SEQUENCE {
    qosCurCfgPortIndex      PortNumber,
    qosCurCfgPortPriority   INTEGER
    }

qosCurCfgPortIndex  OBJECT-TYPE
    SYNTAX  PortNumber
    MAX-ACCESS  read-only
    STATUS  current
    DESCRIPTION
        "Switch Port Number"
    ::= { qosCurCfgPortPriorityEntry 1 }

qosCurCfgPortPriority  OBJECT-TYPE
    SYNTAX  INTEGER  (0..7)
    MAX-ACCESS  read-only
    STATUS  current
    DESCRIPTION
        "Switch Port Priority Should be between 0 and 7"
    ::= { qosCurCfgPortPriorityEntry 2 }

qosNewCfgPortPriorityTable OBJECT-TYPE
    SYNTAX SEQUENCE OF QoSNewCfgPortPriorityEntry
    MAX-ACCESS not-accessible
    STATUS current
    DESCRIPTION
        "The table of QOS Port Priority configuration."
    ::= { qos8021p  2 }

qosNewCfgPortPriorityEntry OBJECT-TYPE
    SYNTAX QoSNewCfgPortPriorityEntry
    MAX-ACCESS not-accessible
    STATUS current
    DESCRIPTION
        "Information about a particular QOS Port Priority configuration."
    INDEX { qosNewCfgPortIndex }
    ::= { qosNewCfgPortPriorityTable 1 }

QoSNewCfgPortPriorityEntry ::= SEQUENCE {
    qosNewCfgPortIndex      PortNumber,
    qosNewCfgPortPriority   INTEGER
    }

qosNewCfgPortIndex  OBJECT-TYPE
    SYNTAX  PortNumber
    MAX-ACCESS  read-only
    STATUS  current
    DESCRIPTION
        "Switch Port Number"
    ::= { qosNewCfgPortPriorityEntry 1 }

qosNewCfgPortPriority  OBJECT-TYPE
    SYNTAX  INTEGER  (0..7)
    MAX-ACCESS  read-write
    STATUS  current
    DESCRIPTION
        "Switch Port Priority Should be between 0 and 7"
    ::= { qosNewCfgPortPriorityEntry 2 }

qosCurCfgPriorityCoSTable OBJECT-TYPE
    SYNTAX SEQUENCE OF QoSCurCfgPriorityCoSEntry
    MAX-ACCESS not-accessible
    STATUS current
    DESCRIPTION
        "The table of Frame Priority and COSq configuration."
    ::= { qos8021p  3 }

qosCurCfgPriorityCoSEntry OBJECT-TYPE
    SYNTAX QoSCurCfgPriorityCoSEntry
    MAX-ACCESS not-accessible
    STATUS current
    DESCRIPTION
        "Information about a particular Frame Priority and COSq configuration."
    INDEX { qosCurCfgPriorityIndex }
    ::= { qosCurCfgPriorityCoSTable 1 }

QoSCurCfgPriorityCoSEntry ::= SEQUENCE {
    qosCurCfgPriorityIndex INTEGER,
    qosCurCfgPriorityCoSq  INTEGER
    }

qosCurCfgPriorityIndex  OBJECT-TYPE
    SYNTAX  INTEGER  (0..7)
    MAX-ACCESS  read-only
    STATUS  current
    DESCRIPTION
        "Frame priority Number"
    ::= { qosCurCfgPriorityCoSEntry 1 }

qosCurCfgPriorityCoSq  OBJECT-TYPE
    SYNTAX  INTEGER  (0..7)
    MAX-ACCESS  read-only
    STATUS  current
    DESCRIPTION
        "CoSq for a Frame Priority Should be between 0 and 7"
    ::= { qosCurCfgPriorityCoSEntry 2 }

qosNewCfgPriorityCoSTable OBJECT-TYPE
    SYNTAX SEQUENCE OF QoSNewCfgPriorityCoSEntry
    MAX-ACCESS not-accessible
    STATUS current
    DESCRIPTION
        "The table of Frame Priority and COSq configuration."
    ::= { qos8021p  4 }

qosNewCfgPriorityCoSEntry OBJECT-TYPE
    SYNTAX QoSNewCfgPriorityCoSEntry
    MAX-ACCESS not-accessible
    STATUS current
    DESCRIPTION
        "Information about a particular Frame Priority and COSq configuration."
    INDEX { qosNewCfgPriorityIndex }
    ::= { qosNewCfgPriorityCoSTable 1 }

QoSNewCfgPriorityCoSEntry ::= SEQUENCE {
    qosNewCfgPriorityIndex INTEGER,
    qosNewCfgPriorityCoSq  INTEGER
    }

qosNewCfgPriorityIndex  OBJECT-TYPE
    SYNTAX  INTEGER  (0..7)
    MAX-ACCESS  read-only
    STATUS  current
    DESCRIPTION
        "Frame priority Number"
    ::= { qosNewCfgPriorityCoSEntry 1 }

qosNewCfgPriorityCoSq  OBJECT-TYPE
    SYNTAX  INTEGER  (0..7)
    MAX-ACCESS  read-write
    STATUS  current
    DESCRIPTION
        "CoSq for a Frame Priority Should be between 0 and 7"
    ::= { qosNewCfgPriorityCoSEntry 2 }

qosCurCfgCosWeightTable OBJECT-TYPE
    SYNTAX SEQUENCE OF QoSCurCfgCosWeightEntry
    MAX-ACCESS not-accessible
    STATUS current
    DESCRIPTION
        "The table of CoSq and Weight configuration."
    ::= { qos8021p  5 }

qosCurCfgCosWeightEntry OBJECT-TYPE
    SYNTAX QoSCurCfgCosWeightEntry
    MAX-ACCESS not-accessible
    STATUS current
    DESCRIPTION
        "Information about a particular CoSq and Weight configuration."
    INDEX { qosCurCfgCosIndex }
    ::= { qosCurCfgCosWeightTable 1 }

QoSCurCfgCosWeightEntry ::= SEQUENCE {
    qosCurCfgCosIndex    INTEGER,
    qosCurCfgCosWeight   INTEGER
    }

qosCurCfgCosIndex  OBJECT-TYPE
    SYNTAX  INTEGER  (0..7)
    MAX-ACCESS  read-only
    STATUS  current
    DESCRIPTION
        "CoSq Number"
    ::= { qosCurCfgCosWeightEntry 1 }

qosCurCfgCosWeight  OBJECT-TYPE
    SYNTAX  INTEGER  (0..15)
    MAX-ACCESS  read-only
    STATUS  current
    DESCRIPTION
        "Weight of CoSq"
    ::= { qosCurCfgCosWeightEntry 2 }

qosNewCfgCosWeightTable OBJECT-TYPE
    SYNTAX SEQUENCE OF QoSNewCfgCosWeightEntry
    MAX-ACCESS not-accessible
    STATUS current
    DESCRIPTION
        "The table of CoSq and Weight configuration."
    ::= { qos8021p  6 }

qosNewCfgCosWeightEntry OBJECT-TYPE
    SYNTAX QoSNewCfgCosWeightEntry
    MAX-ACCESS not-accessible
    STATUS current
    DESCRIPTION
        "Information about a particular CoSq and Weight configuration."
    INDEX { qosNewCfgCosIndex }
    ::= { qosNewCfgCosWeightTable 1 }

QoSNewCfgCosWeightEntry ::= SEQUENCE {
    qosNewCfgCosIndex    INTEGER,
    qosNewCfgCosWeight   INTEGER
    }

qosNewCfgCosIndex  OBJECT-TYPE
    SYNTAX INTEGER  (0..7)
    MAX-ACCESS read-only
    STATUS  current
    DESCRIPTION
        "CoSq Number"
    ::= { qosNewCfgCosWeightEntry 1 }

qosNewCfgCosWeight  OBJECT-TYPE
    SYNTAX INTEGER  (0..15)
    MAX-ACCESS  read-write
    STATUS  current
    DESCRIPTION
        "Weight of CoSq"
    ::= { qosNewCfgCosWeightEntry 2 }


qosCurCfgCosNum OBJECT-TYPE
    SYNTAX  INTEGER { 
	num2(2),
	num8(8)
	}
    MAX-ACCESS  read-only
    STATUS  current  
    DESCRIPTION
        "Number of CoSq." 
    ::= { qos8021p 7 }

qosDefaultCfg OBJECT-TYPE
    SYNTAX  INTEGER {
        none(0),
        defaultCosNum(1),
        defaultWeight(2),
        defaultPriority(3)
        }
    MAX-ACCESS  read-write
    STATUS  current
    DESCRIPTION
        "Load default configuration."
    ::= { qos8021p 9 }


qosCurCfgDscpTable OBJECT-TYPE
    SYNTAX SEQUENCE OF QoSCurCfgDscpEntry
    MAX-ACCESS not-accessible
    STATUS current
    DESCRIPTION
        "The table of Dscp to New Dscp/802.1p priority configuration."
    ::= { qosdscp  1 }

qosCurCfgDscpEntry OBJECT-TYPE
    SYNTAX QoSCurCfgDscpEntry
    MAX-ACCESS not-accessible
    STATUS current
    DESCRIPTION
        "Information about a particular Dscp to New Dscp/802.1p priority configuration"
    INDEX { qosCurCfgDscpIndex }
    ::= { qosCurCfgDscpTable 1 }

QoSCurCfgDscpEntry ::= SEQUENCE {
    qosCurCfgDscpIndex    INTEGER,
    qosCurCfgMapDscp   INTEGER
    ,qosCurCfgMap8021p INTEGER
    }

qosCurCfgDscpIndex  OBJECT-TYPE
    SYNTAX  INTEGER  (0..63)
    MAX-ACCESS  read-only
    STATUS  current
    DESCRIPTION
        "Dscp value"
    ::= { qosCurCfgDscpEntry 1 }

qosCurCfgMapDscp  OBJECT-TYPE
    SYNTAX  INTEGER  (0..63)
    MAX-ACCESS  read-only
    STATUS  current
    DESCRIPTION
        "Map Dscp Value"
    ::= { qosCurCfgDscpEntry 2 }

qosCurCfgMap8021p  OBJECT-TYPE
    SYNTAX  INTEGER  (0..7)
    MAX-ACCESS  read-only
    STATUS  current
    DESCRIPTION
        "Map 802.1p value"
    ::= { qosCurCfgDscpEntry 3 }

qosNewCfgDscpTable OBJECT-TYPE
    SYNTAX SEQUENCE OF QoSNewCfgDscpEntry
    MAX-ACCESS not-accessible
    STATUS current
    DESCRIPTION
        "The table of Dscp to New Dscp/802.1p priority configuration."
    ::= { qosdscp  2 }

qosNewCfgDscpEntry OBJECT-TYPE
    SYNTAX QoSNewCfgDscpEntry
    MAX-ACCESS not-accessible
    STATUS current
    DESCRIPTION
        "Information about a particular Dscp to New Dscp/802.1p priority configuration"
    INDEX { qosNewCfgDscpIndex }
    ::= { qosNewCfgDscpTable 1 }

QoSNewCfgDscpEntry ::= SEQUENCE {
    qosNewCfgDscpIndex    INTEGER,
    qosNewCfgMapDscp   INTEGER
    ,qosNewCfgMap8021p INTEGER
    }

qosNewCfgDscpIndex  OBJECT-TYPE
    SYNTAX  INTEGER  (0..63)
    MAX-ACCESS  read-only
    STATUS  current
    DESCRIPTION
        "Dscp value"
    ::= { qosNewCfgDscpEntry 1 }

qosNewCfgMapDscp  OBJECT-TYPE
    SYNTAX  INTEGER  (0..63)
    MAX-ACCESS  read-write
    STATUS  current
    DESCRIPTION
        "Map Dscp Value"
    ::= { qosNewCfgDscpEntry 2 }

qosNewCfgMap8021p  OBJECT-TYPE
    SYNTAX  INTEGER  (0..7)
    MAX-ACCESS  read-write
    STATUS  current
    DESCRIPTION
        "Map 802.1p value"
    ::= { qosNewCfgDscpEntry 3 }

qosCurCfgDscpState OBJECT-TYPE
    SYNTAX  INTEGER {
        on(1),
        off(2)
        }
    MAX-ACCESS  read-only
    STATUS  current
    DESCRIPTION
        "This is for turning on/off DSCP globally." 
    ::= { qosdscp 3 }

qosNewCfgDscpState OBJECT-TYPE
    SYNTAX  INTEGER {
        on(1),
        off(2)
        }
    MAX-ACCESS  read-write
    STATUS  current
    DESCRIPTION
        "This is for turning on/off DSCP globally." 
    ::= { qosdscp 4 }

-- WRED ECN Configuration 
-- cur port profile table
qosCurCfgPortProfileTable OBJECT-TYPE
    SYNTAX SEQUENCE OF QoSCurCfgPortProfileEntry
    MAX-ACCESS not-accessible
    STATUS current
    DESCRIPTION
        "The table of QOS port WRED ECN profile configuration."
    ::= { qoswredecn  1 }

qoSCurCfgPortProfileEntry OBJECT-TYPE
    SYNTAX QoSCurCfgPortProfileEntry
    MAX-ACCESS not-accessible
    STATUS current
    DESCRIPTION
        "Information about a particular Transmit queue of a port WRED ECN profile configuration."
    INDEX { qosCurCfgProfilePortIndex , qosCurCfgTrqIndex}
    ::= { qosCurCfgPortProfileTable 1 }

QoSCurCfgPortProfileEntry ::= SEQUENCE {
    qosCurCfgProfilePortIndex      PortNumber,
    qosCurCfgTrqIndex		INTEGER,
                                        qosCurCfgTrqNonTcpMin       INTEGER,
                                        qosCurCfgTrqNonTcpMax       INTEGER,
                                        qosCurCfgTrqNonTcpRate      INTEGER,
                                        qosCurCfgTrqTcpMin          INTEGER,
                                        qosCurCfgTrqTcpMax          INTEGER,
                                        qosCurCfgTrqTcpRate     INTEGER,
    qosCurCfgPortTrqWredState   INTEGER
    }

qosCurCfgProfilePortIndex  OBJECT-TYPE
    SYNTAX  PortNumber
    MAX-ACCESS  read-only
    STATUS  current
    DESCRIPTION
        "Switch Port Number"
    ::= { qoSCurCfgPortProfileEntry 1 }

qosCurCfgTrqIndex  OBJECT-TYPE
    SYNTAX  INTEGER  (0..7)
    MAX-ACCESS  read-only
    STATUS  current
    DESCRIPTION
        "Transmit Queue Number"
    ::= { qoSCurCfgPortProfileEntry 2 }

    qosCurCfgTrqNonTcpMin  OBJECT-TYPE
    SYNTAX  INTEGER  (1..100)
    MAX-ACCESS  read-only
    STATUS  current
    DESCRIPTION
        "Port Transmit queue WRED ECN nontcp profile MinThreshold value."
    ::= { qoSCurCfgPortProfileEntry 3 }

    qosCurCfgTrqNonTcpMax  OBJECT-TYPE
    SYNTAX  INTEGER  (1..100)
    MAX-ACCESS  read-only
    STATUS  current
    DESCRIPTION
        "Port Transmit queue WRED ECN nontcp profile MaxThreshold value"
    ::= { qoSCurCfgPortProfileEntry 4 }

    qosCurCfgTrqNonTcpRate  OBJECT-TYPE
    SYNTAX  INTEGER  (1..100)
    MAX-ACCESS  read-only
    STATUS  current
    DESCRIPTION
        "Port Transmit queue WRED ECN nontcp profile DropRate value."
    ::= { qoSCurCfgPortProfileEntry 5 }
    qosCurCfgTrqTcpMin  OBJECT-TYPE
        SYNTAX  INTEGER  (1..100)
        MAX-ACCESS  read-only
        STATUS  current
        DESCRIPTION
        "Port Transmit queue WRED ECN tcp profile MinThreshold value."
        ::= { qoSCurCfgPortProfileEntry 6 }
    qosCurCfgTrqTcpMax  OBJECT-TYPE
        SYNTAX  INTEGER  (1..100)
        MAX-ACCESS  read-only
        STATUS  current
        DESCRIPTION
        "Port Transmit queue WRED ECN tcp profile MaxThreshold value"
        ::= { qoSCurCfgPortProfileEntry 7 }
    qosCurCfgTrqTcpRate  OBJECT-TYPE
        SYNTAX  INTEGER  (1..100)
        MAX-ACCESS  read-only
        STATUS  current
        DESCRIPTION
        "Port Transmit queue WRED ECN tcp profile DropRate value."
        ::= { qoSCurCfgPortProfileEntry 8 }

qosCurCfgPortTrqWredState  OBJECT-TYPE
        SYNTAX  INTEGER {
        on(1),
        off(2)
        }
    MAX-ACCESS  read-only
    STATUS  current
    DESCRIPTION
        "This is for turning on/off WRED per transmit queue per port."
        ::= { qoSCurCfgPortProfileEntry 9 }

-- new port profile table
qosNewCfgPortProfileTable OBJECT-TYPE
    SYNTAX SEQUENCE OF QoSNewCfgPortProfileEntry
    MAX-ACCESS not-accessible
    STATUS current
    DESCRIPTION
        "The table of QOS Port WRED ECN configuration."
    ::= { qoswredecn  2 }

qoSNewCfgPortProfileEntry OBJECT-TYPE
    SYNTAX QoSNewCfgPortProfileEntry
    MAX-ACCESS not-accessible
    STATUS current
    DESCRIPTION
        "Information about a particular Transmit queue of a port WRED ECN configuration."
    INDEX { qosNewCfgProfilePortIndex , qosNewCfgTrqIndex}
    ::= { qosNewCfgPortProfileTable 1 }

QoSNewCfgPortProfileEntry ::= SEQUENCE {
    qosNewCfgProfilePortIndex      PortNumber,
    qosNewCfgTrqIndex		INTEGER,
                                        qosNewCfgTrqNonTcpMin       INTEGER,
                                        qosNewCfgTrqNonTcpMax       INTEGER,
                                        qosNewCfgTrqNonTcpRate      INTEGER,
                                        qosNewCfgTrqTcpMin          INTEGER,
                                        qosNewCfgTrqTcpMax      INTEGER,
                                        qosNewCfgTrqTcpRate     INTEGER,
    qosNewCfgPortTrqWredState   INTEGER
    }

qosNewCfgProfilePortIndex  OBJECT-TYPE
    SYNTAX  PortNumber
    MAX-ACCESS  read-only
    STATUS  current
    DESCRIPTION
        "Switch Port Number"
    ::= { qoSNewCfgPortProfileEntry 1 }

qosNewCfgTrqIndex  OBJECT-TYPE
    SYNTAX  INTEGER  (0..7)
    MAX-ACCESS  read-only
    STATUS  current
    DESCRIPTION
        "Transmit Queue Number"
    ::= { qoSNewCfgPortProfileEntry 2 }

    qosNewCfgTrqNonTcpMin  OBJECT-TYPE
    SYNTAX  INTEGER  (1..100)
    MAX-ACCESS  read-write
    STATUS  current
    DESCRIPTION
        "Port Transmit queue WRED ECN nontcp profile MinThreshold value."
    ::= { qoSNewCfgPortProfileEntry 3 }

    qosNewCfgTrqNonTcpMax  OBJECT-TYPE
    SYNTAX  INTEGER  (1..100)
    MAX-ACCESS  read-write
    STATUS  current
    DESCRIPTION
        "Port Transmit queue WRED ECN nontcp profile MaxThreshold value."
    ::= { qoSNewCfgPortProfileEntry 4 }

    qosNewCfgTrqNonTcpRate  OBJECT-TYPE
    SYNTAX  INTEGER  (1..100)
    MAX-ACCESS  read-write
    STATUS  current
    DESCRIPTION
        "Port Transmit queue WRED ECN nontcp profile DropRate value."
    ::= { qoSNewCfgPortProfileEntry 5 }
    qosNewCfgTrqTcpMin  OBJECT-TYPE
        SYNTAX  INTEGER  (1..100)
        MAX-ACCESS  read-write
        STATUS  current
        DESCRIPTION
        "Port Transmit queue WRED ECN tcp profile MinThreshold value."
        ::= { qoSNewCfgPortProfileEntry 6 }
    qosNewCfgTrqTcpMax  OBJECT-TYPE
        SYNTAX  INTEGER  (1..100)
        MAX-ACCESS  read-write
        STATUS  current
        DESCRIPTION
        "Port Transmit queue WRED ECN tcp profile MaxThreshold value."
        ::= { qoSNewCfgPortProfileEntry 7 }
    qosNewCfgTrqTcpRate  OBJECT-TYPE
        SYNTAX  INTEGER  (1..100)
        MAX-ACCESS  read-write
        STATUS  current
        DESCRIPTION
        "Port Transmit queue WRED ECN tcp profile DropRate value."
        ::= { qoSNewCfgPortProfileEntry 8 }

qosNewCfgPortTrqWredState  OBJECT-TYPE
        SYNTAX  INTEGER {
        on(1),
        off(2)
        }
    MAX-ACCESS  read-write
    STATUS  current
    DESCRIPTION
        "This is for turning on/off WRED per transmit queue per port."
        ::= { qoSNewCfgPortProfileEntry 9 }

-- cur port wred ecn state
qosCurCfgPortStateTable OBJECT-TYPE
    SYNTAX SEQUENCE OF QoSCurCfgPortStateEntry
    MAX-ACCESS not-accessible
    STATUS current
    DESCRIPTION
        "The table of QOS port WRED ECN state configuration."
    ::= { qoswredecn  3 }

qoSCurCfgPortStateEntry OBJECT-TYPE
    SYNTAX QoSCurCfgPortStateEntry
    MAX-ACCESS not-accessible
    STATUS current
    DESCRIPTION
        "Information about a particular port WRED ECN state configuration."
    INDEX { qosCurCfgStatePortIndex }
    ::= { qosCurCfgPortStateTable 1 }

QoSCurCfgPortStateEntry ::= SEQUENCE {
    qosCurCfgStatePortIndex      PortNumber,
    qosCurCfgPortWredState   INTEGER,
    qosCurCfgPortEcnState   INTEGER
    }

qosCurCfgStatePortIndex  OBJECT-TYPE
    SYNTAX  PortNumber
    MAX-ACCESS  read-only
    STATUS  current
    DESCRIPTION
        "Switch Port Number"
    ::= { qoSCurCfgPortStateEntry 1 }

qosCurCfgPortWredState  OBJECT-TYPE
    SYNTAX  INTEGER {
        on(1),
        off(2)
        }
    MAX-ACCESS  read-only
    STATUS  current
    DESCRIPTION
        "This is for turning on/off WRED per port."
    ::= { qoSCurCfgPortStateEntry 2 }

qosCurCfgPortEcnState  OBJECT-TYPE
    SYNTAX  INTEGER {
        on(1),
        off(2)
        }
    MAX-ACCESS  read-only
    STATUS  current
    DESCRIPTION
        "This is for turning on/off ECN per port."
    ::= { qoSCurCfgPortStateEntry 3 }

-- new port wred ecn state
qosNewCfgPortStateTable OBJECT-TYPE
    SYNTAX SEQUENCE OF QoSNewCfgPortStateEntry
    MAX-ACCESS not-accessible
    STATUS current
    DESCRIPTION
        "The table of QOS port WRED ECN state configuration."
    ::= { qoswredecn  4 }

qoSNewCfgPortStateEntry OBJECT-TYPE
    SYNTAX QoSNewCfgPortStateEntry
    MAX-ACCESS not-accessible
    STATUS current
    DESCRIPTION
        "Information about a particular port WRED ECN state configuration."
    INDEX { qosNewCfgStatePortIndex }
    ::= { qosNewCfgPortStateTable 1 }

QoSNewCfgPortStateEntry ::= SEQUENCE {
    qosNewCfgStatePortIndex      PortNumber,
    qosNewCfgPortWredState   INTEGER,
    qosNewCfgPortEcnState   INTEGER
    }

qosNewCfgStatePortIndex  OBJECT-TYPE
    SYNTAX  PortNumber
    MAX-ACCESS  read-only
    STATUS  current
    DESCRIPTION
        "Switch Port Number"
    ::= { qoSNewCfgPortStateEntry 1 }

qosNewCfgPortWredState  OBJECT-TYPE
    SYNTAX  INTEGER {
        on(1),
        off(2)
        }
    MAX-ACCESS  read-write
    STATUS  current
    DESCRIPTION
        "This is for turning on/off WRED per port"
    ::= { qoSNewCfgPortStateEntry 2 }

qosNewCfgPortEcnState  OBJECT-TYPE
    SYNTAX  INTEGER {
        on(1),
        off(2)
        }
    MAX-ACCESS  read-write
    STATUS  current
    DESCRIPTION
        "This is for turning on/off ECN per port."
    ::= { qoSNewCfgPortStateEntry 3 }

-- global cur profile config
qosCurCfgGlobalProfileTable OBJECT-TYPE
    SYNTAX SEQUENCE OF QoSCurCfgGlobalProfileEntry
    MAX-ACCESS not-accessible
    STATUS current
    DESCRIPTION
        "The table of QOS global WRED ECN profile configuration."
    ::= { qoswredecn  5 }

qoSCurCfgGlobalProfileEntry OBJECT-TYPE
    SYNTAX QoSCurCfgGlobalProfileEntry
    MAX-ACCESS not-accessible
    STATUS current
    DESCRIPTION
        "Information about a particular Transmit queue of global WRED ECN profile configuration."
    INDEX { qosCurCfgGlobalTrqIndex}
    ::= { qosCurCfgGlobalProfileTable 1 }

QoSCurCfgGlobalProfileEntry ::= SEQUENCE {
    qosCurCfgGlobalTrqIndex		INTEGER,
                                        qosCurCfgGlobalTrqNonTcpMin     INTEGER,
                                        qosCurCfgGlobalTrqNonTcpMax INTEGER,
                                        qosCurCfgGlobalTrqNonTcpRate    INTEGER,
                                        qosCurCfgGlobalTrqTcpMin        INTEGER,
                                        qosCurCfgGlobalTrqTcpMax        INTEGER,
                                        qosCurCfgGlobalTrqTcpRate       INTEGER,    
    qosCurCfgGlobalTrqWredState   INTEGER
    }

qosCurCfgGlobalTrqIndex  OBJECT-TYPE
    SYNTAX  INTEGER  (0..7)
    MAX-ACCESS  read-only
    STATUS  current
    DESCRIPTION
        "Global Transmit Queue Number"
    ::= { qoSCurCfgGlobalProfileEntry 1 }

    qosCurCfgGlobalTrqNonTcpMin  OBJECT-TYPE
    SYNTAX  INTEGER  (1..100)
    MAX-ACCESS  read-only
    STATUS  current
    DESCRIPTION
        "Global transmit queue WRED ECN nontcp profile MinThreshold value"
    ::= { qoSCurCfgGlobalProfileEntry 2 }

    qosCurCfgGlobalTrqNonTcpMax  OBJECT-TYPE
    SYNTAX  INTEGER  (1..100)
    MAX-ACCESS  read-only
    STATUS  current
    DESCRIPTION
        "Global transmit queue WRED ECN nontcp profile MaxThreshold value"
    ::= { qoSCurCfgGlobalProfileEntry 3 }

    qosCurCfgGlobalTrqNonTcpRate  OBJECT-TYPE
    SYNTAX  INTEGER  (1..100)
    MAX-ACCESS  read-only
    STATUS  current
    DESCRIPTION
        "Global transmit queue WRED ECN nontcp profile DropRate value"
    ::= { qoSCurCfgGlobalProfileEntry 4 }
    qosCurCfgGlobalTrqTcpMin  OBJECT-TYPE
        SYNTAX  INTEGER  (1..100)
        MAX-ACCESS  read-only
        STATUS  current
        DESCRIPTION
        "Global transmit queue WRED ECN tcp profile MinThreshold value"
        ::= { qoSCurCfgGlobalProfileEntry 5 }
    qosCurCfgGlobalTrqTcpMax  OBJECT-TYPE
        SYNTAX  INTEGER  (1..100)
        MAX-ACCESS  read-only
        STATUS  current
        DESCRIPTION
        "Global transmit queue WRED ECN tcp profile MaxThreshold value"
        ::= { qoSCurCfgGlobalProfileEntry 6 }
    qosCurCfgGlobalTrqTcpRate  OBJECT-TYPE
        SYNTAX  INTEGER  (1..100)
        MAX-ACCESS  read-only
        STATUS  current
        DESCRIPTION
        "Global transmit queue WRED ECN tcp profile DropRate value"
        ::= { qoSCurCfgGlobalProfileEntry 7 }

qosCurCfgGlobalTrqWredState  OBJECT-TYPE
        SYNTAX  INTEGER {
        on(1),
        off(2)
        }
    MAX-ACCESS  read-only
    STATUS  current
    DESCRIPTION
        "This is for turning on/off WRED per global transmit queue"
        ::= { qoSCurCfgGlobalProfileEntry 8 }
    
-- global new profile config
qosNewCfgGlobalProfileTable OBJECT-TYPE
    SYNTAX SEQUENCE OF QoSNewCfgGlobalProfileEntry
    MAX-ACCESS not-accessible
    STATUS current
    DESCRIPTION
        "The table of QOS global WRED ECN profile configuration."
    ::= { qoswredecn  6 }

qoSNewCfgGlobalProfileEntry OBJECT-TYPE
    SYNTAX QoSNewCfgGlobalProfileEntry
    MAX-ACCESS not-accessible
    STATUS current
    DESCRIPTION
        "Information about a particular Transmit queue of global WRED ECN profile configuration."
    INDEX { qosNewCfgGlobalTrqIndex}
    ::= { qosNewCfgGlobalProfileTable 1 }

QoSNewCfgGlobalProfileEntry ::= SEQUENCE {
    qosNewCfgGlobalTrqIndex		INTEGER,
                                    qosNewCfgGlobalTrqNonTcpMin INTEGER,
                                    qosNewCfgGlobalTrqNonTcpMax INTEGER,
                                    qosNewCfgGlobalTrqNonTcpRate       INTEGER,
                                    qosNewCfgGlobalTrqTcpMin        INTEGER,
                                    qosNewCfgGlobalTrqTcpMax        INTEGER,
                                    qosNewCfgGlobalTrqTcpRate       INTEGER,
    qosNewCfgGlobalTrqWredState   INTEGER
    }

qosNewCfgGlobalTrqIndex  OBJECT-TYPE
    SYNTAX  INTEGER  (0..7)
    MAX-ACCESS  read-only
    STATUS  current
    DESCRIPTION
        "Global Transmit Queue Number"
    ::= { qoSNewCfgGlobalProfileEntry 1 }

    qosNewCfgGlobalTrqNonTcpMin  OBJECT-TYPE
    SYNTAX  INTEGER  (1..100)
    MAX-ACCESS  read-write
    STATUS  current
    DESCRIPTION
        "Global transmit queue WRED ECN nontcp profile MinThreshold value"
    ::= { qoSNewCfgGlobalProfileEntry 2 }

    qosNewCfgGlobalTrqNonTcpMax  OBJECT-TYPE
    SYNTAX  INTEGER  (1..100)
    MAX-ACCESS  read-write
    STATUS  current
    DESCRIPTION
        "Global transmit queue WRED ECN nontcp profile MaxThreshold value"
    ::= { qoSNewCfgGlobalProfileEntry 3 }

    qosNewCfgGlobalTrqNonTcpRate  OBJECT-TYPE
    SYNTAX  INTEGER  (1..100)
    MAX-ACCESS  read-write
    STATUS  current
    DESCRIPTION
        "Global transmit queue WRED ECN nontcp profile DropRate value"
    ::= { qoSNewCfgGlobalProfileEntry 4 }
    qosNewCfgGlobalTrqTcpMin  OBJECT-TYPE
        SYNTAX  INTEGER  (1..100)
        MAX-ACCESS  read-write
        STATUS  current
        DESCRIPTION
        "Global transmit queue WRED ECN tcp profile MinThreshold value"
        ::= { qoSNewCfgGlobalProfileEntry 5 }
    qosNewCfgGlobalTrqTcpMax  OBJECT-TYPE
        SYNTAX  INTEGER  (1..100)
        MAX-ACCESS  read-write
        STATUS  current
        DESCRIPTION
        "Global transmit queue WRED ECN tcp profile MaxThreshold value"
        ::= { qoSNewCfgGlobalProfileEntry 6 }
    qosNewCfgGlobalTrqTcpRate  OBJECT-TYPE
        SYNTAX  INTEGER  (1..100)
        MAX-ACCESS  read-write
        STATUS  current
        DESCRIPTION
        "Global transmit queue WRED ECN tcp profile DropRate value"
        ::= { qoSNewCfgGlobalProfileEntry 7 }

qosNewCfgGlobalTrqWredState  OBJECT-TYPE
        SYNTAX  INTEGER {
        on(1),
        off(2)
        }
    MAX-ACCESS  read-write
    STATUS  current
    DESCRIPTION
        "This is for turning on/off WRED per global transmit queue"
        ::= { qoSNewCfgGlobalProfileEntry 8 }

-- cur global wred ecn state
qosCurCfgGlobalWredState OBJECT-TYPE
    SYNTAX  INTEGER {
        on(1),
        off(2)
        }
    MAX-ACCESS  read-only
    STATUS  current
    DESCRIPTION
        "This is for turning on/off WRED globally." 
    ::= { qoswredecn 7 }

qosCurCfgGlobalEcnState OBJECT-TYPE
    SYNTAX  INTEGER {
        on(1),
        off(2)
        }
    MAX-ACCESS  read-only
    STATUS  current
    DESCRIPTION
        "This is for turning on/off ECN globally." 
    ::= { qoswredecn 8 }

-- new global wred ecn state
qosNewCfgGlobalWredState OBJECT-TYPE
    SYNTAX  INTEGER {
        on(1),
        off(2)
        }
    MAX-ACCESS  read-write
    STATUS  current
    DESCRIPTION
        "This is for turning on/off WRED globally." 
    ::= { qoswredecn 9 }

qosNewCfgGlobalEcnState OBJECT-TYPE
    SYNTAX  INTEGER {
        on(1),
        off(2)
        }
    MAX-ACCESS  read-write
    STATUS  current
    DESCRIPTION
        "This is for turning on/off ECN globally." 
    ::= { qoswredecn 10 }




-- ----------------------------------------------------------------------------
-- } INSERT:  qos
-- ----------------------------------------------------------------------------
-------------------------------------------------------------------------------
-- Feature Dependent Private MIBs for g8264T-mgmt
-------------------------------------------------------------------------------
acl                     OBJECT IDENTIFIER ::= { g8264T-mgmt 9 }
-- ----------------------------------------------------------------------------
-- { INSERT:  acl
-- ----------------------------------------------------------------------------

acConfig   OBJECT IDENTIFIER ::= { acl 1 }


acList      OBJECT IDENTIFIER ::= { acConfig 1 }

aclGroup    OBJECT IDENTIFIER ::= { acConfig 3 }

aclCfg      OBJECT IDENTIFIER ::= { acConfig 4 }

vmapConfig              OBJECT IDENTIFIER ::= { acl 3 }

acl6List      OBJECT IDENTIFIER ::= { acConfig 5 }

aclLog      OBJECT IDENTIFIER ::= { acConfig 6 }

-- ---------------------------------------------------------- --
-- Access Control List (ACL) Configuration
-- ---------------------------------------------------------- --

aclCurCfgTable  OBJECT-TYPE
    SYNTAX      SEQUENCE OF AclCurCfgEntry
    MAX-ACCESS  not-accessible
    STATUS      current
    DESCRIPTION
        "The table of current ACL configuration."
    ::= { acList 1 }

aclCurCfgEntry  OBJECT-TYPE
    SYNTAX      AclCurCfgEntry
    MAX-ACCESS  not-accessible
    STATUS      current
    DESCRIPTION
        "Current information about a particular ACL configuration entry."
    INDEX { aclCurCfgIndex }
    ::= { aclCurCfgTable 1 }

AclCurCfgEntry  ::= SEQUENCE {
    aclCurCfgIndex              Unsigned32,
    aclCurCfgGroup              Unsigned32,
    aclCurCfgFilterAction       INTEGER,
    aclCurCfgFilterActionSetPrio INTEGER,
    aclCurCfgEthFmt             INTEGER,
    aclCurCfgTagFmt             INTEGER,
    aclCurCfgIPFmt              INTEGER,
    aclCurCfgSrcMACAddress      MacAddress,
    aclCurCfgSrcMACMask         MacAddress,
    aclCurCfgDstMACAddress      MacAddress,
    aclCurCfgDstMACMask         MacAddress,
    aclCurCfgEthernetTypeName   INTEGER,
    aclCurCfgEthernetTypeValue  INTEGER,
    aclCurCfgVLanId             INTEGER,
    aclCurCfgVLanMask           DisplayString,
    aclCurCfg8021pPriority      INTEGER,
    aclCurCfgTypeOfService      DisplayString,
    aclCurCfgProtocol           DisplayString,
    aclCurCfgSrcIPAddress       IpAddress,
    aclCurCfgSrcIPMask          IpAddress,
    aclCurCfgDstIPAddress       IpAddress,
    aclCurCfgDstIPMask          IpAddress,
    aclCurCfgSrcPort            INTEGER,
    aclCurCfgSrcPortMask        DisplayString,
    aclCurCfgDstPort            INTEGER,
    aclCurCfgDstPortMask        DisplayString,
    aclCurCfgTCPFlags           BITS,
    aclCurCfgTCPFlagsMask       BITS,
    aclCurCfgEgressPorts        OCTET STRING,
    aclCurCfgStatistics         INTEGER,
    aclCurCfgMeterAction        INTEGER,
    aclCurCfgMeterEnable        INTEGER,
    aclCurCfgKbitsSec          	Unsigned32,
    aclCurCfgKbitsBurst        	INTEGER,
    aclCurCfgUser      	        INTEGER,
    aclCurCfgInprofDscp        	INTEGER,
    aclCurCfgTos        	INTEGER,
    aclCurCfgOutprofDscp        INTEGER,
    aclCurCfgUserEnable  	INTEGER,
    aclCurCfgInprofDscpEnable  	INTEGER,
    aclCurCfgOutprofDscpEnable  INTEGER
    , aclCurCfgMirrorPort         Integer32
    , aclCurCfgLog                INTEGER
     }

aclCurCfgIndex  OBJECT-TYPE
    SYNTAX      Unsigned32
    MAX-ACCESS  read-only
    STATUS      current
    DESCRIPTION
        "The index associated with this ACL entry."
    ::= { aclCurCfgEntry 1 }


aclCurCfgGroup  OBJECT-TYPE
    SYNTAX      Unsigned32
    MAX-ACCESS  read-only
    STATUS      current
    DESCRIPTION
        "The index of the ACL group to which this ACL entry is a member of.
        A value of zero means the ACL is not a member of any group."
    ::= { aclCurCfgEntry 3 }

aclCurCfgFilterAction  OBJECT-TYPE
    SYNTAX      INTEGER {
                    none(0),
                    permit(1),
                    deny(2)
                    ,setprio(3)

                }
    MAX-ACCESS  read-only
    STATUS      current
    DESCRIPTION
        "The action to be performed on a packet that matches the filter
        settings of this ACL entry."
    ::= { aclCurCfgEntry 4 }

aclCurCfgFilterActionSetPrio  OBJECT-TYPE
    SYNTAX      INTEGER {
                    none(0),
                    prio0(1),
                    prio1(2),
                    prio2(3),
                    prio3(4),
                    prio4(5),
                    prio5(6),
                    prio6(7),
                    prio7(8)
                }
    MAX-ACCESS  read-only
    STATUS      current
    DESCRIPTION
        "The value to be used when the action to be performed is setprio
        for this ACL entry."
    ::= { aclCurCfgEntry 5 }

aclCurCfgEthFmt  OBJECT-TYPE
    SYNTAX      INTEGER {
                    none(0),
                    ethernet2(1),
                    snap(2),
                    llc(3)
                }
    MAX-ACCESS  read-only
    STATUS      current
    DESCRIPTION
        "The packet ethernet format to be filtered."
    ::= { aclCurCfgEntry 6 }

aclCurCfgTagFmt  OBJECT-TYPE
    SYNTAX      INTEGER {
                    disabled(1),
                    any(2),
                    untagged(3),
                    tagged(4)
                }
    MAX-ACCESS  read-only
    STATUS      current
    DESCRIPTION
        "The packet tag format to be filtered."
    ::= { aclCurCfgEntry 7 }

aclCurCfgIPFmt  OBJECT-TYPE
    SYNTAX      INTEGER {
                    none(1),
                    ipv4(2),
                    ipv6(3)
                }
    MAX-ACCESS  read-only
    STATUS      current
    DESCRIPTION
        "The packet IP format to be filtered."
    ::= { aclCurCfgEntry 8 }


aclCurCfgSrcMACAddress  OBJECT-TYPE
    SYNTAX      MacAddress
    MAX-ACCESS  read-only
    STATUS      current
    DESCRIPTION
        "The source MAC address to be filtered."
    ::= { aclCurCfgEntry 9 }

aclCurCfgSrcMACMask  OBJECT-TYPE
    SYNTAX      MacAddress
    MAX-ACCESS  read-only
    STATUS      current
    DESCRIPTION
        "The address mask applied to aclCurCfgSrcMACAddress for filtering."
    ::= { aclCurCfgEntry 10 }

aclCurCfgDstMACAddress  OBJECT-TYPE
    SYNTAX      MacAddress
    MAX-ACCESS  read-only
    STATUS      current
    DESCRIPTION
        "The destination MAC address to be filtered."
    ::= { aclCurCfgEntry 11 }

aclCurCfgDstMACMask  OBJECT-TYPE
    SYNTAX      MacAddress
    MAX-ACCESS  read-only
    STATUS      current
    DESCRIPTION
        "The address mask applied to aclCurCfgDstMACAddress for filtering."
    ::= { aclCurCfgEntry 12 }

aclCurCfgEthernetTypeName  OBJECT-TYPE
    SYNTAX      INTEGER {
                    none(0),
                    arp(1),
                    ipv4(2),
                    ipv6(3),
                    mpls(4),
                    rarp(5),
                    any(6),
                    other(7)
                }
    MAX-ACCESS  read-only
    STATUS      current
    DESCRIPTION
        "The Ethernet type to be filtered. If the value of this
        object is other(7), the value of aclNewCfgEthernetTypeValue
        indicates the ethernet type that will be filtered."
    ::= { aclCurCfgEntry 13 }

aclCurCfgEthernetTypeValue  OBJECT-TYPE
    SYNTAX      INTEGER (1536..65535)
    MAX-ACCESS  read-only
    STATUS      current
    DESCRIPTION
        "The Ethernet type value to be filtered. The value of this
        object is equivalent to the value of aclNewCfgEthernetTypeName
        except when the value of aclNewCfgEthernetTypeName is other(7),
        which can be any user-defined value for this object."
    ::= { aclCurCfgEntry 14 }

aclCurCfgVLanId  OBJECT-TYPE
    SYNTAX      INTEGER (0..4095)
    MAX-ACCESS  read-only
    STATUS      current
    DESCRIPTION
        "The virtual LAN identifier to be filtered."
    ::= { aclCurCfgEntry 15 }

aclCurCfgVLanMask  OBJECT-TYPE
    SYNTAX      DisplayString
    MAX-ACCESS  read-only
    STATUS      current
    DESCRIPTION
        "The mask applied to aclCurCfgVLanId for filtering."
    ::= { aclCurCfgEntry 16 }

aclCurCfg8021pPriority  OBJECT-TYPE
    SYNTAX      INTEGER {
                    none(0),
                    priority0(1),
                    priority1(2),
                    priority2(3),
                    priority3(4),
                    priority4(5),
                    priority5(6),
                    priority6(7),
                    priority7(8)
                }
    MAX-ACCESS  read-only
    STATUS      current
    DESCRIPTION
        "The 802.1p priority to be filtered."
    ::= { aclCurCfgEntry 17 }

aclCurCfgTypeOfService  OBJECT-TYPE
    SYNTAX      DisplayString
    MAX-ACCESS  read-only
    STATUS      current
    DESCRIPTION
        "The type of service to be filtered.
         'none' for not initialised, within the
         range 0-255"
    ::= { aclCurCfgEntry 18 }

aclCurCfgProtocol  OBJECT-TYPE
    SYNTAX      DisplayString
    MAX-ACCESS  read-only
    STATUS      current
    DESCRIPTION
        "The protocol to be filtered.
         'none' for not initialised, within the
         range 0-255"
    ::= { aclCurCfgEntry 19 }

aclCurCfgSrcIPAddress  OBJECT-TYPE
    SYNTAX      IpAddress
    MAX-ACCESS  read-only
    STATUS      current
    DESCRIPTION
        "The source IP address to be filtered."
    ::= { aclCurCfgEntry 20 }

aclCurCfgSrcIPMask  OBJECT-TYPE
    SYNTAX      IpAddress
    MAX-ACCESS  read-only
    STATUS      current
    DESCRIPTION
        "The address mask applied to aclCurCfgSrcIPAddress for filtering."
    ::= { aclCurCfgEntry 21 }

aclCurCfgDstIPAddress  OBJECT-TYPE
    SYNTAX      IpAddress
    MAX-ACCESS  read-only
    STATUS      current
    DESCRIPTION
        "The destination IP address to be filtered."
    ::= { aclCurCfgEntry 22 }

aclCurCfgDstIPMask  OBJECT-TYPE
    SYNTAX      IpAddress
    MAX-ACCESS  read-only
    STATUS      current
    DESCRIPTION
        "The address mask applied to aclCurCfgDstIPAddress for filtering."
    ::= { aclCurCfgEntry 23 }

aclCurCfgSrcPort  OBJECT-TYPE
    SYNTAX      INTEGER (0..65535)
    MAX-ACCESS  read-only
    STATUS      current
    DESCRIPTION
        "The source TCP/UDP port number to be filtered."
    ::= { aclCurCfgEntry 24 }

aclCurCfgSrcPortMask  OBJECT-TYPE
    SYNTAX      DisplayString
    MAX-ACCESS  read-only
    STATUS      current
    DESCRIPTION
        "The mask applied to aclCurCfgSrcPort for filtering."
    ::= { aclCurCfgEntry 25 }

aclCurCfgDstPort  OBJECT-TYPE
    SYNTAX      INTEGER (0..65535)
    MAX-ACCESS  read-only
    STATUS      current
    DESCRIPTION
        "The destination TCP/UDP port number to be filtered."
    ::= { aclCurCfgEntry 26 }

aclCurCfgDstPortMask  OBJECT-TYPE
    SYNTAX      DisplayString
    MAX-ACCESS  read-only
    STATUS      current
    DESCRIPTION
        "The mask applied to aclCurCfgDstPort for filtering."
    ::= { aclCurCfgEntry 27 }

aclCurCfgTCPFlags  OBJECT-TYPE
    SYNTAX      BITS {
                    reserved1(0),
                    reserved2(1),
                    tcpURG(2),
                    tcpACK(3),
                    tcpPSH(4),
                    tcpRST(5),
                    tcpSYN(6),
                    tcpFIN(7)
                }
    MAX-ACCESS  read-only
    STATUS      current
    DESCRIPTION
        "The TCP flags to be filtered.
         OCTET
         xxxxxxxx
         ||||..||
         ||||..||_tcpFIN(7)
         ||||..|__tcpSYN(6)
         ||||
         ||||_____tcpACK(3)
         |||______tcpURG(2)
         ||_______reserved2(1)
         |________reserved1(0)

         where:
         - reserved1 - 0;
         - reserved2 - 0;
         - x - 0 or 1;
        "
    ::= { aclCurCfgEntry 28 }

aclCurCfgTCPFlagsMask  OBJECT-TYPE
    SYNTAX      BITS {
                    reserved1(0),
                    reserved2(1),
                    tcpURG(2),
                    tcpACK(3),
                    tcpPSH(4),
                    tcpRST(5),
                    tcpSYN(6),
                    tcpFIN(7)
                }
    MAX-ACCESS  read-only
    STATUS      current
    DESCRIPTION
        "The TCP flags mask.
         OCTET
         xxxxxxxx
         ||||..||
         ||||..||_tcpFIN(7)
         ||||..|__tcpSYN(6)
         ||||
         ||||_____tcpACK(3)
         |||______tcpURG(2)
         ||_______reserved2(1)
         |________reserved1(0)

         where:
         - reserved1 - 0;
         - reserved2 - 0;
         - x - 0 or 1;
        "
    ::= { aclCurCfgEntry 39 }
aclCurCfgEgressPorts  OBJECT-TYPE
    SYNTAX      OCTET STRING
    MAX-ACCESS  read-only
    STATUS      current
    DESCRIPTION
        "The port list in the ACL configured for egress filtering.
         The ports are presented in bitmap format, as follows:

            OCTET 1  OCTET 2  .....
            xxxxxxxx xxxxxxxx .....
            ||    || |
            ||    || |_ port 9
            ||    ||
            ||    ||___ port 8
            ||    |____ port 7
            ||      .    .   .
            ||_________ port 2
            |__________ port 1

         where x:
            1 - the represented port is configured for filtering.
            0 - the represented port is not configured for filtering."
    ::= { aclCurCfgEntry 29 }

aclCurCfgStatistics  OBJECT-TYPE
    SYNTAX      INTEGER {
                    disable(0),
                    enable(1)
                }
    MAX-ACCESS  read-only
    STATUS      current
    DESCRIPTION
        "Whether statistics collection for this ACL is enabled or not."
    ::= { aclCurCfgEntry 30 }

aclCurCfgMeterAction  OBJECT-TYPE
    SYNTAX      INTEGER {
					unconfigured(0),
					outdrop(1),
					outpass(2)
				}
    MAX-ACCESS  read-only
    STATUS      current
    DESCRIPTION
        "Meter Action for this ACL."
    ::= { aclCurCfgEntry 41 }

aclCurCfgMeterEnable  OBJECT-TYPE
    SYNTAX      INTEGER {
	enabled(0),
	disabled(1)
				}
    MAX-ACCESS  read-only
    STATUS      current
    DESCRIPTION
        "Meter state for this ACL."
    ::= { aclCurCfgEntry 42 }

aclCurCfgKbitsSec  OBJECT-TYPE
    SYNTAX      Unsigned32 (64..40000000)
    MAX-ACCESS  read-only
    STATUS      current
    DESCRIPTION
        "The commited rate of meter associated with this ACL entry."
    ::= { aclCurCfgEntry 43 }

aclCurCfgKbitsBurst  OBJECT-TYPE
    SYNTAX      INTEGER {
					kbits32(32),
					kbits64(64),
					kbits128(128),
					kbits256(256),
					kbits512(512),
					kbits1024(1024),
					kbits2048(2048),
					kbits4096(4096)
   				}
	MAX-ACCESS  read-only
    STATUS      current
    DESCRIPTION
        "The maxmium burst sizeof meter associated with this ACL entry."
    ::= { aclCurCfgEntry 44 }

aclCurCfgUser  OBJECT-TYPE
    SYNTAX      INTEGER (0..7)
    MAX-ACCESS  read-only
    STATUS      current
    DESCRIPTION
        "Set user defined priority for this ACL."
    ::= { aclCurCfgEntry 45 }

aclCurCfgInprofDscp  OBJECT-TYPE
    SYNTAX      INTEGER (0..63)
    MAX-ACCESS  read-only
    STATUS      current
    DESCRIPTION
        "Set in profile pkts DSCP value."
    ::= { aclCurCfgEntry 46 }

aclCurCfgTos  OBJECT-TYPE
    SYNTAX      INTEGER {
                    disable(0),
                    enable(1)
                }
    MAX-ACCESS  read-only
    STATUS      current
    DESCRIPTION
        "To enable/disable setting pkts based on TOS bits."
    ::= { aclCurCfgEntry 47 }

aclCurCfgOutprofDscp  OBJECT-TYPE
    SYNTAX      INTEGER (0..63)
    MAX-ACCESS  read-only
    STATUS      current
    DESCRIPTION
        "Set out profile pkts DSCP value."
    ::= { aclCurCfgEntry 48 }

aclCurCfgUserEnable  OBJECT-TYPE
    SYNTAX      INTEGER {
				    disabled(0),
					userdefined(1)
				}
    MAX-ACCESS  read-only
    STATUS      current
    DESCRIPTION
        "Set update method for this ACL."
    ::= { aclCurCfgEntry 49 }

aclCurCfgInprofDscpEnable  OBJECT-TYPE
    SYNTAX      INTEGER {
                    disable(0),
                    enable(1)
                }
    MAX-ACCESS  read-only
    STATUS      current
    DESCRIPTION
        "Whether in profile update DSCP for this ACL is enabled or not."
    ::= { aclCurCfgEntry 50 }

aclCurCfgOutprofDscpEnable  OBJECT-TYPE
    SYNTAX      INTEGER {
                    disable(0),
                    enable(1)
                }
    MAX-ACCESS  read-only
    STATUS      current
    DESCRIPTION
        "Whether out profile update DSCP for this ACL is enabled or not."
    ::= { aclCurCfgEntry 51 }







aclCurCfgMirrorPort  OBJECT-TYPE
    SYNTAX      Integer32
    MAX-ACCESS  read-only
    STATUS      current
    DESCRIPTION
        "Set port in the ACL for mirroring.
            n > 0 - the represented port is configured for mirroring.
            0     - the represented port is not configured for mirroring."
    ::= { aclCurCfgEntry 74 }


aclCurCfgLog  OBJECT-TYPE
    SYNTAX      INTEGER {
        disable(0),
        enable(1)
    }
    MAX-ACCESS  read-only
    STATUS      current
    DESCRIPTION
        "Whether log for this ACL is enabled or not."
    ::= { aclCurCfgEntry 81 }





 
--
-- New ACL Configuration Table
--

aclNewCfgTable OBJECT-TYPE
    SYNTAX      SEQUENCE OF AclNewCfgEntry
    MAX-ACCESS  not-accessible
    STATUS      current
    DESCRIPTION
        "The table of new ACL configuration."
    ::= { acList 2 }

aclNewCfgEntry OBJECT-TYPE
    SYNTAX      AclNewCfgEntry
    MAX-ACCESS  not-accessible
    STATUS      current
    DESCRIPTION
        "New information about a particular ACL configuration."
    INDEX { aclNewCfgIndex }
    ::= { aclNewCfgTable 1 }

AclNewCfgEntry ::= SEQUENCE {
    aclNewCfgIndex              Unsigned32,


    aclNewCfgGroup              Unsigned32,
    aclNewCfgFilterAction       INTEGER,
    aclNewCfgFilterActionSetPrio INTEGER,
    aclNewCfgEthFmt       INTEGER,
    aclNewCfgTagFmt       INTEGER,
    aclNewCfgIPFmt        INTEGER,
    aclNewCfgSrcMACAddress      MacAddress,
    aclNewCfgSrcMACMask         MacAddress,
    aclNewCfgDstMACAddress      MacAddress,
    aclNewCfgDstMACMask         MacAddress,
    aclNewCfgEthernetTypeName   INTEGER,
    aclNewCfgEthernetTypeValue  INTEGER,
    aclNewCfgVLanId             INTEGER,
    aclNewCfgVLanMask           DisplayString,
    aclNewCfg8021pPriority      INTEGER,
    aclNewCfgTypeOfService      DisplayString,
    aclNewCfgProtocol           DisplayString,
    aclNewCfgSrcIPAddress       IpAddress,
    aclNewCfgSrcIPMask          IpAddress,
    aclNewCfgDstIPAddress       IpAddress,
    aclNewCfgDstIPMask          IpAddress,
    aclNewCfgSrcPort            INTEGER,
    aclNewCfgSrcPortMask        DisplayString,
    aclNewCfgDstPort            INTEGER,
    aclNewCfgDstPortMask        DisplayString,
    aclNewCfgTCPFlags           BITS,
    aclNewCfgTCPFlagsMask       BITS,
    aclNewCfgEgressPorts        OCTET STRING,
    aclNewCfgStatistics         INTEGER,
    aclNewCfgAddEgressPort      PortNumber,
    aclNewCfgRemoveEgressPort   PortNumber,
    aclNewCfgDelete             INTEGER,
    aclNewCfgMeterAction        INTEGER,
    aclNewCfgMeterEnable        INTEGER,
    aclNewCfgKbitsSec          	Unsigned32,
    aclNewCfgKbitsBurst        	INTEGER,
    aclNewCfgUser 	     	INTEGER,
    aclNewCfgInprofDscp        	INTEGER,
    aclNewCfgTos        	INTEGER,
    aclNewCfgOutprofDscp        INTEGER,
    aclNewCfgUserEnable  	INTEGER,
    aclNewCfgInprofDscpEnable  	INTEGER,
    aclNewCfgOutprofDscpEnable  INTEGER,
    aclNewCfgReset		INTEGER
    , aclNewCfgEthernetReset      INTEGER
    , aclNewCfgIpv4Reset          INTEGER
    , aclNewCfgTcpudpReset        INTEGER
    , aclNewCfgMeterReset         INTEGER
    , aclNewCfgRemarkReset        INTEGER
    , aclNewCfgRemarkInprofReset  INTEGER
    , aclNewCfgRemarkOutprofReset INTEGER
    , aclNewCfgPktfmtReset        INTEGER
    , aclNewCfgMirrorPort         Integer32
    , aclNewCfgLog            INTEGER
     }

aclNewCfgIndex  OBJECT-TYPE
    SYNTAX      Unsigned32
    MAX-ACCESS  read-only
    STATUS      current
    DESCRIPTION
        "The index associated with this ACL entry."
    ::= { aclNewCfgEntry 1 }


aclNewCfgGroup  OBJECT-TYPE
    SYNTAX      Unsigned32
    MAX-ACCESS  read-only
    STATUS      current
    DESCRIPTION
        "The index of the ACL group to which this ACL entry is a member of.
        A value of zero means the ACL is not a member of any group."
    ::= { aclNewCfgEntry 3 }

aclNewCfgFilterAction  OBJECT-TYPE
    SYNTAX      INTEGER {
                    none(0),
                    permit(1),
                    deny(2)
                    ,setprio(3)


                }
    MAX-ACCESS  read-write
    STATUS      current
    DESCRIPTION
        "The action to be performed on a packet that matches the filter
        settings of this ACL entry."
    ::= { aclNewCfgEntry 4 }

aclNewCfgFilterActionSetPrio  OBJECT-TYPE
    SYNTAX      INTEGER {
                    none(0),
                    prio0(1),
                    prio1(2),
                    prio2(3),
                    prio3(4),
                    prio4(5),
                    prio5(6),
                    prio6(7),
                    prio7(8)
                }
    MAX-ACCESS  read-write
    STATUS      current
    DESCRIPTION
        "The COS queue to be used when the action for this ACL entry is
        set to setprio."
    ::= { aclNewCfgEntry 5 }

aclNewCfgEthFmt  OBJECT-TYPE
    SYNTAX      INTEGER {
                    none(0),
                    ethernet2(1),
                    snap(2),
                    llc(3)
                }
    MAX-ACCESS  read-write
    STATUS      current
    DESCRIPTION
        "The packet ethernet format to be filtered."
    ::= { aclNewCfgEntry 6 }

aclNewCfgTagFmt  OBJECT-TYPE
    SYNTAX      INTEGER {
                    disabled(1),
                    any(2),
                    none(3),
                    tagged(4)
                }
    MAX-ACCESS  read-write
    STATUS      current
    DESCRIPTION
        "The packet tagging format to be filtered."
    ::= { aclNewCfgEntry 7 }

aclNewCfgIPFmt  OBJECT-TYPE
    SYNTAX      INTEGER {
                    none(1),
                    ipv4(2),
                    ipv6(3)
                }
    MAX-ACCESS  read-write
    STATUS      current
    DESCRIPTION
        "The packet IP format to be filtered."
    ::= { aclNewCfgEntry 8 }


aclNewCfgSrcMACAddress  OBJECT-TYPE
    SYNTAX      MacAddress
    MAX-ACCESS  read-write
    STATUS      current
    DESCRIPTION
        "The source MAC address to be filtered. Whenever this object is
        set to a nonzero value, the aclNewCfgSrcMACMask object, if not
        yet set, will be automatically set to ff:ff:ff:ff:ff:ff."
    ::= { aclNewCfgEntry 9 }

aclNewCfgSrcMACMask  OBJECT-TYPE
    SYNTAX      MacAddress
    MAX-ACCESS  read-write
    STATUS      current
    DESCRIPTION
        "The address mask to be applied to aclNewCfgSrcMACAddress
         for filtering."
    ::= { aclNewCfgEntry 10 }

aclNewCfgDstMACAddress  OBJECT-TYPE
    SYNTAX      MacAddress
    MAX-ACCESS  read-write
    STATUS      current
    DESCRIPTION
        "The destination MAC address to be filtered. Whenever this object
        is set to a nonzero value, the aclNewCfgDstMACMask object, if not
        yet set, will be automatically set to ff:ff:ff:ff:ff:ff."
    ::= { aclNewCfgEntry 11 }

aclNewCfgDstMACMask  OBJECT-TYPE
    SYNTAX      MacAddress
    MAX-ACCESS  read-write
    STATUS      current
    DESCRIPTION
        "The address mask to be applied to aclNewCfgDstMACAddress
         for filtering."
    ::= { aclNewCfgEntry 12 }

aclNewCfgEthernetTypeName  OBJECT-TYPE
    SYNTAX      INTEGER {
                    none(0),
                    arp(1),
                    ipv4(2),
                    ipv6(3),
                    mpls(4),
                    rarp(5),
                    any(6),
                    other(7)
                }
    MAX-ACCESS  read-write
    STATUS      current
    DESCRIPTION
        "The Ethernet type to be filtered. If the value of this
        object is other(7), the value of aclNewCfgEthernetTypeValue
        indicates the ethernet type that will be filtered. If this
        object is set to a value other than other(7), the value of
        the aclNewCfgEthernetTypeValue object is automatically set,
        as follows:

        aclNewCfgEthernetTypeName   aclNewCfgEthernetTypeValue
            none(0)                         0
            arp(1)                       2054  (0x0806)
            ipv4(2)                      2048  (0x0800)
            ipv6(3)                     34525  (0x86dd)
            mpls(4)                     34887  (0x8847)
            rarp(5)                     32821  (0x8035)
            any(6)                      65535  (0xffff)
        "
    ::= { aclNewCfgEntry 13 }

aclNewCfgEthernetTypeValue  OBJECT-TYPE
    SYNTAX      INTEGER (1536..65535)
    MAX-ACCESS  read-write
    STATUS      current
    DESCRIPTION
        "The Ethernet type value to be filtered. The value of this
        object is equivalent to the value of aclNewCfgEthernetTypeName
        except when the value of aclNewCfgEthernetTypeName is other(7),
        which can be any user-defined value for this object."
    ::= { aclNewCfgEntry 14 }

aclNewCfgVLanId  OBJECT-TYPE
    SYNTAX      INTEGER (0..4095)
    MAX-ACCESS  read-write
    STATUS      current
    DESCRIPTION
        "The virtual LAN identifier to be filtered. Whenever this object
        is set to a nonzero value, the aclNewCfgVLanMask object, if not
        yet set, will be automatically set to 4095 (0xfff). When this
        object is set to 0, the Vlan ACL filter is disabled."
    ::= { aclNewCfgEntry 15 }

aclNewCfgVLanMask  OBJECT-TYPE
    SYNTAX      DisplayString
    MAX-ACCESS  read-write
    STATUS      current
    DESCRIPTION
        "The mask to be applied to aclNewCfgVLanId for filtering."
    ::= { aclNewCfgEntry 16 }

aclNewCfg8021pPriority  OBJECT-TYPE
    SYNTAX      INTEGER {
                    none(0),
                    priority0(1),
                    priority1(2),
                    priority2(3),
                    priority3(4),
                    priority4(5),
                    priority5(6),
                    priority6(7),
                    priority7(8)
                }
    MAX-ACCESS  read-write
    STATUS      current
    DESCRIPTION
        "The 802.1p priority to be filtered."
    ::= { aclNewCfgEntry 17 }

aclNewCfgTypeOfService  OBJECT-TYPE
    SYNTAX      DisplayString
    MAX-ACCESS  read-write
    STATUS      current
    DESCRIPTION
        "The type of service to be filtered.
         'none' for not initialised, within the
         range 0-255"
    ::= { aclNewCfgEntry 18 }

aclNewCfgProtocol  OBJECT-TYPE
    SYNTAX	DisplayString
    MAX-ACCESS  read-write
    STATUS      current
    DESCRIPTION
        "The protocol to be filtered.
         'none' for not initialised, within the
         range 0-255"
    ::= { aclNewCfgEntry 19 }

aclNewCfgSrcIPAddress  OBJECT-TYPE
    SYNTAX      IpAddress
    MAX-ACCESS  read-write
    STATUS      current
    DESCRIPTION
        "The source IP address to be filtered. Whenever this object is set
        to a nonzero value, the aclNewCfgSrcIPMask object, if not yet set,
        will be automatically set to 255.255.255.255."
    ::= { aclNewCfgEntry 20 }

aclNewCfgSrcIPMask  OBJECT-TYPE
    SYNTAX      IpAddress
    MAX-ACCESS  read-write
    STATUS      current
    DESCRIPTION
        "The address mask to be applied to aclNewCfgSrcIPAddress
         for filtering."
    ::= { aclNewCfgEntry 21 }

aclNewCfgDstIPAddress  OBJECT-TYPE
    SYNTAX      IpAddress
    MAX-ACCESS  read-write
    STATUS      current
    DESCRIPTION
        "The destination IP address to be filtered. Whenever this object is set
        to a nonzero value, the aclNewCfgDstIPMask object, if not yet set,
        will be automatically set to 255.255.255.255."
    ::= { aclNewCfgEntry 22 }

aclNewCfgDstIPMask  OBJECT-TYPE
    SYNTAX      IpAddress
    MAX-ACCESS  read-write
    STATUS      current
    DESCRIPTION
        "The address mask to be applied to aclNewCfgDstIPAddress for filtering."
    ::= { aclNewCfgEntry 23 }

aclNewCfgSrcPort  OBJECT-TYPE
    SYNTAX      INTEGER (1..65535)
    MAX-ACCESS  read-write
    STATUS      current
    DESCRIPTION
        "The source TCP/UDP port number to be filtered. Whenever this
        object is set if the aclNewCfgSrcPortMask object is not set
        will be automatically set to 65535 (0xffff)."
    ::= { aclNewCfgEntry 24 }

aclNewCfgSrcPortMask  OBJECT-TYPE
    SYNTAX      DisplayString
    MAX-ACCESS  read-write
    STATUS      current
    DESCRIPTION
        "The mask to be applied to aclNewCfgSrcPort for filtering."
    ::= { aclNewCfgEntry 25 }

aclNewCfgDstPort  OBJECT-TYPE
    SYNTAX      INTEGER (1..65535)
    MAX-ACCESS  read-write
    STATUS      current
    DESCRIPTION
        "The destination TCP/UDP port number to be filtered.  Whenever this
        object is set the aclNewCfgSrcPortMask object, if not yet set, will
	be automatically set to 65535 (0xffff)."
    ::= { aclNewCfgEntry 26 }

aclNewCfgDstPortMask  OBJECT-TYPE
    SYNTAX      DisplayString
    MAX-ACCESS  read-write
    STATUS      current
    DESCRIPTION
        "The mask to be applied to aclNewCfgDstPort for filtering."
    ::= { aclNewCfgEntry 27 }

aclNewCfgTCPFlags  OBJECT-TYPE
    SYNTAX     BITS {
                    reserved1(0),
                    reserved2(1),
                    tcpURG(2),
                    tcpACK(3),
                    tcpPSH(4),
                    tcpRST(5),
                    tcpSYN(6),
                    tcpFIN(7)
                }
    MAX-ACCESS  read-write
    STATUS      current
    DESCRIPTION
        "The TCP flags to be filtered.
         The TCP flags are presented in bitmap format, as follows:
         OCTET
         xxxxxxxx
         ||||..||
         ||||..||_tcpFIN(7)
         ||||..|__tcpSYN(6)
         ||||
         ||||_____tcpACK(3)
         |||______tcpURG(2)
         ||_______reserved2(1)
         |________reserved1(0)

         where:
         - reserved1 - 0;
         - reserved2 - 0;
         - x - 0 or 1;
        "

    ::= { aclNewCfgEntry 28 }

aclNewCfgTCPFlagsMask  OBJECT-TYPE
    SYNTAX      BITS {
                    reserved1(0),
                    reserved2(1),
                    tcpURG(2),
                    tcpACK(3),
                    tcpPSH(4),
                    tcpRST(5),
                    tcpSYN(6),
                    tcpFIN(7)
                }
    MAX-ACCESS  read-write
    STATUS      current
    DESCRIPTION
        "The TCP flags mask.
         The TCP flags are presented in bitmap format, as follows:
         OCTET
         xxxxxxxx
         ||||..||
         ||||..||_tcpFIN(7)
         ||||..|__tcpSYN(6)
         ||||
         ||||_____tcpACK(3)
         |||______tcpURG(2)
         ||_______reserved2(1)
         |________reserved1(0)

         where:
         - reserved1 - 0;
         - reserved2 - 0;
         - x - 0 or 1;
         Default value is 0x3f."
    ::= { aclNewCfgEntry 39 }

aclNewCfgEgressPorts  OBJECT-TYPE
    SYNTAX      OCTET STRING
    MAX-ACCESS  read-only
    STATUS      current
    DESCRIPTION
        "The port list in the ACL configured for egress filtering.
         The ports are presented in bitmap format, as follows:

            OCTET 1  OCTET 2  .....
            xxxxxxxx xxxxxxxx .....
            ||    || |
            ||    || |_ port 9
            ||    ||
            ||    ||___ port 8
            ||    |____ port 7
            ||      .    .   .
            ||_________ port 2
            |__________ port 1

         where x:
            1 - the represented port is configured for filtering.
            0 - the represented port is not configured for filtering."
    ::= { aclNewCfgEntry 29 }


aclNewCfgStatistics  OBJECT-TYPE
    SYNTAX      INTEGER {
                    disable(0),
                    enable(1)
                }
    MAX-ACCESS  read-write
    STATUS      current
    DESCRIPTION
        "Whether statistics collection for this ACL is enabled or not."
    ::= { aclNewCfgEntry 30 }

aclNewCfgAddEgressPort OBJECT-TYPE
    SYNTAX      PortNumber
    MAX-ACCESS  read-write
    STATUS      current
    DESCRIPTION
        "The port to be added to the specified ACL for egress filtering.
        A value of zero is always returned when this object is read."
    ::= { aclNewCfgEntry 31 }

aclNewCfgRemoveEgressPort OBJECT-TYPE
    SYNTAX      PortNumber
    MAX-ACCESS  read-write
    STATUS      current
    DESCRIPTION
        "The port to be removed from the specified ACL.  A value of zero
        is always returned when this object is read."
    ::= { aclNewCfgEntry 32 }


aclNewCfgDelete OBJECT-TYPE
    SYNTAX      INTEGER {
                    other(1),
                    delete(2)
                }
    MAX-ACCESS  read-write
    STATUS      current
    DESCRIPTION
        "This is an action object to delete an ACL entry.  A value of
        other(1) is always returned when this object is read."
    ::= { aclNewCfgEntry 33 }

aclNewCfgMeterAction  OBJECT-TYPE
    SYNTAX      INTEGER {
					unconfigured(0),
					outdrop(1),
					outpass(2)
				}
    MAX-ACCESS  read-write
    STATUS      current
    DESCRIPTION
        "Meter Action for this ACL."
    ::= { aclNewCfgEntry 41 }

aclNewCfgMeterEnable  OBJECT-TYPE
    SYNTAX      INTEGER {
	enabled(0),
	disabled(1)
				}
    MAX-ACCESS  read-write
    STATUS      current
    DESCRIPTION
        "Meter state for this ACL."
    ::= { aclNewCfgEntry 42 }

aclNewCfgKbitsSec  OBJECT-TYPE
    SYNTAX      Unsigned32 (64..40000000)
    MAX-ACCESS  read-write
    STATUS      current
    DESCRIPTION
        "The commited rate of meter associated with this ACL entry."
    ::= { aclNewCfgEntry 43 }


aclNewCfgKbitsBurst  OBJECT-TYPE
    SYNTAX      INTEGER {
					kbits32(32),
					kbits64(64),
					kbits128(128),
					kbits256(256),
					kbits512(512),
					kbits1024(1024),
					kbits2048(2048),
					kbits4096(4096)
   				}
    MAX-ACCESS  read-write
    STATUS      current
    DESCRIPTION
        "The maximum burst size of the meter associated with this ACL entry."
    ::= { aclNewCfgEntry 44 }

aclNewCfgUser  OBJECT-TYPE
    SYNTAX      INTEGER (0..7)
    MAX-ACCESS  read-write
    STATUS      current
    DESCRIPTION
        "Set user defined priority for this ACL."
    ::= { aclNewCfgEntry 45 }

aclNewCfgInprofDscp  OBJECT-TYPE
    SYNTAX      INTEGER (0..63)
    MAX-ACCESS  read-write
    STATUS      current
    DESCRIPTION
        "Set in profile pkts DSCP value."
    ::= { aclNewCfgEntry 46 }

aclNewCfgTos  OBJECT-TYPE
    SYNTAX      INTEGER {
                    disable(0),
                    enable(1)
                }
    MAX-ACCESS  read-write
    STATUS      current
    DESCRIPTION
        "To enable/disable setting pkts based on TOS bits."
    ::= { aclNewCfgEntry 47 }

aclNewCfgOutprofDscp  OBJECT-TYPE
    SYNTAX      INTEGER (0..63)
    MAX-ACCESS  read-write
    STATUS      current
    DESCRIPTION
        "Set out profile pkts DSCP value."
    ::= { aclNewCfgEntry 48 }

aclNewCfgUserEnable  OBJECT-TYPE
    SYNTAX      INTEGER {
				    disabled(0),
					userdefined(1)
				}
    MAX-ACCESS  read-write
    STATUS      current
    DESCRIPTION
        "Set update method for this ACL."
    ::= { aclNewCfgEntry 49 }

aclNewCfgInprofDscpEnable  OBJECT-TYPE
    SYNTAX      INTEGER {
                    disable(0),
                    enable(1)
                }
    MAX-ACCESS  read-write
    STATUS      current
    DESCRIPTION
        "Whether in profile update DSCP for this ACL is enabled or not.
         Only the value disable(0) can be set, causing the in profile
         update DSCP to be disabled for this ACL.
         The value enable(1) is automatically set when setting a value
         for aclNewCfgInprofDscp object."
    ::= { aclNewCfgEntry 50 }

aclNewCfgOutprofDscpEnable  OBJECT-TYPE
    SYNTAX      INTEGER {
                    disable(0),
                    enable(1)
                }
    MAX-ACCESS  read-write
    STATUS      current
    DESCRIPTION
        "Whether out profile update DSCP for this ACL is enabled or not.
         Only the value disable(0) can be set, causing the out profile
         update DSCP to be disabled for this ACL.
         The value enable(1) is automatically set when setting a value
         for aclNewCfgOutprofDscp object."
    ::= { aclNewCfgEntry 51 }


aclNewCfgReset OBJECT-TYPE
    SYNTAX      INTEGER {
                    other(1),
                    reset(2)
                }
    MAX-ACCESS  read-write
    STATUS      current
    DESCRIPTION
        "This is an action object to reset an ACL entry. A value of
        other(1) is always returned when this object is read."
    ::= { aclNewCfgEntry 52 }

aclNewCfgEthernetReset OBJECT-TYPE
    SYNTAX      INTEGER {
                    other(1),
                    reset(2)
                }
    MAX-ACCESS  read-write
    STATUS      current
    DESCRIPTION
        "This is an action object to reset an ACL Ethernet entry. A value of
        other(1) is always returned when this object is read."
    ::= { aclNewCfgEntry 53 }

aclNewCfgIpv4Reset OBJECT-TYPE
    SYNTAX      INTEGER {
                    other(1),
                    reset(2)
                }
    MAX-ACCESS  read-write
    STATUS      current
    DESCRIPTION
        "This is an action object to reset an ACL IPV4 entry. A value of
        other(1) is always returned when this object is read."
    ::= { aclNewCfgEntry 54 }

aclNewCfgTcpudpReset OBJECT-TYPE
    SYNTAX      INTEGER {
                    other(1),
                    reset(2)
                }
    MAX-ACCESS  read-write
    STATUS      current
    DESCRIPTION
        "This is an action object to reset an ACL Tcpudp entry. A value of
        other(1) is always returned when this object is read."
    ::= { aclNewCfgEntry 55 }

aclNewCfgMeterReset OBJECT-TYPE
    SYNTAX      INTEGER {
                    other(1),
                    reset(2)
                }
    MAX-ACCESS  read-write
    STATUS      current
    DESCRIPTION
        "This is an action object to reset an ACL Meter entry. A value of
        other(1) is always returned when this object is read."
    ::= { aclNewCfgEntry 56 }

aclNewCfgRemarkReset OBJECT-TYPE
    SYNTAX      INTEGER {
                    other(1),
                    reset(2)
                }
    MAX-ACCESS  read-write
    STATUS      current
    DESCRIPTION
        "This is an action object to reset an ACL Remark entry. A value of
        other(1) is always returned when this object is read."
    ::= { aclNewCfgEntry 57 }

aclNewCfgRemarkInprofReset OBJECT-TYPE
    SYNTAX      INTEGER {
                    other(1),
                    reset(2)
                }
    MAX-ACCESS  read-write
    STATUS      current
    DESCRIPTION
        "This is an action object to reset an ACL Remark Inprof entry. A value of
        other(1) is always returned when this object is read."
    ::= { aclNewCfgEntry 58 }

aclNewCfgRemarkOutprofReset OBJECT-TYPE
    SYNTAX      INTEGER {
                    other(1),
                    reset(2)
                }
    MAX-ACCESS  read-write
    STATUS      current
    DESCRIPTION
        "This is an action object to reset an ACL Remark Outprof entry. A value of
        other(1) is always returned when this object is read."
    ::= { aclNewCfgEntry 59 }

aclNewCfgPktfmtReset OBJECT-TYPE
    SYNTAX      INTEGER {
                    other(1),
                    reset(2)
                }
    MAX-ACCESS  read-write
    STATUS      current
    DESCRIPTION
        "This is an action object to reset an ACL Pktfmt entry. A value of
        other(1) is always returned when this object is read."
    ::= { aclNewCfgEntry 60 }




aclNewCfgMirrorPort  OBJECT-TYPE
    SYNTAX  Integer32
    MAX-ACCESS  read-write
    STATUS  current
    DESCRIPTION
        "Set port in the ACL for mirroring.
            n > 0 - the represented port is configured for mirroring.
            0     - the represented port is not configured for mirroring."
    ::= { aclNewCfgEntry 74 }


    aclNewCfgLog  OBJECT-TYPE
    SYNTAX  INTEGER {
        disable(0),
        enable(1)
    }
    MAX-ACCESS  read-write
    STATUS      current
    DESCRIPTION
        "Whether log for this ACL is enabled or not."
    ::= { aclNewCfgEntry 81 }




 

aclTableMaxSize OBJECT-TYPE
    SYNTAX  Integer32
    MAX-ACCESS  read-only
    STATUS  current
    DESCRIPTION
        "The maximum number of entries in the acl config tables."
    ::= { acList 5 }


-- ---------------------------------------------------------- --
-- Management Access Control List (MACL) Configuration
-- ---------------------------------------------------------- --

--
-- New Management ACL Configuration Table
--


-- ---------------------------------------------------------- --
-- Access Control List6 (ACL6) Configuration
-- ---------------------------------------------------------- --

acl6CurCfgTable  OBJECT-TYPE
    SYNTAX      SEQUENCE OF Acl6CurCfgEntry
    MAX-ACCESS  not-accessible
    STATUS      current
    DESCRIPTION
        "The table of current ACL6 configuration."
    ::= { acl6List 1 }

acl6CurCfgEntry  OBJECT-TYPE
    SYNTAX      Acl6CurCfgEntry
    MAX-ACCESS  not-accessible
    STATUS      current
    DESCRIPTION
        "Current information about a particular ACL6 configuration entry."
    INDEX { acl6CurCfgIndex }
    ::= { acl6CurCfgTable 1 }

Acl6CurCfgEntry  ::= SEQUENCE {
    acl6CurCfgIndex               Unsigned32,
	acl6CurCfgGroup				  Unsigned32,
    acl6CurCfgFilterAction        INTEGER,
    acl6CurCfgFilterActionSetPrio INTEGER,
    acl6CurCfgSrcIPv6Address      DisplayString,
    acl6CurCfgSrcIPv6PrefixLen    INTEGER,
    acl6CurCfgDstIPv6Address      DisplayString,
    acl6CurCfgDstIPv6PrefixLen    INTEGER,
    acl6CurCfgIPv6FlowLabel       DisplayString,
    acl6CurCfgIPv6TrafficClass    DisplayString,
    acl6CurCfgIPv6NextHeader      DisplayString,
    acl6CurCfgSrcPort             INTEGER,
    acl6CurCfgSrcPortMask         DisplayString,
    acl6CurCfgDstPort             INTEGER,
    acl6CurCfgDstPortMask         DisplayString,
    acl6CurCfgTCPFlags            BITS,
    acl6CurCfgTCPFlagsMask        BITS,
    acl6CurCfgEgressPorts         OCTET STRING,
	acl6CurCfgStatistics 		  INTEGER,
	acl6CurCfgUser				  INTEGER,
	acl6CurCfgInprofDscp 		  INTEGER,
	acl6CurCfgTos			      INTEGER,

	acl6CurCfgUserEnable 	      INTEGER,
	acl6CurCfgInprofDscpEnable	  INTEGER
    , acl6CurCfgLog             INTEGER
    , acl6CurCfgMeterAction        INTEGER
    , acl6CurCfgMeterEnable        INTEGER
    , acl6CurCfgKbitsSec           Unsigned32
    , acl6CurCfgKbitsBurst         INTEGER
    , acl6CurCfgOutprofDscp        INTEGER
    , acl6CurCfgOutprofDscpEnable  INTEGER
    }

acl6CurCfgIndex  OBJECT-TYPE
    SYNTAX      Unsigned32
    MAX-ACCESS  read-only
    STATUS      current
    DESCRIPTION
        "The index associated with this ACL6 entry."
    ::= { acl6CurCfgEntry 1 }

acl6CurCfgGroup	OBJECT-TYPE
	SYNTAX		Unsigned32
	MAX-ACCESS	read-only
	STATUS		current
	DESCRIPTION
		"The index of the ACL group to which this ACL6 entry is a member of.
		A value of zero means the ACL6 is not a member of any group."
	::= { acl6CurCfgEntry 2 }

acl6CurCfgFilterAction  OBJECT-TYPE
    SYNTAX      INTEGER {
                    none(0),
                    permit(1),
                    deny(2)
					,setprio(3)
                }
    MAX-ACCESS  read-only
    STATUS      current
    DESCRIPTION
        "The action to be performed on a packet that matches the filter
        settings of this ACL6 entry."
    ::= { acl6CurCfgEntry 3 }

acl6CurCfgFilterActionSetPrio  OBJECT-TYPE
    SYNTAX      INTEGER {
                    none(0),
                    prio0(1),
                    prio1(2),
                    prio2(3),
                    prio3(4),
                    prio4(5),
                    prio5(6),
                    prio6(7),
                    prio7(8)
                }
    MAX-ACCESS  read-only
    STATUS      current
    DESCRIPTION
        "The value to be used when the action to be performed is setprio
        for this ACL6 entry."
    ::= { acl6CurCfgEntry 4 }

acl6CurCfgSrcIPv6Address  OBJECT-TYPE
    SYNTAX      DisplayString (SIZE(0..40))
    MAX-ACCESS  read-only
    STATUS      current
    DESCRIPTION
        "The source IPv6 address to be filtered.
         Address should be 4-byte hexadecimal colon notation.
	     Valid IPv6 address should be in any of the following forms
	     xxxx:xxxx:xxxx:xxxx:xxxx:xxxx:xxxx:xxxx or
	     xxxx::xxxx:xxxx:xxxx:xxxx"
    ::= { acl6CurCfgEntry 5 }

acl6CurCfgSrcIPv6PrefixLen  OBJECT-TYPE
    SYNTAX      INTEGER (1..128)
    MAX-ACCESS  read-only
    STATUS      current
    DESCRIPTION
        "The IPv6 prefix applied to acl6CurCfgSrcIPv6PrefixLen for filtering."
    ::= { acl6CurCfgEntry 6 }

acl6CurCfgDstIPv6Address  OBJECT-TYPE
    SYNTAX      DisplayString (SIZE(0..40))
    MAX-ACCESS  read-only
    STATUS      current
    DESCRIPTION
        "The destination IPv6 address to be filtered.
         Address should be 4-byte hexadecimal colon notation.
	     Valid IPv6 address should be in any of the following forms
	     xxxx:xxxx:xxxx:xxxx:xxxx:xxxx:xxxx:xxxx or
	     xxxx::xxxx:xxxx:xxxx:xxxx"
    ::= { acl6CurCfgEntry 7 }

acl6CurCfgDstIPv6PrefixLen  OBJECT-TYPE
    SYNTAX      INTEGER (1..128)
    MAX-ACCESS  read-only
    STATUS      current
    DESCRIPTION
        "The IPv6 prefix applied to acl6CurCfgDstIPv6PrefixLen for filtering."
    ::= { acl6CurCfgEntry 8 }

acl6CurCfgIPv6FlowLabel  OBJECT-TYPE
    SYNTAX      DisplayString
    MAX-ACCESS  read-only
    STATUS      current
    DESCRIPTION
    	"The IPv6 FlowLabel to be filtered.
    	 'none' for not initialised, within the
    	 range 0-1048575"
    ::= { acl6CurCfgEntry 9 }

acl6CurCfgIPv6TrafficClass  OBJECT-TYPE
    SYNTAX      DisplayString
    MAX-ACCESS  read-only
    STATUS      current
    DESCRIPTION
    	"The IPv6 Traffic Class to be filtered.
    	 'none' for not initialised, within the
    	 range 0-255"
    ::= { acl6CurCfgEntry 10 }

acl6CurCfgIPv6NextHeader  OBJECT-TYPE
    SYNTAX      DisplayString
    MAX-ACCESS  read-only
    STATUS      current
    DESCRIPTION
        "The IPv6 next header to be filtered.
         'none' for not initialised, within the
         range 0-255"
    ::= { acl6CurCfgEntry 11 }

acl6CurCfgSrcPort  OBJECT-TYPE
    SYNTAX      INTEGER (1..65535)
    MAX-ACCESS  read-only
    STATUS      current
    DESCRIPTION
        "The source TCP/UDP port number to be filtered."
    ::= { acl6CurCfgEntry 12 }

acl6CurCfgSrcPortMask  OBJECT-TYPE
    SYNTAX      DisplayString
    MAX-ACCESS  read-only
    STATUS      current
    DESCRIPTION
        "The mask applied to acl6CurCfgSrcPort for filtering."
    ::= { acl6CurCfgEntry 13 }

acl6CurCfgDstPort  OBJECT-TYPE
    SYNTAX      INTEGER (1..65535)
    MAX-ACCESS  read-only
    STATUS      current
    DESCRIPTION
        "The destination TCP/UDP port number to be filtered."
    ::= { acl6CurCfgEntry 14 }

acl6CurCfgDstPortMask  OBJECT-TYPE
    SYNTAX      DisplayString
    MAX-ACCESS  read-only
    STATUS      current
    DESCRIPTION
        "The mask applied to acl6CurCfgDstPort for filtering."
    ::= { acl6CurCfgEntry 15 }

acl6CurCfgTCPFlags  OBJECT-TYPE
    SYNTAX      BITS {
                    reserved1(0),
                    reserved2(1),
                    tcpURG(2),
                    tcpACK(3),
                    tcpPSH(4),
                    tcpRST(5),
                    tcpSYN(6),
                    tcpFIN(7)
                }
    MAX-ACCESS  read-only
    STATUS      current
    DESCRIPTION
        "The TCP flags to be filtered.
         OCTET
         xxxxxxxx
         ||||..||
         ||||..||_tcpFIN(7)
         ||||..|__tcpSYN(6)
         ||||
         ||||_____tcpACK(3)
         |||______tcpURG(2)
         ||_______reserved2(1)
         |________reserved1(0)

         where:
         - reserved1 - 0;
         - reserved2 - 0;
         - x - 0 or 1;
        "
    ::= { acl6CurCfgEntry 16 }

acl6CurCfgTCPFlagsMask  OBJECT-TYPE
    SYNTAX      BITS {
                    reserved1(0),
                    reserved2(1),
                    tcpURG(2),
                    tcpACK(3),
                    tcpPSH(4),
                    tcpRST(5),
                    tcpSYN(6),
                    tcpFIN(7)
                }
    MAX-ACCESS  read-only
    STATUS      current
    DESCRIPTION
        "The TCP flags mask.
         OCTET
         xxxxxxxx
         ||||..||
         ||||..||_tcpFIN(7)
         ||||..|__tcpSYN(6)
         ||||
         ||||_____tcpACK(3)
         |||______tcpURG(2)
         ||_______reserved2(1)
         |________reserved1(0)

         where:
         - reserved1 - 0;
         - reserved2 - 0;
         - x - 0 or 1;
        "
    ::= { acl6CurCfgEntry 17 }

acl6CurCfgEgressPorts  OBJECT-TYPE
    SYNTAX      OCTET STRING
    MAX-ACCESS  read-only
    STATUS      current
    DESCRIPTION
        "The port list in the ACL6 configured for egress filtering.
         The ports are presented in bitmap format, as follows:

            OCTET 1  OCTET 2  .....
            xxxxxxxx xxxxxxxx .....
            ||    || |
            ||    || |_ port 9
            ||    ||
            ||    ||___ port 8
            ||    |____ port 7
            ||      .    .   .
            ||_________ port 2
            |__________ port 1

         where x:
            1 - the represented port is configured for filtering.
            0 - the represented port is not configured for filtering."
    ::= { acl6CurCfgEntry 18 }

acl6CurCfgStatistics  OBJECT-TYPE
    SYNTAX      INTEGER {
                    disable(0),
                    enable(1)
                }
    MAX-ACCESS  read-only
    STATUS      current
    DESCRIPTION
        "Whether statistics collection for this ACL6 is enabled or not."
    ::= { acl6CurCfgEntry 19 }

	acl6CurCfgUser  OBJECT-TYPE
		SYNTAX		INTEGER (0..7)
		MAX-ACCESS	read-only
		STATUS		current
		DESCRIPTION
			"Set user defined priority for this ACL6."
		::= { acl6CurCfgEntry 20 }

	acl6CurCfgInprofDscp  OBJECT-TYPE
		SYNTAX		INTEGER (0..63)
		MAX-ACCESS	read-only
		STATUS		current
		DESCRIPTION
			"Set in profile pkts DSCP value."
		::= { acl6CurCfgEntry 21 }

	acl6CurCfgTos  OBJECT-TYPE
		SYNTAX		INTEGER {
						disable(0),
						enable(1)
					}
		MAX-ACCESS	read-only
		STATUS		current
		DESCRIPTION
			"To enable/disable setting pkts based on TOS bits."
		::= { acl6CurCfgEntry 22 }

	acl6CurCfgUserEnable  OBJECT-TYPE
		SYNTAX		INTEGER {
						disabled(0),
						userdefined(1)
					}
		MAX-ACCESS	read-only
		STATUS		current
		DESCRIPTION
			"Set update method for this ACL6."
		::= { acl6CurCfgEntry 24 }

	acl6CurCfgInprofDscpEnable  OBJECT-TYPE
		SYNTAX		INTEGER {
						disable(0),
						enable(1)
					}
		MAX-ACCESS	read-only
		STATUS		current
		DESCRIPTION
			"Whether in profile update DSCP for this ACL6 is enabled or not."
		::= { acl6CurCfgEntry 25 }



    acl6CurCfgLog  OBJECT-TYPE
    SYNTAX  INTEGER {
        disable(0),
        enable(1)
    }
    MAX-ACCESS  read-only
    STATUS      current
    DESCRIPTION
        "Whether log for this ACL is enabled or not."
    ::= { acl6CurCfgEntry 26 }


acl6CurCfgMeterAction  OBJECT-TYPE
    SYNTAX      INTEGER {
                                        unconfigured(0),
                                        outdrop(1),
                                        outpass(2)
                                }
    MAX-ACCESS  read-only
    STATUS      current
    DESCRIPTION
        "Meter Action for this ACL."
    ::= { acl6CurCfgEntry 28 }

acl6CurCfgMeterEnable  OBJECT-TYPE
    SYNTAX      INTEGER {
        enabled(0),
        disabled(1)
                                }
    MAX-ACCESS  read-only
    STATUS      current
    DESCRIPTION
        "Meter state for this ACL."
    ::= { acl6CurCfgEntry 29 }

acl6CurCfgKbitsSec  OBJECT-TYPE
    SYNTAX      Unsigned32 (64..40000000)
    MAX-ACCESS  read-only
    STATUS      current
    DESCRIPTION
        "The commited rate of meter associated with this ACL entry."
    ::= { acl6CurCfgEntry 30 }

acl6CurCfgKbitsBurst  OBJECT-TYPE
    SYNTAX      INTEGER {
                                        kbits32(32),
                                        kbits64(64),
                                        kbits128(128),
                                        kbits256(256),
                                        kbits512(512),
                                        kbits1024(1024),
                                        kbits2048(2048),
                                        kbits4096(4096)
                                }
        MAX-ACCESS  read-only
    STATUS      current
    DESCRIPTION
        "The maxmium burst sizeof meter associated with this ACL entry."
    ::= { acl6CurCfgEntry 31 }

acl6CurCfgOutprofDscp  OBJECT-TYPE
    SYNTAX      INTEGER (0..63)
    MAX-ACCESS  read-only
    STATUS      current
    DESCRIPTION
        "Set out profile pkts DSCP value."
    ::= { acl6CurCfgEntry 32 }

acl6CurCfgOutprofDscpEnable  OBJECT-TYPE
    SYNTAX      INTEGER {
                    disable(0),
                    enable(1)
                }
    MAX-ACCESS  read-only
    STATUS      current
    DESCRIPTION
        "Whether out profile update DSCP for this ACL is enabled or not."
    ::= { acl6CurCfgEntry 33 }


--
-- New ACL6 Configuration Table
--

acl6NewCfgTable OBJECT-TYPE
    SYNTAX      SEQUENCE OF Acl6NewCfgEntry
    MAX-ACCESS  not-accessible
    STATUS      current
    DESCRIPTION
        "The table of new ACL6 configuration."
    ::= { acl6List 2 }

acl6NewCfgEntry OBJECT-TYPE
    SYNTAX      Acl6NewCfgEntry
    MAX-ACCESS  not-accessible
    STATUS      current
    DESCRIPTION
        "New information about a particular ACL6 configuration."
    INDEX { acl6NewCfgIndex }
    ::= { acl6NewCfgTable 1 }

Acl6NewCfgEntry ::= SEQUENCE {
    acl6NewCfgIndex               Unsigned32,
	acl6NewCfgGroup				  Unsigned32,
    acl6NewCfgFilterAction        INTEGER,
    acl6NewCfgFilterActionSetPrio INTEGER,
    acl6NewCfgSrcIPv6Address      DisplayString,
    acl6NewCfgSrcIPv6PrefixLen    INTEGER,
    acl6NewCfgDstIPv6Address      DisplayString,
    acl6NewCfgDstIPv6PrefixLen    INTEGER,
    acl6NewCfgIPv6FlowLabel       DisplayString,
    acl6NewCfgIPv6TrafficClass    DisplayString,
    acl6NewCfgIPv6NextHeader      DisplayString,
    acl6NewCfgSrcPort             INTEGER,
    acl6NewCfgSrcPortMask         DisplayString,
    acl6NewCfgDstPort             INTEGER,
    acl6NewCfgDstPortMask         DisplayString,
    acl6NewCfgTCPFlags            BITS,
    acl6NewCfgTCPFlagsMask        BITS,
	acl6NewCfgEgressPorts		  OCTET STRING,
    acl6NewCfgStatistics          INTEGER,
	acl6NewCfgAddEgressPort		  PortNumber,
	acl6NewCfgRemoveEgressPort	  PortNumber,
    acl6NewCfgDelete              INTEGER,
	acl6NewCfgUser			      INTEGER,
	acl6NewCfgInprofDscp 		  INTEGER,
	acl6NewCfgTos			      INTEGER,

	acl6NewCfgUserEnable 	INTEGER,
	acl6NewCfgInprofDscpEnable	   INTEGER
	, acl6NewCfgIPv6Reset		   INTEGER
	, acl6NewCfgTcpudpReset		   INTEGER
	, acl6NewCfgRemarkInprofReset  INTEGER
        , acl6NewCfgLog                    INTEGER
    , acl6NewCfgMeterAction        INTEGER
    , acl6NewCfgMeterEnable        INTEGER
    , acl6NewCfgKbitsSec           Unsigned32
    , acl6NewCfgKbitsBurst         INTEGER
    , acl6NewCfgMeterReset         INTEGER
    , acl6NewCfgOutprofDscp        INTEGER
    , acl6NewCfgOutprofDscpEnable  INTEGER
    , acl6NewCfgRemarkOutprofReset INTEGER
    }


acl6NewCfgIndex  OBJECT-TYPE
    SYNTAX      Unsigned32
    MAX-ACCESS  read-only
    STATUS      current
    DESCRIPTION
        "The index associated with this ACL6 entry."
    ::= { acl6NewCfgEntry 1 }

acl6NewCfgGroup	OBJECT-TYPE
	SYNTAX		Unsigned32
	MAX-ACCESS	read-only
	STATUS		current
	DESCRIPTION
		"The index of the ACL group to which this ACL6 entry is a member of.
		A value of zero means the ACL6 is not a member of any group."
	::= { acl6NewCfgEntry 2 }

acl6NewCfgFilterAction  OBJECT-TYPE
    SYNTAX      INTEGER {
                    none(0),
                    permit(1),
                    deny(2)
					,setprio(3)
                }
    MAX-ACCESS  read-write
    STATUS      current
    DESCRIPTION
        "The action to be performed on a packet that matches the filter
        settings of this ACL6 entry."
    ::= { acl6NewCfgEntry 3 }

acl6NewCfgFilterActionSetPrio  OBJECT-TYPE
    SYNTAX      INTEGER {
                    none(0),
                    prio0(1),
                    prio1(2),
                    prio2(3),
                    prio3(4),
                    prio4(5),
                    prio5(6),
                    prio6(7),
                    prio7(8)
                }
    MAX-ACCESS  read-write
    STATUS      current
    DESCRIPTION
        "The COS queue to be used when the action for this ACL6 entry is
        set to setprio."
    ::= { acl6NewCfgEntry 4 }

acl6NewCfgSrcIPv6Address  OBJECT-TYPE
    SYNTAX      DisplayString (SIZE(0..40))
    MAX-ACCESS  read-write
    STATUS      current
    DESCRIPTION
        "The source IPv6 address to be filtered.
        Address should be 4-byte hexadecimal colon notation.
	    Valid IPv6 address should be in any of the following forms
	     xxxx:xxxx:xxxx:xxxx:xxxx:xxxx:xxxx:xxxx or
	     xxxx::xxxx:xxxx:xxxx:xxxx"
    ::= { acl6NewCfgEntry 5 }

acl6NewCfgSrcIPv6PrefixLen  OBJECT-TYPE
    SYNTAX      INTEGER (1..128)
    MAX-ACCESS  read-write
    STATUS      current
    DESCRIPTION
        "The IPv6 prefix applied to acl6CurCfgSrcIPv6PrefixLen for filtering."
    ::= { acl6NewCfgEntry 6 }

acl6NewCfgDstIPv6Address  OBJECT-TYPE
    SYNTAX      DisplayString (SIZE(0..40))
    MAX-ACCESS  read-write
    STATUS      current
    DESCRIPTION
        "The destination IPv6 address to be filtered.
         Address should be 4-byte hexadecimal colon notation.
	     Valid IPv6 address should be in any of the following forms
	     xxxx:xxxx:xxxx:xxxx:xxxx:xxxx:xxxx:xxxx or
	     xxxx::xxxx:xxxx:xxxx:xxxx"
    ::= { acl6NewCfgEntry 7 }

acl6NewCfgDstIPv6PrefixLen  OBJECT-TYPE
    SYNTAX      INTEGER (1..128)
    MAX-ACCESS  read-write
    STATUS      current
    DESCRIPTION
        "The IPv6 prefix applied to acl6CurCfgDstIPv6PrefixLen for filtering."
    ::= { acl6NewCfgEntry 8 }

acl6NewCfgIPv6FlowLabel  OBJECT-TYPE
    SYNTAX      DisplayString
    MAX-ACCESS  read-write
    STATUS      current
    DESCRIPTION
        "The IPv6 flow label  to be filtered.
         'none' for not initialised, within the
         range 0-1048575"
    ::= { acl6NewCfgEntry 9 }

acl6NewCfgIPv6TrafficClass  OBJECT-TYPE
    SYNTAX      DisplayString
    MAX-ACCESS  read-write
    STATUS      current
    DESCRIPTION
        "The IPv6 traffic class to be filtered.
         'none' for not initialised, within the
         range 0-255"
    ::= { acl6NewCfgEntry 10 }

acl6NewCfgIPv6NextHeader  OBJECT-TYPE
    SYNTAX      DisplayString
    MAX-ACCESS  read-write
    STATUS      current
    DESCRIPTION
        "The IPv6 next header to be filtered.
         'none' for not initialised, within the
         range 0-255"
    ::= { acl6NewCfgEntry 11 }

acl6NewCfgSrcPort  OBJECT-TYPE
    SYNTAX      INTEGER (1..65535)
    MAX-ACCESS  read-write
    STATUS      current
    DESCRIPTION
        "The source TCP/UDP port number to be filtered."
    ::= { acl6NewCfgEntry 12 }

acl6NewCfgSrcPortMask  OBJECT-TYPE
    SYNTAX      DisplayString
    MAX-ACCESS  read-write
    STATUS      current
    DESCRIPTION
        "The mask applied to acl6CurCfgSrcPort for filtering."
    ::= { acl6NewCfgEntry 13 }

acl6NewCfgDstPort  OBJECT-TYPE
    SYNTAX      INTEGER (1..65535)
    MAX-ACCESS  read-write
    STATUS      current
    DESCRIPTION
        "The destination TCP/UDP port number to be filtered."
    ::= { acl6NewCfgEntry 14 }

acl6NewCfgDstPortMask  OBJECT-TYPE
    SYNTAX      DisplayString
    MAX-ACCESS  read-write
    STATUS      current
    DESCRIPTION
        "The mask applied to acl6CurCfgDstPort for filtering."
    ::= { acl6NewCfgEntry 15 }

acl6NewCfgTCPFlags  OBJECT-TYPE
    SYNTAX      BITS {
                    reserved1(0),
                    reserved2(1),
                    tcpURG(2),
                    tcpACK(3),
                    tcpPSH(4),
                    tcpRST(5),
                    tcpSYN(6),
                    tcpFIN(7)
                }
    MAX-ACCESS  read-write
    STATUS      current
    DESCRIPTION
        "The TCP flags to be filtered.
         OCTET
         xxxxxxxx
         ||||..||
         ||||..||_tcpFIN(7)
         ||||..|__tcpSYN(6)
         ||||
         ||||_____tcpACK(3)
         |||______tcpURG(2)
         ||_______reserved2(1)
         |________reserved1(0)

         where:
         - reserved1 - 0;
         - reserved2 - 0;
         - x - 0 or 1;
        "
    ::= { acl6NewCfgEntry 16 }

acl6NewCfgTCPFlagsMask  OBJECT-TYPE
    SYNTAX      BITS {
                    reserved1(0),
                    reserved2(1),
                    tcpURG(2),
                    tcpACK(3),
                    tcpPSH(4),
                    tcpRST(5),
                    tcpSYN(6),
                    tcpFIN(7)
                }
    MAX-ACCESS  read-write
    STATUS      current
    DESCRIPTION
        "The TCP flags mask.
         OCTET
         xxxxxxxx
         ||||..||
         ||||..||_tcpFIN(7)
         ||||..|__tcpSYN(6)
         ||||
         ||||_____tcpACK(3)
         |||______tcpURG(2)
         ||_______reserved2(1)
         |________reserved1(0)

         where:
         - reserved1 - 0;
         - reserved2 - 0;
         - x - 0 or 1;
        "
    ::= { acl6NewCfgEntry 17 }

acl6NewCfgEgressPorts  OBJECT-TYPE
    SYNTAX      OCTET STRING
    MAX-ACCESS  read-only
    STATUS      current
    DESCRIPTION
        "The port list in the ACL6 configured for egress filtering.
         The ports are presented in bitmap format, as follows:

            OCTET 1  OCTET 2  .....
            xxxxxxxx xxxxxxxx .....
            ||    || |
            ||    || |_ port 9
            ||    ||
            ||    ||___ port 8
            ||    |____ port 7
            ||      .    .   .
            ||_________ port 2
            |__________ port 1

         where x:
            1 - the represented port is configured for filtering.
            0 - the represented port is not configured for filtering."
    ::= { acl6NewCfgEntry 18 }

acl6NewCfgStatistics  OBJECT-TYPE
    SYNTAX      INTEGER {
                    disable(0),
                    enable(1)
                }
    MAX-ACCESS  read-write
    STATUS      current
    DESCRIPTION
        "Whether statistics collection for this ACL6 is enabled or not."
    ::= { acl6NewCfgEntry 19 }

acl6NewCfgAddEgressPort OBJECT-TYPE
    SYNTAX      PortNumber
    MAX-ACCESS  read-write
    STATUS      current
    DESCRIPTION
        "The port to be added to the specified ACL6 for egress filtering.
        A value of zero is always returned when this object is read."
    ::= { acl6NewCfgEntry 20 }

acl6NewCfgRemoveEgressPort OBJECT-TYPE
    SYNTAX      PortNumber
    MAX-ACCESS  read-write
    STATUS      current
    DESCRIPTION
        "The port to be removed from the specified ACL6.  A value of zero
        is always returned when this object is read."
    ::= { acl6NewCfgEntry 21 }

acl6NewCfgDelete OBJECT-TYPE
    SYNTAX      INTEGER {
                    other(1),
                    delete(2)
                }
    MAX-ACCESS  read-write
    STATUS      current
    DESCRIPTION
        "This is an action object to delete an ACL6 entry.  A value of
        other(1) is always returned when this object is read."
    ::= { acl6NewCfgEntry 22 }

acl6NewCfgUser  OBJECT-TYPE
	SYNTAX		INTEGER (0..7)
	MAX-ACCESS	read-write
	STATUS		current
	DESCRIPTION
		"Set user defined priority for this ACL6."
	::= { acl6NewCfgEntry 23 }

acl6NewCfgInprofDscp  OBJECT-TYPE
	SYNTAX		INTEGER (0..63)
	MAX-ACCESS	read-write
	STATUS		current
	DESCRIPTION
		"Set in profile pkts DSCP value."
	::= { acl6NewCfgEntry 24 }

acl6NewCfgTos  OBJECT-TYPE
	SYNTAX		INTEGER {
					disable(0),
					enable(1)
				}
	MAX-ACCESS	read-write
	STATUS		current
	DESCRIPTION
		"To enable/disable setting pkts based on TOS bits."
	::= { acl6NewCfgEntry 25 }

acl6NewCfgUserEnable  OBJECT-TYPE
	SYNTAX		INTEGER {
					disabled(0),
					userdefined(1)
				}
	MAX-ACCESS	read-write
	STATUS		current
	DESCRIPTION
		"Set update method for this ACL6."
	::= { acl6NewCfgEntry 27 }

acl6NewCfgInprofDscpEnable  OBJECT-TYPE
	SYNTAX		INTEGER {
					disable(0),
					enable(1)
				}
	MAX-ACCESS	read-write
	STATUS		current
	DESCRIPTION
		"Whether in profile update DSCP for this ACL6 is enabled or not.
		 Only the value disable(0) can be set, causing the in profile
		 update DSCP to be disabled for this ACL6.
		 The value enable(1) is automatically set when setting a value
		 for aclNewCfgInprofDscp object."
	::= { acl6NewCfgEntry 28 }


acl6NewCfgIPv6Reset OBJECT-TYPE
	SYNTAX		INTEGER {
					other(1),
					reset(2)
				}
	MAX-ACCESS	read-write
	STATUS		current
	DESCRIPTION
		"This is an action object to reset an ACL IPV6 entry. A value of
		other(1) is always returned when this object is read."
	::= { acl6NewCfgEntry 30 }

acl6NewCfgTcpudpReset OBJECT-TYPE
	SYNTAX		INTEGER {
					other(1),
					reset(2)
				}
	MAX-ACCESS	read-write
	STATUS		current
	DESCRIPTION
		"This is an action object to reset an ACL6 Tcpudp entry. A value of
		other(1) is always returned when this object is read."
	::= { acl6NewCfgEntry 31 }

acl6NewCfgRemarkInprofReset OBJECT-TYPE
	SYNTAX		INTEGER {
					other(1),
					reset(2)
				}
	MAX-ACCESS	read-write
	STATUS		current
	DESCRIPTION
		"This is an action object to reset an ACL Remark Inprof entry. A value of
		other(1) is always returned when this object is read."
	::= { acl6NewCfgEntry 32 }

    acl6NewCfgLog  OBJECT-TYPE
    SYNTAX  INTEGER {
        disable(0),
        enable(1)
    }
    MAX-ACCESS  read-write
    STATUS      current
    DESCRIPTION
        "Whether log for this ACL is enabled or not."
    ::= { acl6NewCfgEntry 33 }


acl6NewCfgMeterAction  OBJECT-TYPE
    SYNTAX      INTEGER {
                                        unconfigured(0),
                                        outdrop(1),
                                        outpass(2)
                                }
    MAX-ACCESS  read-write
    STATUS      current
    DESCRIPTION
        "Meter Action for this ACL."
    ::= { acl6NewCfgEntry 35 }

acl6NewCfgMeterEnable  OBJECT-TYPE
    SYNTAX      INTEGER {
        enabled(0),
        disabled(1)
                                }
    MAX-ACCESS  read-write
    STATUS      current
    DESCRIPTION
        "Meter state for this ACL."
    ::= { acl6NewCfgEntry 36 }


acl6NewCfgKbitsSec  OBJECT-TYPE
    SYNTAX      Unsigned32 (64..40000000)
    MAX-ACCESS  read-write
    STATUS      current
    DESCRIPTION
        "The commited rate of meter associated with this ACL entry."
    ::= { acl6NewCfgEntry 37 }


acl6NewCfgKbitsBurst  OBJECT-TYPE
    SYNTAX      INTEGER {
                                        kbits32(32),
                                        kbits64(64),
                                        kbits128(128),
                                        kbits256(256),
                                        kbits512(512),
                                        kbits1024(1024),
                                        kbits2048(2048),
                                        kbits4096(4096)
                                }
    MAX-ACCESS  read-write
    STATUS      current
    DESCRIPTION
        "The maximum burst size of the meter associated with this ACL entry."
    ::= { acl6NewCfgEntry 38 }

acl6NewCfgMeterReset OBJECT-TYPE
    SYNTAX      INTEGER {
                    other(1),
                    reset(2)
                }
    MAX-ACCESS  read-write
    STATUS      current
    DESCRIPTION
        "This is an action object to reset an ACL6 Meter entry. A value of
        other(1) is always returned when this object is read."
    ::= { acl6NewCfgEntry 39 }

acl6NewCfgOutprofDscp  OBJECT-TYPE
    SYNTAX      INTEGER (0..63)
    MAX-ACCESS  read-write
    STATUS      current
    DESCRIPTION
        "Set out profile pkts DSCP value."
    ::= { acl6NewCfgEntry 40 }

acl6NewCfgOutprofDscpEnable  OBJECT-TYPE
    SYNTAX      INTEGER {
                    disable(0),
                    enable(1)
                }
    MAX-ACCESS  read-write
    STATUS      current
    DESCRIPTION
        "Whether out profile update DSCP for this ACL is enabled or not.
         Only the value disable(0) can be set, causing the out profile
         update DSCP to be disabled for this ACL.
         The value enable(1) is automatically set when setting a value
         for aclNewCfgOutprofDscp object."
    ::= { acl6NewCfgEntry 41 }


acl6NewCfgRemarkOutprofReset OBJECT-TYPE
    SYNTAX      INTEGER {
                    other(1),
                    reset(2)
                }
    MAX-ACCESS  read-write
    STATUS      current
    DESCRIPTION
        "This is an action object to reset an ACL Remark Outprof entry. A value of
        other(1) is always returned when this object is read."
    ::= { acl6NewCfgEntry 42 }

acl6TableMaxSize OBJECT-TYPE
    SYNTAX  Integer32
    MAX-ACCESS  read-only
    STATUS  current
    DESCRIPTION
        "The maximum number of entries in the acl6 config tables."
    ::= { acl6List 3 }


-- ---------------------------------------------------------- --
-- ACL Log Configuration
-- ---------------------------------------------------------- --
aclLogCurInterval  OBJECT-TYPE
    SYNTAX      INTEGER (5..600)
    MAX-ACCESS  read-only
    STATUS      current
    DESCRIPTION
        "The interval secends of displaying Logs.
         Default is 300s."
    ::= { aclLog 1 }

aclLogNewInterval  OBJECT-TYPE
    SYNTAX      INTEGER (5..600)
    MAX-ACCESS  read-write
    STATUS      current
    DESCRIPTION
        "The interval secends of displaying Logs.
         Default is 300s."
    ::= { aclLog 2 }

aclLogCurRateLimit  OBJECT-TYPE
    SYNTAX      INTEGER (1..1000)
    MAX-ACCESS  read-only
    STATUS      current
    DESCRIPTION
        "The rate limit of ACL Log queue.
         Default is 10pps."
    ::= { aclLog 3 }
	
aclLogNewRateLimit  OBJECT-TYPE
    SYNTAX      INTEGER (1..1000)
    MAX-ACCESS  read-write
    STATUS      current
    DESCRIPTION
        "The rate limit of ACL Log queue.
         Default is 10pps."
    ::= { aclLog 4 }



-- ---------------------------------------------------------- --
-- ACL Group Configuration
-- ---------------------------------------------------------- --

aclGroupCurCfgTable OBJECT-TYPE
    SYNTAX      SEQUENCE OF AclGroupCurCfgEntry
    MAX-ACCESS  not-accessible
    STATUS      current
    DESCRIPTION
        "The table of current ACL Group configuration."
    ::= { aclGroup 1 }

aclGroupCurCfgEntry OBJECT-TYPE
    SYNTAX      AclGroupCurCfgEntry
    MAX-ACCESS  not-accessible
    STATUS      current
    DESCRIPTION
        "Information about a particular ACL configuration."
    INDEX { aclGroupCurCfgIndex }
    ::= { aclGroupCurCfgTable 1 }

AclGroupCurCfgEntry ::= SEQUENCE {
    aclGroupCurCfgIndex        Unsigned32,
    aclGroupCurCfgMemberAcls   OCTET STRING
    , aclGroupCurCfgMemberAcl6s   OCTET STRING
    }

aclGroupCurCfgIndex  OBJECT-TYPE
    SYNTAX      Unsigned32
    MAX-ACCESS  read-only
    STATUS      current
    DESCRIPTION
        "The index associated with this ACL Group entry."
    ::= { aclGroupCurCfgEntry 1 }

aclGroupCurCfgMemberAcls  OBJECT-TYPE
    SYNTAX      OCTET STRING
    MAX-ACCESS  read-only
    STATUS      current
    DESCRIPTION
        "The ACL members of this ACL group, presented in bitmap
         format, as follows:

            OCTET 1  OCTET 2  .....
            xxxxxxxx xxxxxxxx .....
            ||    || |
            ||    || |_ ACL 9
            ||    ||
            ||    ||___ ACL 8
            ||    |____ ACL 7
            ||      .    .   .
            ||_________ ACL 2
            |__________ ACL 1

         where x:
            1 - the represented ACL is a member of the group.
            0 - the represented ACL is not a member of the group."
    ::= { aclGroupCurCfgEntry 2 }


aclGroupCurCfgMemberAcl6s  OBJECT-TYPE
	SYNTAX		OCTET STRING
	MAX-ACCESS	read-only
	STATUS		current
	DESCRIPTION
		"The ACL6 members of this ACL group, presented in bitmap
		 format, as follows:

			OCTET 1  OCTET 2  .....
			xxxxxxxx xxxxxxxx .....
			||	  || |
			||	  || |_ ACL6 9
			||	  ||
			||	  ||___ ACL6 8
			||	  |____ ACL6 7
			||		.	 .	 .
			||_________ ACL6 2
			|__________ ACL6 1

		 where x:
			1 - the represented ACL6 is a member of the group.
			0 - the represented ACL6 is not a member of the group."
	::= { aclGroupCurCfgEntry 9 }

aclGroupNewCfgTable OBJECT-TYPE
    SYNTAX      SEQUENCE OF AclGroupNewCfgEntry
    MAX-ACCESS  not-accessible
    STATUS      current
    DESCRIPTION
        "The table of new ACL Group configuration."
    ::= { aclGroup 2 }

aclGroupNewCfgEntry OBJECT-TYPE
    SYNTAX      AclGroupNewCfgEntry
    MAX-ACCESS  not-accessible
    STATUS      current
    DESCRIPTION
        "New information about a particular ACL configuration."
    INDEX { aclGroupNewCfgIndex }
    ::= { aclGroupNewCfgTable 1 }

AclGroupNewCfgEntry ::= SEQUENCE {
    aclGroupNewCfgIndex        Unsigned32,
    aclGroupNewCfgMemberAcls   OCTET STRING,
    aclGroupNewCfgAddAcl       Unsigned32,
    aclGroupNewCfgRemoveAcl    Unsigned32,
    aclGroupNewCfgDelete         INTEGER
	, aclGroupNewCfgMemberAcl6s  OCTET STRING
    , aclGroupNewCfgAddAcl6	     Unsigned32
    , aclGroupNewCfgRemoveAcl6   Unsigned32
    }

aclGroupNewCfgIndex  OBJECT-TYPE
    SYNTAX      Unsigned32
    MAX-ACCESS  read-only
    STATUS      current
    DESCRIPTION
        "The index associated with this ACL Group entry."
    ::= { aclGroupNewCfgEntry 1 }

aclGroupNewCfgMemberAcls  OBJECT-TYPE
    SYNTAX      OCTET STRING
    MAX-ACCESS  read-only
    STATUS      current
    DESCRIPTION
        "The ACL members of this ACL group, presented in bitmap
         format, as follows:

            OCTET 1  OCTET 2  .....
            xxxxxxxx xxxxxxxx .....
            ||    || |
            ||    || |_ ACL 9
            ||    ||
            ||    ||___ ACL 8
            ||    |____ ACL 7
            ||      .    .   .
            ||_________ ACL 2
            |__________ ACL 1

         where x:
            1 - the represented ACL is a member of the group.
            0 - the represented ACL is not a member of the group."
    ::= { aclGroupNewCfgEntry 2 }

aclGroupNewCfgAddAcl  OBJECT-TYPE
    SYNTAX      Unsigned32
    MAX-ACCESS  read-write
    STATUS      current
    DESCRIPTION
        "The index of the ACL entry to be added into this ACL group.
        A successful set operation on this object will also set the bit
        corresponding to the ACL entry in the aclGroupNewCfgMemberAcls
        bitmap. A value of zero is always returned when this object
        is read."
    ::= { aclGroupNewCfgEntry 4 }

aclGroupNewCfgRemoveAcl  OBJECT-TYPE
    SYNTAX      Unsigned32
    MAX-ACCESS  read-write
    STATUS      current
    DESCRIPTION
        "The index of the ACL entry to be removed from this ACL group.
        A successful set operation on this object will unset the bit
        corresponding to the ACL entry in the aclGroupNewCfgMemberAcls
        bitmap. A value of zero is always returned when this object
        is read."
    ::= { aclGroupNewCfgEntry 5 }

aclGroupNewCfgDelete  OBJECT-TYPE
    SYNTAX      INTEGER {
                    other(1),
                    delete(2)
                }
    MAX-ACCESS  read-write
    STATUS      current
    DESCRIPTION
        "This is an action object to delete an ACL group.  A value of other(1)
        is always returned when this object is read."
    ::= { aclGroupNewCfgEntry 8 }
aclGroupNewCfgMemberAcl6s  OBJECT-TYPE
    SYNTAX		OCTET STRING
    MAX-ACCESS	read-only
	STATUS		current
	DESCRIPTION
		"The ACL6 members of this ACL group, presented in bitmap
		format, as follows:

		OCTET 1  OCTET 2  .....
		xxxxxxxx xxxxxxxx .....
		||	  || |
		||	  || |_ ACL6 9
		||	  ||
		||	  ||___ ACL6 8
		||	  |____ ACL6 7
		||		.	 .	 .
		||_________ ACL6 2
		|__________ ACL6 1

		where x:
		1 - the represented ACL6 is a member of the group.
		0 - the represented ACL6 is not a member of the group."
::= { aclGroupNewCfgEntry 9 }


aclGroupNewCfgAddAcl6  OBJECT-TYPE
    SYNTAX      Unsigned32
    MAX-ACCESS  read-write
    STATUS      current
    DESCRIPTION
        "The index of the ACL6 entry to be added into this ACL group.
        A successful set operation on this object will also set the bit
        corresponding to the ACL6 entry in the aclGroupNewCfgMemberAcl6s
        bitmap. A value of zero is always returned when this object
        is read."
    ::= { aclGroupNewCfgEntry 10 }

aclGroupNewCfgRemoveAcl6  OBJECT-TYPE
    SYNTAX      Unsigned32
    MAX-ACCESS  read-write
    STATUS      current
    DESCRIPTION
        "The index of the ACL entry to be removed from this ACL group.
        A successful set operation on this object will unset the bit
        corresponding to the ACL entry in the aclGroupNewCfgMemberAcls
        bitmap. A value of zero is always returned when this object
        is read."
    ::= { aclGroupNewCfgEntry 11 }


aclCurCfgPortTable OBJECT-TYPE
    SYNTAX SEQUENCE OF AclCurCfgPortTableEntry
    MAX-ACCESS not-accessible
    STATUS current
    DESCRIPTION
        "The table of port acl groups configuration."
    ::= { aclCfg 1 }

aclCurCfgPortTableEntry OBJECT-TYPE
    SYNTAX AclCurCfgPortTableEntry
    MAX-ACCESS not-accessible
    STATUS current
    DESCRIPTION
        "Information about a particular port acl configuration."
    INDEX { aclCurCfgPortIndex }
    ::= { aclCurCfgPortTable 1 }

AclCurCfgPortTableEntry ::= SEQUENCE {
    aclCurCfgPortIndex    PortNumber,
    aclCurCfgPortAclBmap  OCTET STRING
    , aclCurCfgPortAclGrpBmap  OCTET STRING
    , aclCurCfgPortAcl6Bmap  OCTET STRING
    }

aclCurCfgPortIndex OBJECT-TYPE
    SYNTAX PortNumber
    MAX-ACCESS read-only
    STATUS current
    DESCRIPTION
        "The identifier of a particular port.  This is also
         index to the entLogicalTable of Entity MIB."
    ::= { aclCurCfgPortTableEntry 1 }

aclCurCfgPortAclBmap OBJECT-TYPE
    SYNTAX  OCTET STRING (SIZE(0..512))
    MAX-ACCESS  read-only
    STATUS  current
    DESCRIPTION
        "The acls applied to the port.  The acls are
         presented in bitmap format. This string displays acl number
         from 1 to 896.

         in receiving order:

             OCTET 1  OCTET 2  .....
             xxxxxxxx xxxxxxxx .....
             ||    || |_ acl 9
             ||    ||
             ||    ||___ acl 8
             ||    |____ acl 7
             ||      .    .   .
             ||_________ acl 2
             |__________ acl 1

         where x : 1 - The represented acl applied to the port.
                   0 - The represented acl not applied to the port."
    ::= { aclCurCfgPortTableEntry 2 }


aclCurCfgPortAclGrpBmap OBJECT-TYPE
    SYNTAX  OCTET STRING (SIZE(0..512))
    MAX-ACCESS  read-only
    STATUS  current
    DESCRIPTION
        "The acl groups applied to the port.  The acls are
         presented in bitmap format. This string displays acl number
         from 1 to 896.
         in receiving order:

             OCTET 1  OCTET 2  .....
             xxxxxxxx xxxxxxxx .....
             ||    || |_ aclgrp 9
             ||    ||
             ||    ||___ aclgrp 8
             ||    |____ aclgrp 7
             ||      .    .   .
             ||_________ aclgrp 2
             |__________ aclgrp 1

         where x : 1 - The represented acl applied to the port.
                   0 - The represented acl not applied to the port."
    ::= { aclCurCfgPortTableEntry 4 }

	aclCurCfgPortAcl6Bmap OBJECT-TYPE
    SYNTAX  OCTET STRING (SIZE(0..128))
    MAX-ACCESS  read-only
    STATUS  current
    DESCRIPTION
        "The acls applied to the port.  The acls are
         presented in bitmap format. This string displays acl number
         from 1 to 128.

         in receiving order:

             OCTET 1  OCTET 2  .....
             xxxxxxxx xxxxxxxx .....
             ||    || |_ acl6 9
             ||    ||
             ||    ||___ acl6 8
             ||    |____ acl6 7
             ||      .    .   .
             ||_________ acl6 2
             |__________ acl6 1

         where x : 1 - The represented acl6 applied to the port.
                   0 - The represented acl6 not applied to the port."
    ::= { aclCurCfgPortTableEntry 13 }


aclNewCfgPortTable OBJECT-TYPE
    SYNTAX SEQUENCE OF AclNewCfgPortTableEntry
    MAX-ACCESS not-accessible
    STATUS current
    DESCRIPTION
        "The table of port acl configuration."
    ::= { aclCfg 2 }

aclNewCfgPortTableEntry OBJECT-TYPE
    SYNTAX AclNewCfgPortTableEntry
    MAX-ACCESS not-accessible
    STATUS current
    DESCRIPTION
        "Information about a particular port acl groups configuration."
    INDEX { aclNewCfgPortIndex }
    ::= { aclNewCfgPortTable 1 }

AclNewCfgPortTableEntry ::= SEQUENCE {
    aclNewCfgPortIndex         PortNumber,
    aclNewCfgPortAddAcl        Unsigned32
    , aclNewCfgPortAddAclGrp     Unsigned32
    , aclNewCfgPortRemoveAcl     Unsigned32
    , aclNewCfgPortRemoveAclGrp  Unsigned32
    , aclNewCfgPortAclBmap       OCTET STRING
    , aclNewCfgPortAclGrpBmap    OCTET STRING
    , aclNewCfgPortAddAcl6        Unsigned32
    , aclNewCfgPortRemoveAcl6     Unsigned32
    , aclNewCfgPortAcl6Bmap 	  OCTET STRING
    }

aclNewCfgPortIndex  OBJECT-TYPE
    SYNTAX PortNumber
    MAX-ACCESS read-only
    STATUS current
    DESCRIPTION
        "The identifier of a particular port. This is also
         index to the entLogicalTable of Entity MIB."
    ::= { aclNewCfgPortTableEntry 1 }

aclNewCfgPortAddAcl OBJECT-TYPE
    SYNTAX  Unsigned32
    MAX-ACCESS  read-write
    STATUS  current
    DESCRIPTION
        "The acl to be added to the specified port.  A
         '0' value is returned when read."
    ::= {aclNewCfgPortTableEntry 2 }
aclNewCfgPortAddAclGrp OBJECT-TYPE
    SYNTAX  Unsigned32
    MAX-ACCESS  read-write
    STATUS  current
    DESCRIPTION
        "The acl group to be added to the specified port.  A
         '0' value is returned when read."
    ::= {aclNewCfgPortTableEntry 4 }

aclNewCfgPortRemoveAcl OBJECT-TYPE
    SYNTAX  Unsigned32
    MAX-ACCESS  read-write
    STATUS  current
    DESCRIPTION
        "The acl to be removed from the specified port.
         A '0' value is returned when read."
    ::= { aclNewCfgPortTableEntry 5 }
aclNewCfgPortRemoveAclGrp OBJECT-TYPE
    SYNTAX  Unsigned32
    MAX-ACCESS  read-write
    STATUS  current
    DESCRIPTION
        "The acl group to be removed from the specified port.
         A '0' value is returned when read."
    ::= { aclNewCfgPortTableEntry 7 }


aclNewCfgPortAclBmap OBJECT-TYPE
    SYNTAX  OCTET STRING (SIZE(0..512))
    MAX-ACCESS  read-only
    STATUS  current
    DESCRIPTION
        "The acls applied to the port.  The acls are
         presented in bitmap format. This string displays acl number
         from 1 to 896.
         in receiving order:

             OCTET 1  OCTET 2  .....
             xxxxxxxx xxxxxxxx .....
             ||    || |_ acl 9
             ||    ||
             ||    ||___ acl 8
             ||    |____ acl 7
             ||      .    .   .
             ||_________ acl 2
             |__________ acl 1

         where x : 1 - The represented acl applied to the port.
                   0 - The represented acl not applied to the port."
    ::= { aclNewCfgPortTableEntry 8 }
aclNewCfgPortAclGrpBmap OBJECT-TYPE
    SYNTAX  OCTET STRING (SIZE(0..512))
    MAX-ACCESS  read-only
    STATUS  current
    DESCRIPTION
        "The acl groups applied to the port.  The acl groups are
         presented in bitmap format. This string displays group number
         from 1 to 4096.

         in receiving order:

             OCTET 1  OCTET 2  .....
             xxxxxxxx xxxxxxxx .....
             ||    || |_ aclgrp 9
             ||    ||
             ||    ||___ aclgrp 8
             ||    |____ aclgrp 7
             ||      .    .   .
             ||_________ aclgrp 2
             |__________ aclgrp 1

         where x : 1 - The represented acl group applied to the port.
                   0 - The represented acl group not applied to the port."
    ::= { aclNewCfgPortTableEntry 10 }

	aclNewCfgPortAddAcl6 OBJECT-TYPE
    SYNTAX  Unsigned32
    MAX-ACCESS  read-write
    STATUS  current
    DESCRIPTION
        "The acl6 to be added to the specified port.  A
         '0' value is returned when read."
    ::= {aclNewCfgPortTableEntry 11 }

	aclNewCfgPortRemoveAcl6 OBJECT-TYPE
    SYNTAX  Unsigned32
    MAX-ACCESS  read-write
    STATUS  current
    DESCRIPTION
        "The acl6 to be removed from the specified port.
         A '0' value is returned when read."
    ::= { aclNewCfgPortTableEntry 12 }

    aclNewCfgPortAcl6Bmap OBJECT-TYPE
	SYNTAX	OCTET STRING (SIZE(0..512))
	MAX-ACCESS	read-only
	STATUS	current
	DESCRIPTION
		"The acl6s applied to the port.  The acl6s are
		 presented in bitmap format. This string displays acl number
		 from 1 to 128.
		 in receiving order:

			 OCTET 1  OCTET 2  .....
			 xxxxxxxx xxxxxxxx .....
			 ||    || |_ acl6 9
			 ||    ||
			 ||    ||___ acl6 8
			 ||    |____ acl6 7
			 || 	 .	  .   .
			 ||_________ acl6 2
			 |__________ acl6 1

		 where x : 1 - The represented acl6 applied to the port.
				   0 - The represented acl6 not applied to the port."
	::= { aclNewCfgPortTableEntry 13 }











-- ------------------------------------------------------------------------- --
-- VMAP Configuration                                                      {
-- ------------------------------------------------------------------------- --

vmapList                OBJECT IDENTIFIER ::= { vmapConfig 1 }
vmapCfg                 OBJECT IDENTIFIER ::= { vmapConfig 2 }

vmapVlanCfg             OBJECT IDENTIFIER ::= { vmapCfg 1 }
vmapGroupCfg            OBJECT IDENTIFIER ::= { vmapCfg 2 }

vmapVlanCfgNonServerPorts     OBJECT IDENTIFIER ::= { vmapVlanCfg 1 }
vmapVlanCfgServerPorts     OBJECT IDENTIFIER ::= { vmapVlanCfg 2 }
vmapVlanCfgAllPorts     OBJECT IDENTIFIER ::= { vmapVlanCfg 3 }

vmapGroupCfgNonServerPorts    OBJECT IDENTIFIER ::= { vmapGroupCfg 1 }
vmapGroupCfgServerPorts    OBJECT IDENTIFIER ::= { vmapGroupCfg 2 }
vmapGroupCfgAllPorts    OBJECT IDENTIFIER ::= { vmapGroupCfg 3 }

-- ------------------------------------------------------------------------- --
-- Current VMAP Configuration Table                                        {
-- ------------------------------------------------------------------------- --
vmapCurCfgTable  OBJECT-TYPE
    SYNTAX      SEQUENCE OF VmapCurCfgEntry
    MAX-ACCESS  not-accessible
    STATUS      current
    DESCRIPTION
        "The table of current VMAP configuration."
    ::= { vmapList 1 }

vmapCurCfgEntry  OBJECT-TYPE
    SYNTAX      VmapCurCfgEntry
    MAX-ACCESS  not-accessible
    STATUS      current
    DESCRIPTION
        "Current information about a particular VMAP configuration entry."
    INDEX { vmapCurCfgIndex }
    ::= { vmapCurCfgTable 1 }

VmapCurCfgEntry  ::= SEQUENCE {
    vmapCurCfgIndex                 Unsigned32,
    vmapCurCfgFilterAction          INTEGER,
    vmapCurCfgFilterActionSetPrio   INTEGER,
    vmapCurCfgEthFmt                INTEGER,
    vmapCurCfgTagFmt                INTEGER,
    vmapCurCfgIPFmt                 INTEGER,
    vmapCurCfgSrcMACAddress         MacAddress,
    vmapCurCfgSrcMACMask            MacAddress,
    vmapCurCfgDstMACAddress         MacAddress,
    vmapCurCfgDstMACMask            MacAddress,
    vmapCurCfgEthernetTypeName      INTEGER,
    vmapCurCfgEthernetTypeValue     INTEGER,
    vmapCurCfg8021pPriority         INTEGER,
    vmapCurCfgTypeOfService         DisplayString,
    vmapCurCfgProtocol              DisplayString,
    vmapCurCfgSrcIPAddress          IpAddress,
    vmapCurCfgSrcIPMask             IpAddress,
    vmapCurCfgDstIPAddress          IpAddress,
    vmapCurCfgDstIPMask             IpAddress,
    vmapCurCfgSrcPort               INTEGER,
    vmapCurCfgSrcPortMask           DisplayString,
    vmapCurCfgDstPort               INTEGER,
    vmapCurCfgDstPortMask           DisplayString,
    vmapCurCfgTCPFlags              BITS,
    vmapCurCfgTCPFlagsMask          BITS,
    vmapCurCfgEgressPorts           OCTET STRING,
    vmapCurCfgStatistics            INTEGER,
    vmapCurCfgMeterAction           INTEGER,
    vmapCurCfgMeterEnable           INTEGER,
    vmapCurCfgKbitsSec              Unsigned32,
    vmapCurCfgKbitsBurst            INTEGER,
    vmapCurCfgUser                  INTEGER,
    vmapCurCfgInprofDscp            INTEGER,
    vmapCurCfgTos                   INTEGER,
    vmapCurCfgOutprofDscp           INTEGER,
    vmapCurCfgUserEnable            INTEGER,
    vmapCurCfgInprofDscpEnable      INTEGER,
    vmapCurCfgOutprofDscpEnable     INTEGER
    , vmapCurCfgMirrorPort           Integer32
    }

vmapCurCfgIndex  OBJECT-TYPE
    SYNTAX      Unsigned32
    MAX-ACCESS  read-only
    STATUS      current
    DESCRIPTION
        "The index associated with this VMAP entry."
    ::= { vmapCurCfgEntry 1 }

vmapCurCfgFilterAction  OBJECT-TYPE
    SYNTAX      INTEGER {
                    none(0),
                    permit(1),
                    deny(2),
                    setprio(3)
                }
    MAX-ACCESS  read-only
    STATUS      current
    DESCRIPTION
        "The action to be performed on a packet that matches the filter
        settings of this VMAP entry."
    ::= { vmapCurCfgEntry 2 }

vmapCurCfgFilterActionSetPrio  OBJECT-TYPE
    SYNTAX      INTEGER {
                    none(0),
                    prio0(1),
                    prio1(2),
                    prio2(3),
                    prio3(4),
                    prio4(5),
                    prio5(6),
                    prio6(7),
                    prio7(8)
                }
    MAX-ACCESS  read-only
    STATUS      current
    DESCRIPTION
        "The value to be used when the action to be performed is setprio
        for this VMAP entry."
    ::= { vmapCurCfgEntry 3 }

vmapCurCfgEthFmt  OBJECT-TYPE
    SYNTAX      INTEGER {
                    none(0),
                    ethernet2(1),
                    snap(2),
                    llc(3)
                }
    MAX-ACCESS  read-only
    STATUS      current
    DESCRIPTION
        "The packet ethernet format to be filtered."
    ::= { vmapCurCfgEntry 4 }

vmapCurCfgTagFmt  OBJECT-TYPE
    SYNTAX      INTEGER {
                    disabled(1),
                    any(2),
                    untagged(3),
                    tagged(4)
                }
    MAX-ACCESS  read-only
    STATUS      current
    DESCRIPTION
        "The packet tag format to be filtered."
    ::= { vmapCurCfgEntry 5 }

vmapCurCfgIPFmt  OBJECT-TYPE
    SYNTAX      INTEGER {
                    none(1),
                    ipv4(2),
                    ipv6(3)
                }
    MAX-ACCESS  read-only
    STATUS      current
    DESCRIPTION
        "The packet IP format to be filtered."
    ::= { vmapCurCfgEntry 6 }

vmapCurCfgSrcMACAddress  OBJECT-TYPE
    SYNTAX      MacAddress
    MAX-ACCESS  read-only
    STATUS      current
    DESCRIPTION
        "The source MAC address to be filtered."
    ::= { vmapCurCfgEntry 7 }

vmapCurCfgSrcMACMask  OBJECT-TYPE
    SYNTAX      MacAddress
    MAX-ACCESS  read-only
    STATUS      current
    DESCRIPTION
        "The address mask applied to aclCurCfgSrcMACAddress for filtering."
    ::= { vmapCurCfgEntry 8 }

vmapCurCfgDstMACAddress  OBJECT-TYPE
    SYNTAX      MacAddress
    MAX-ACCESS  read-only
    STATUS      current
    DESCRIPTION
        "The destination MAC address to be filtered."
    ::= { vmapCurCfgEntry 9 }

vmapCurCfgDstMACMask  OBJECT-TYPE
    SYNTAX      MacAddress
    MAX-ACCESS  read-only
    STATUS      current
    DESCRIPTION
        "The address mask applied to aclCurCfgDstMACAddress for filtering."
    ::= { vmapCurCfgEntry 10 }

vmapCurCfgEthernetTypeName  OBJECT-TYPE
    SYNTAX      INTEGER {
                    none(0),
                    arp(1),
                    ipv4(2),
                    ipv6(3),
                    mpls(4),
                    rarp(5),
                    any(6),
                    other(7)
                }
    MAX-ACCESS  read-only
    STATUS      current
    DESCRIPTION
        "The Ethernet type to be filtered. If the value of this
        object is other(7), the value of aclNewCfgEthernetTypeValue
        indicates the ethernet type that will be filtered."
    ::= { vmapCurCfgEntry 11 }

vmapCurCfgEthernetTypeValue  OBJECT-TYPE
    SYNTAX      INTEGER (1536..65535)
    MAX-ACCESS  read-only
    STATUS      current
    DESCRIPTION
        "The Ethernet type value to be filtered. The value of this
        object is equivalent to the value of aclNewCfgEthernetTypeName
        except when the value of aclNewCfgEthernetTypeName is other(7),
        which can be any user-defined value for this object."
    ::= { vmapCurCfgEntry 12 }

vmapCurCfg8021pPriority  OBJECT-TYPE
    SYNTAX      INTEGER {
                    none(0),
                    priority0(1),
                    priority1(2),
                    priority2(3),
                    priority3(4),
                    priority4(5),
                    priority5(6),
                    priority6(7),
                    priority7(8)
                }
    MAX-ACCESS  read-only
    STATUS      current
    DESCRIPTION
        "The 802.1p priority to be filtered."
    ::= { vmapCurCfgEntry 13 }

vmapCurCfgTypeOfService  OBJECT-TYPE
    SYNTAX      DisplayString
    MAX-ACCESS  read-only
    STATUS      current
    DESCRIPTION
        "The type of service to be filtered.
         'none' for not initialised, within the
         range 0-255"
    ::= { vmapCurCfgEntry 14 }

vmapCurCfgProtocol  OBJECT-TYPE
    SYNTAX      DisplayString
    MAX-ACCESS  read-only
    STATUS      current
    DESCRIPTION
        "The protocol to be filtered.
         'none' for not initialised, within the
         range 0-255"
    ::= { vmapCurCfgEntry 15 }

vmapCurCfgSrcIPAddress  OBJECT-TYPE
    SYNTAX      IpAddress
    MAX-ACCESS  read-only
    STATUS      current
    DESCRIPTION
        "The source IP address to be filtered."
    ::= { vmapCurCfgEntry 16 }

vmapCurCfgSrcIPMask  OBJECT-TYPE
    SYNTAX      IpAddress
    MAX-ACCESS  read-only
    STATUS      current
    DESCRIPTION
        "The address mask applied to aclCurCfgSrcIPAddress for filtering."
    ::= { vmapCurCfgEntry 17 }

vmapCurCfgDstIPAddress  OBJECT-TYPE
    SYNTAX      IpAddress
    MAX-ACCESS  read-only
    STATUS      current
    DESCRIPTION
        "The destination IP address to be filtered."
    ::= { vmapCurCfgEntry 18 }

vmapCurCfgDstIPMask  OBJECT-TYPE
    SYNTAX      IpAddress
    MAX-ACCESS  read-only
    STATUS      current
    DESCRIPTION
        "The address mask applied to aclCurCfgDstIPAddress for filtering."
    ::= { vmapCurCfgEntry 19 }

vmapCurCfgSrcPort  OBJECT-TYPE
    SYNTAX      INTEGER (0..65535)
    MAX-ACCESS  read-only
    STATUS      current
    DESCRIPTION
        "The source TCP/UDP port number to be filtered."
    ::= { vmapCurCfgEntry 20 }

vmapCurCfgSrcPortMask  OBJECT-TYPE
    SYNTAX      DisplayString
    MAX-ACCESS  read-only
    STATUS      current
    DESCRIPTION
        "The mask applied to aclCurCfgSrcPort for filtering."
    ::= { vmapCurCfgEntry 21 }

vmapCurCfgDstPort  OBJECT-TYPE
    SYNTAX      INTEGER (0..65535)
    MAX-ACCESS  read-only
    STATUS      current
    DESCRIPTION
        "The destination TCP/UDP port number to be filtered."
    ::= { vmapCurCfgEntry 22 }

vmapCurCfgDstPortMask  OBJECT-TYPE
    SYNTAX      DisplayString
    MAX-ACCESS  read-only
    STATUS      current
    DESCRIPTION
        "The mask applied to aclCurCfgDstPort for filtering."
    ::= { vmapCurCfgEntry 23 }

vmapCurCfgTCPFlags  OBJECT-TYPE
    SYNTAX      BITS {
                    reserved1(0),
                    reserved2(1),
                    tcpURG(2),
                    tcpACK(3),
                    tcpPSH(4),
                    tcpRST(5),
                    tcpSYN(6),
                    tcpFIN(7)
                }
    MAX-ACCESS  read-only
    STATUS      current
    DESCRIPTION
        "The TCP flags to be filtered.
         OCTET
         xxxxxxxx
         ||||..||
         ||||..||_tcpFIN(7)
         ||||..|__tcpSYN(6)
         ||||
         ||||_____tcpACK(3)
         |||______tcpURG(2)
         ||_______reserved2(1)
         |________reserved1(0)

         where:
         - reserved1 - 0;
         - reserved2 - 0;
         - x - 0 or 1;
        "
    ::= { vmapCurCfgEntry 24 }

vmapCurCfgTCPFlagsMask  OBJECT-TYPE
    SYNTAX      BITS {
                    reserved1(0),
                    reserved2(1),
                    tcpURG(2),
                    tcpACK(3),
                    tcpPSH(4),
                    tcpRST(5),
                    tcpSYN(6),
                    tcpFIN(7)
                }
    MAX-ACCESS  read-only
    STATUS      current
    DESCRIPTION
        "The TCP flags mask.
         OCTET
         xxxxxxxx
         ||||..||
         ||||..||_tcpFIN(7)
         ||||..|__tcpSYN(6)
         ||||
         ||||_____tcpACK(3)
         |||______tcpURG(2)
         ||_______reserved2(1)
         |________reserved1(0)

         where:
         - reserved1 - 0;
         - reserved2 - 0;
         - x - 0 or 1;
        "
    ::= { vmapCurCfgEntry 25 }

vmapCurCfgEgressPorts  OBJECT-TYPE
    SYNTAX      OCTET STRING
    MAX-ACCESS  read-only
    STATUS      current
    DESCRIPTION
        "The port list in the VMAP configured for egress filtering.
         The ports are presented in bitmap format, as follows:

            OCTET 1  OCTET 2  .....
            xxxxxxxx xxxxxxxx .....
            ||    || |
            ||    || |_ port 9
            ||    ||
            ||    ||___ port 8
            ||    |____ port 7
            ||      .    .   .
            ||_________ port 2
            |__________ port 1

         where x:
            1 - the represented port is configured for filtering.
            0 - the represented port is not configured for filtering."
    ::= { vmapCurCfgEntry 26 }

vmapCurCfgStatistics  OBJECT-TYPE
    SYNTAX      INTEGER {
                    disable(0),
                    enable(1)
                }
    MAX-ACCESS  read-only
    STATUS      current
    DESCRIPTION
        "Whether statistics collection for this VMAP is enabled or not."
    ::= { vmapCurCfgEntry 27 }

vmapCurCfgMeterAction  OBJECT-TYPE
    SYNTAX      INTEGER {
					unconfigured(0),
					outdrop(1),
					outpass(2)
				}
    MAX-ACCESS  read-only
    STATUS      current
    DESCRIPTION
        "Meter Action for this VMAP."
    ::= { vmapCurCfgEntry 31 }

vmapCurCfgMeterEnable  OBJECT-TYPE
    SYNTAX      INTEGER {
	enabled(0),
	disabled(1)
				}
    MAX-ACCESS  read-only
    STATUS      current
    DESCRIPTION
        "Meter state for this VMAP."
    ::= { vmapCurCfgEntry 32 }

vmapCurCfgKbitsSec  OBJECT-TYPE
    SYNTAX      Unsigned32 (64..10000000)
    MAX-ACCESS  read-only
    STATUS      current
    DESCRIPTION
        "The commited rate of meter associated with this VMAP entry."
    ::= { vmapCurCfgEntry 33 }

vmapCurCfgKbitsBurst  OBJECT-TYPE
    SYNTAX      INTEGER {
					kbits32(32),
					kbits64(64),
					kbits128(128),
					kbits256(256),
					kbits512(512),
					kbits1024(1024),
					kbits2048(2048),
					kbits4096(4096)
   				}
	MAX-ACCESS  read-only
    STATUS      current
    DESCRIPTION
        "The maxmium burst sizeof meter associated with this VMAP entry."
    ::= { vmapCurCfgEntry 34 }

vmapCurCfgUser  OBJECT-TYPE
    SYNTAX      INTEGER (0..7)
    MAX-ACCESS  read-only
    STATUS      current
    DESCRIPTION
        "Set user defined priority for this VMAP."
    ::= { vmapCurCfgEntry 35 }

vmapCurCfgInprofDscp  OBJECT-TYPE
    SYNTAX      INTEGER (0..63)
    MAX-ACCESS  read-only
    STATUS      current
    DESCRIPTION
        "Set in profile pkts DSCP value."
    ::= { vmapCurCfgEntry 36 }

vmapCurCfgTos  OBJECT-TYPE
    SYNTAX      INTEGER {
                    disable(0),
                    enable(1)
                }
    MAX-ACCESS  read-only
    STATUS      current
    DESCRIPTION
        "To enable/disable setting pkts based on TOS bits."
    ::= { vmapCurCfgEntry 37 }

vmapCurCfgOutprofDscp  OBJECT-TYPE
    SYNTAX      INTEGER (0..63)
    MAX-ACCESS  read-only
    STATUS      current
    DESCRIPTION
        "Set out profile pkts DSCP value."
    ::= { vmapCurCfgEntry 38 }

vmapCurCfgUserEnable  OBJECT-TYPE
    SYNTAX      INTEGER {
				    disabled(0),
					userdefined(1)
				}
    MAX-ACCESS  read-only
    STATUS      current
    DESCRIPTION
        "Set update method for this VMAP."
    ::= { vmapCurCfgEntry 39 }

vmapCurCfgInprofDscpEnable  OBJECT-TYPE
    SYNTAX      INTEGER {
                    disable(0),
                    enable(1)
                }
    MAX-ACCESS  read-only
    STATUS      current
    DESCRIPTION
        "Whether in profile update DSCP for this VMAP is enabled or not."
    ::= { vmapCurCfgEntry 40 }

vmapCurCfgOutprofDscpEnable  OBJECT-TYPE
    SYNTAX      INTEGER {
                    disable(0),
                    enable(1)
                }
    MAX-ACCESS  read-only
    STATUS      current
    DESCRIPTION
        "Whether out profile update DSCP for this VMAP is enabled or not."
    ::= { vmapCurCfgEntry 41 }

vmapCurCfgMirrorPort  OBJECT-TYPE
    SYNTAX      Integer32
    MAX-ACCESS  read-only
    STATUS      current
    DESCRIPTION
        "Set port in the VMAP for mirroring.
            n > 0 - the represented port is configured for mirroring.
            0     - the represented port is not configured for mirroring."
    ::= { vmapCurCfgEntry 51 }

-- ------------------------------------------------------------------------- --
-- Current VMAP Configuration Table (end)                                  }
-- ------------------------------------------------------------------------- --

-- ------------------------------------------------------------------------- --
-- New VMAP Configuration Table                                            {
-- ------------------------------------------------------------------------- --
vmapNewCfgTable OBJECT-TYPE
    SYNTAX      SEQUENCE OF VmapNewCfgEntry
    MAX-ACCESS  not-accessible
    STATUS      current
    DESCRIPTION
        "The table of new VMAP configuration."
    ::= { vmapList 2 }

vmapNewCfgEntry OBJECT-TYPE
    SYNTAX      VmapNewCfgEntry
    MAX-ACCESS  not-accessible
    STATUS      current
    DESCRIPTION
        "New information about a particular VMAP configuration."
    INDEX { vmapNewCfgIndex }
    ::= { vmapNewCfgTable 1 }

VmapNewCfgEntry ::= SEQUENCE {
    vmapNewCfgIndex                 Unsigned32,
    vmapNewCfgFilterAction          INTEGER,
    vmapNewCfgFilterActionSetPrio   INTEGER,
    vmapNewCfgEthFmt                INTEGER,
    vmapNewCfgTagFmt                INTEGER,
    vmapNewCfgIPFmt                 INTEGER,
    vmapNewCfgSrcMACAddress         MacAddress,
    vmapNewCfgSrcMACMask            MacAddress,
    vmapNewCfgDstMACAddress         MacAddress,
    vmapNewCfgDstMACMask            MacAddress,
    vmapNewCfgEthernetTypeName      INTEGER,
    vmapNewCfgEthernetTypeValue     INTEGER,
    vmapNewCfg8021pPriority         INTEGER,
    vmapNewCfgTypeOfService         DisplayString,
    vmapNewCfgProtocol              DisplayString,
    vmapNewCfgSrcIPAddress          IpAddress,
    vmapNewCfgSrcIPMask             IpAddress,
    vmapNewCfgDstIPAddress          IpAddress,
    vmapNewCfgDstIPMask             IpAddress,
    vmapNewCfgSrcPort               INTEGER,
    vmapNewCfgSrcPortMask           DisplayString,
    vmapNewCfgDstPort               INTEGER,
    vmapNewCfgDstPortMask           DisplayString,
    vmapNewCfgTCPFlags              BITS,
    vmapNewCfgTCPFlagsMask          BITS,
    vmapNewCfgEgressPorts           OCTET STRING,
    vmapNewCfgStatistics            INTEGER,
    vmapNewCfgAddEgressPort         PortNumber,
    vmapNewCfgRemoveEgressPort      PortNumber,
    vmapNewCfgDelete                INTEGER,
    vmapNewCfgMeterAction           INTEGER,
    vmapNewCfgMeterEnable           INTEGER,
    vmapNewCfgKbitsSec              Unsigned32,
    vmapNewCfgKbitsBurst            INTEGER,
    vmapNewCfgUser 	     	    INTEGER,
    vmapNewCfgInprofDscp            INTEGER,
    vmapNewCfgTos                   INTEGER,
    vmapNewCfgOutprofDscp           INTEGER,
    vmapNewCfgUserEnable            INTEGER,
    vmapNewCfgInprofDscpEnable      INTEGER,
    vmapNewCfgOutprofDscpEnable     INTEGER,
    vmapNewCfgReset                 INTEGER
    , vmapNewCfgEthernetReset       INTEGER
    , vmapNewCfgIpv4Reset           INTEGER
    , vmapNewCfgTcpudpReset         INTEGER
    , vmapNewCfgMeterReset          INTEGER
    , vmapNewCfgRemarkReset         INTEGER
    , vmapNewCfgRemarkInprofReset   INTEGER
    , vmapNewCfgRemarkOutprofReset  INTEGER
    , vmapNewCfgPktfmtReset         INTEGER
    , vmapNewCfgMirrorPort          Integer32
    }

vmapNewCfgIndex  OBJECT-TYPE
    SYNTAX      Unsigned32
    MAX-ACCESS  read-only
    STATUS      current
    DESCRIPTION
        "The index associated with this VMAP entry."
    ::= { vmapNewCfgEntry 1 }

vmapNewCfgFilterAction  OBJECT-TYPE
    SYNTAX      INTEGER {
                    none(0),
                    permit(1),
                    deny(2),
                    setprio(3)
                }
    MAX-ACCESS  read-write
    STATUS      current
    DESCRIPTION
        "The action to be performed on a packet that matches the filter
        settings of this VMAP entry."
    ::= { vmapNewCfgEntry 2 }

vmapNewCfgFilterActionSetPrio  OBJECT-TYPE
    SYNTAX      INTEGER {
                    none(0),
                    prio0(1),
                    prio1(2),
                    prio2(3),
                    prio3(4),
                    prio4(5),
                    prio5(6),
                    prio6(7),
                    prio7(8)
                }
    MAX-ACCESS  read-write
    STATUS      current
    DESCRIPTION
        "The COS queue to be used when the action for this VMAP entry is
        set to setprio."
    ::= { vmapNewCfgEntry 3 }

vmapNewCfgEthFmt  OBJECT-TYPE
    SYNTAX      INTEGER {
                    none(0),
                    ethernet2(1),
                    snap(2),
                    llc(3)
                }
    MAX-ACCESS  read-write
    STATUS      current
    DESCRIPTION
        "The packet ethernet format to be filtered."
    ::= { vmapNewCfgEntry 4 }

vmapNewCfgTagFmt  OBJECT-TYPE
    SYNTAX      INTEGER {
                    disabled(1),
                    any(2),
                    none(3),
                    tagged(4)
                }
    MAX-ACCESS  read-write
    STATUS      current
    DESCRIPTION
        "The packet tagging format to be filtered."
    ::= { vmapNewCfgEntry 5 }

vmapNewCfgIPFmt  OBJECT-TYPE
    SYNTAX      INTEGER {
                    none(1),
                    ipv4(2),
                    ipv6(3)
                }
    MAX-ACCESS  read-write
    STATUS      current
    DESCRIPTION
        "The packet IP format to be filtered."
    ::= { vmapNewCfgEntry 6 }

vmapNewCfgSrcMACAddress  OBJECT-TYPE
    SYNTAX      MacAddress
    MAX-ACCESS  read-write
    STATUS      current
    DESCRIPTION
        "The source MAC address to be filtered. Whenever this object is
        set to a nonzero value, the aclNewCfgSrcMACMask object, if not
        yet set, will be automatically set to ff:ff:ff:ff:ff:ff."
    ::= { vmapNewCfgEntry 7 }

vmapNewCfgSrcMACMask  OBJECT-TYPE
    SYNTAX      MacAddress
    MAX-ACCESS  read-write
    STATUS      current
    DESCRIPTION
        "The address mask to be applied to aclNewCfgSrcMACAddress
         for filtering."
    ::= { vmapNewCfgEntry 8 }

vmapNewCfgDstMACAddress  OBJECT-TYPE
    SYNTAX      MacAddress
    MAX-ACCESS  read-write
    STATUS      current
    DESCRIPTION
        "The destination MAC address to be filtered. Whenever this object
        is set to a nonzero value, the aclNewCfgDstMACMask object, if not
        yet set, will be automatically set to ff:ff:ff:ff:ff:ff."
    ::= { vmapNewCfgEntry 9 }

vmapNewCfgDstMACMask  OBJECT-TYPE
    SYNTAX      MacAddress
    MAX-ACCESS  read-write
    STATUS      current
    DESCRIPTION
        "The address mask to be applied to aclNewCfgDstMACAddress
         for filtering."
    ::= { vmapNewCfgEntry 10 }

vmapNewCfgEthernetTypeName  OBJECT-TYPE
    SYNTAX      INTEGER {
                    none(0),
                    arp(1),
                    ipv4(2),
                    ipv6(3),
                    mpls(4),
                    rarp(5),
                    any(6),
                    other(7)
                }
    MAX-ACCESS  read-write
    STATUS      current
    DESCRIPTION
        "The Ethernet type to be filtered. If the value of this
        object is other(7), the value of aclNewCfgEthernetTypeValue
        indicates the ethernet type that will be filtered. If this
        object is set to a value other than other(7), the value of
        the aclNewCfgEthernetTypeValue object is automatically set,
        as follows:

        aclNewCfgEthernetTypeName   aclNewCfgEthernetTypeValue
            none(0)                         0
            arp(1)                       2054  (0x0806)
            ipv4(2)                      2048  (0x0800)
            ipv6(3)                     34525  (0x86dd)
            mpls(4)                     34887  (0x8847)
            rarp(5)                     32821  (0x8035)
            any(6)                      65535  (0xffff)
        "
    ::= { vmapNewCfgEntry 11 }

vmapNewCfgEthernetTypeValue  OBJECT-TYPE
    SYNTAX      INTEGER (1536..65535)
    MAX-ACCESS  read-write
    STATUS      current
    DESCRIPTION
        "The Ethernet type value to be filtered. The value of this
        object is equivalent to the value of aclNewCfgEthernetTypeName
        except when the value of aclNewCfgEthernetTypeName is other(7),
        which can be any user-defined value for this object."
    ::= { vmapNewCfgEntry 12 }

vmapNewCfg8021pPriority  OBJECT-TYPE
    SYNTAX      INTEGER {
                    none(0),
                    priority0(1),
                    priority1(2),
                    priority2(3),
                    priority3(4),
                    priority4(5),
                    priority5(6),
                    priority6(7),
                    priority7(8)
                }
    MAX-ACCESS  read-write
    STATUS      current
    DESCRIPTION
        "The 802.1p priority to be filtered."
    ::= { vmapNewCfgEntry 13 }

vmapNewCfgTypeOfService  OBJECT-TYPE
    SYNTAX      DisplayString
    MAX-ACCESS  read-write
    STATUS      current
    DESCRIPTION
        "The type of service to be filtered.
         'none' for not initialised, within the
         range 0-255"
    ::= { vmapNewCfgEntry 14 }

vmapNewCfgProtocol  OBJECT-TYPE
    SYNTAX	DisplayString
    MAX-ACCESS  read-write
    STATUS      current
    DESCRIPTION
        "The protocol to be filtered.
         'none' for not initialised, within the
         range 0-255"
    ::= { vmapNewCfgEntry 15 }

vmapNewCfgSrcIPAddress  OBJECT-TYPE
    SYNTAX      IpAddress
    MAX-ACCESS  read-write
    STATUS      current
    DESCRIPTION
        "The source IP address to be filtered. Whenever this object is set
        to a nonzero value, the aclNewCfgSrcIPMask object, if not yet set,
        will be automatically set to 255.255.255.255."
    ::= { vmapNewCfgEntry 16 }

vmapNewCfgSrcIPMask  OBJECT-TYPE
    SYNTAX      IpAddress
    MAX-ACCESS  read-write
    STATUS      current
    DESCRIPTION
        "The address mask to be applied to aclNewCfgSrcIPAddress
         for filtering."
    ::= { vmapNewCfgEntry 17 }

vmapNewCfgDstIPAddress  OBJECT-TYPE
    SYNTAX      IpAddress
    MAX-ACCESS  read-write
    STATUS      current
    DESCRIPTION
        "The destination IP address to be filtered. Whenever this object is set
        to a nonzero value, the aclNewCfgDstIPMask object, if not yet set,
        will be automatically set to 255.255.255.255."
    ::= { vmapNewCfgEntry 18 }

vmapNewCfgDstIPMask  OBJECT-TYPE
    SYNTAX      IpAddress
    MAX-ACCESS  read-write
    STATUS      current
    DESCRIPTION
        "The address mask to be applied to aclNewCfgDstIPAddress for filtering."
    ::= { vmapNewCfgEntry 19 }

vmapNewCfgSrcPort  OBJECT-TYPE
    SYNTAX      INTEGER (1..65535)
    MAX-ACCESS  read-write
    STATUS      current
    DESCRIPTION
        "The source TCP/UDP port number to be filtered. Whenever this
        object is set if the aclNewCfgSrcPortMask object is not set
        will be automatically set to 65535 (0xffff)."
    ::= { vmapNewCfgEntry 20 }

vmapNewCfgSrcPortMask  OBJECT-TYPE
    SYNTAX      DisplayString
    MAX-ACCESS  read-write
    STATUS      current
    DESCRIPTION
        "The mask to be applied to aclNewCfgSrcPort for filtering."
    ::= { vmapNewCfgEntry 21 }

vmapNewCfgDstPort  OBJECT-TYPE
    SYNTAX      INTEGER (1..65535)
    MAX-ACCESS  read-write
    STATUS      current
    DESCRIPTION
        "The destination TCP/UDP port number to be filtered.  Whenever this
        object is set the aclNewCfgSrcPortMask object, if not yet set, will
	be automatically set to 65535 (0xffff)."
    ::= { vmapNewCfgEntry 22 }

vmapNewCfgDstPortMask  OBJECT-TYPE
    SYNTAX      DisplayString
    MAX-ACCESS  read-write
    STATUS      current
    DESCRIPTION
        "The mask to be applied to aclNewCfgDstPort for filtering."
    ::= { vmapNewCfgEntry 23 }

vmapNewCfgTCPFlags  OBJECT-TYPE
    SYNTAX     BITS {
                    reserved1(0),
                    reserved2(1),
                    tcpURG(2),
                    tcpACK(3),
                    tcpPSH(4),
                    tcpRST(5),
                    tcpSYN(6),
                    tcpFIN(7)
                }
    MAX-ACCESS  read-write
    STATUS      current
    DESCRIPTION
        "The TCP flags to be filtered.
         The TCP flags are presented in bitmap format, as follows:
         OCTET
         xxxxxxxx
         ||||..||
         ||||..||_tcpFIN(7)
         ||||..|__tcpSYN(6)
         ||||
         ||||_____tcpACK(3)
         |||______tcpURG(2)
         ||_______reserved2(1)
         |________reserved1(0)

         where:
         - reserved1 - 0;
         - reserved2 - 0;
         - x - 0 or 1;
        "

    ::= { vmapNewCfgEntry 24 }

vmapNewCfgTCPFlagsMask  OBJECT-TYPE
    SYNTAX      BITS {
                    reserved1(0),
                    reserved2(1),
                    tcpURG(2),
                    tcpACK(3),
                    tcpPSH(4),
                    tcpRST(5),
                    tcpSYN(6),
                    tcpFIN(7)
                }
    MAX-ACCESS  read-write
    STATUS      current
    DESCRIPTION
        "The TCP flags mask.
         The TCP flags are presented in bitmap format, as follows:
         OCTET
         xxxxxxxx
         ||||..||
         ||||..||_tcpFIN(7)
         ||||..|__tcpSYN(6)
         ||||
         ||||_____tcpACK(3)
         |||______tcpURG(2)
         ||_______reserved2(1)
         |________reserved1(0)

         where:
         - reserved1 - 0;
         - reserved2 - 0;
         - x - 0 or 1;
         Default value is 0x3f."
    ::= { vmapNewCfgEntry 25 }

vmapNewCfgEgressPorts  OBJECT-TYPE
    SYNTAX      OCTET STRING
    MAX-ACCESS  read-only
    STATUS      current
    DESCRIPTION
        "The port list in the VMAP configured for egress filtering.
         The ports are presented in bitmap format, as follows:

            OCTET 1  OCTET 2  .....
            xxxxxxxx xxxxxxxx .....
            ||    || |
            ||    || |_ port 9
            ||    ||
            ||    ||___ port 8
            ||    |____ port 7
            ||      .    .   .
            ||_________ port 2
            |__________ port 1

         where x:
            1 - the represented port is configured for filtering.
            0 - the represented port is not configured for filtering."
    ::= { vmapNewCfgEntry 26 }

vmapNewCfgStatistics  OBJECT-TYPE
    SYNTAX      INTEGER {
                    disable(0),
                    enable(1)
                }
    MAX-ACCESS  read-write
    STATUS      current
    DESCRIPTION
        "Whether statistics collection for this VMAP is enabled or not."
    ::= { vmapNewCfgEntry 27 }

vmapNewCfgAddEgressPort OBJECT-TYPE
    SYNTAX      PortNumber
    MAX-ACCESS  read-write
    STATUS      current
    DESCRIPTION
        "The port to be added to the specified VMAP for egress filtering.
        A value of zero is always returned when this object is read."
    ::= { vmapNewCfgEntry 28 }

vmapNewCfgRemoveEgressPort OBJECT-TYPE
    SYNTAX      PortNumber
    MAX-ACCESS  read-write
    STATUS      current
    DESCRIPTION
        "The port to be removed from the specified VMAP.  A value of zero
        is always returned when this object is read."
    ::= { vmapNewCfgEntry 29 }

vmapNewCfgDelete OBJECT-TYPE
    SYNTAX      INTEGER {
                    other(1),
                    delete(2)
                }
    MAX-ACCESS  read-write
    STATUS      current
    DESCRIPTION
        "This is an action object to delete an VMAP entry.  A value of
        other(1) is always returned when this object is read."
    ::= { vmapNewCfgEntry 30 }

vmapNewCfgMeterAction  OBJECT-TYPE
    SYNTAX      INTEGER {
					unconfigured(0),
					outdrop(1),
					outpass(2)
				}
    MAX-ACCESS  read-write
    STATUS      current
    DESCRIPTION
        "Meter Action for this VMAP."
    ::= { vmapNewCfgEntry 31 }

vmapNewCfgMeterEnable  OBJECT-TYPE
    SYNTAX      INTEGER {
	enabled(0),
	disabled(1)
				}
    MAX-ACCESS  read-write
    STATUS      current
    DESCRIPTION
        "Meter state for this VMAP."
    ::= { vmapNewCfgEntry 32 }

vmapNewCfgKbitsSec  OBJECT-TYPE
    SYNTAX      Unsigned32 (64..10000000)
    MAX-ACCESS  read-write
    STATUS      current
    DESCRIPTION
        "The commited rate of meter associated with this VMAP entry."
    ::= { vmapNewCfgEntry 33 }

vmapNewCfgKbitsBurst  OBJECT-TYPE
    SYNTAX      INTEGER {
					kbits32(32),
					kbits64(64),
					kbits128(128),
					kbits256(256),
					kbits512(512),
					kbits1024(1024),
					kbits2048(2048),
					kbits4096(4096)
   				}
    MAX-ACCESS  read-write
    STATUS      current
    DESCRIPTION
        "The maximum burst size of the meter associated with this VMAP entry."
    ::= { vmapNewCfgEntry 34 }

vmapNewCfgUser  OBJECT-TYPE
    SYNTAX      INTEGER (0..7)
    MAX-ACCESS  read-write
    STATUS      current
    DESCRIPTION
        "Set user defined priority for this VMAP."
    ::= { vmapNewCfgEntry 35 }

vmapNewCfgInprofDscp  OBJECT-TYPE
    SYNTAX      INTEGER (0..63)
    MAX-ACCESS  read-write
    STATUS      current
    DESCRIPTION
        "Set in profile pkts DSCP value."
    ::= { vmapNewCfgEntry 36 }

vmapNewCfgTos  OBJECT-TYPE
    SYNTAX      INTEGER {
                    disable(0),
                    enable(1)
                }
    MAX-ACCESS  read-write
    STATUS      current
    DESCRIPTION
        "To enable/disable setting pkts based on TOS bits."
    ::= { vmapNewCfgEntry 37 }

vmapNewCfgOutprofDscp  OBJECT-TYPE
    SYNTAX      INTEGER (0..63)
    MAX-ACCESS  read-write
    STATUS      current
    DESCRIPTION
        "Set out profile pkts DSCP value."
    ::= { vmapNewCfgEntry 38 }

vmapNewCfgUserEnable  OBJECT-TYPE
    SYNTAX      INTEGER {
				    disabled(0),
					userdefined(1)
				}
    MAX-ACCESS  read-write
    STATUS      current
    DESCRIPTION
        "Set update method for this VMAP."
    ::= { vmapNewCfgEntry 39 }

vmapNewCfgInprofDscpEnable  OBJECT-TYPE
    SYNTAX      INTEGER {
                    disable(0),
                    enable(1)
                }
    MAX-ACCESS  read-write
    STATUS      current
    DESCRIPTION
        "Whether in profile update DSCP for this VMAP is enabled or not.
         Only the value disable(0) can be set, causing the in profile
         update DSCP to be disabled for this VMAP.
         The value enable(1) is automatically set when setting a value
         for aclNewCfgInprofDscp object."
    ::= { vmapNewCfgEntry 40 }

vmapNewCfgOutprofDscpEnable  OBJECT-TYPE
    SYNTAX      INTEGER {
                    disable(0),
                    enable(1)
                }
    MAX-ACCESS  read-write
    STATUS      current
    DESCRIPTION
        "Whether out profile update DSCP for this VMAP is enabled or not.
         Only the value disable(0) can be set, causing the out profile
         update DSCP to be disabled for this VMAP.
         The value enable(1) is automatically set when setting a value
         for aclNewCfgOutprofDscp object."
    ::= { vmapNewCfgEntry 41 }

vmapNewCfgReset OBJECT-TYPE
    SYNTAX      INTEGER {
                    other(1),
                    reset(2)
                }
    MAX-ACCESS  read-write
    STATUS      current
    DESCRIPTION
        "This is an action object to reset an VMAP entry. A value of
        other(1) is always returned when this object is read."
    ::= { vmapNewCfgEntry 42 }

vmapNewCfgEthernetReset OBJECT-TYPE
    SYNTAX      INTEGER {
                    other(1),
                    reset(2)
                }
    MAX-ACCESS  read-write
    STATUS      current
    DESCRIPTION
        "This is an action object to reset an VMAP Ethernet entry. A value of
        other(1) is always returned when this object is read."
    ::= { vmapNewCfgEntry 43 }

vmapNewCfgIpv4Reset OBJECT-TYPE
    SYNTAX      INTEGER {
                    other(1),
                    reset(2)
                }
    MAX-ACCESS  read-write
    STATUS      current
    DESCRIPTION
        "This is an action object to reset an VMAP IPV4 entry. A value of
        other(1) is always returned when this object is read."
    ::= { vmapNewCfgEntry 44 }

vmapNewCfgTcpudpReset OBJECT-TYPE
    SYNTAX      INTEGER {
                    other(1),
                    reset(2)
                }
    MAX-ACCESS  read-write
    STATUS      current
    DESCRIPTION
        "This is an action object to reset an VMAP Tcpudp entry. A value of
        other(1) is always returned when this object is read."
    ::= { vmapNewCfgEntry 45 }

vmapNewCfgMeterReset OBJECT-TYPE
    SYNTAX      INTEGER {
                    other(1),
                    reset(2)
                }
    MAX-ACCESS  read-write
    STATUS      current
    DESCRIPTION
        "This is an action object to reset an VMAP Meter entry. A value of
        other(1) is always returned when this object is read."
    ::= { vmapNewCfgEntry 46 }

vmapNewCfgRemarkReset OBJECT-TYPE
    SYNTAX      INTEGER {
                    other(1),
                    reset(2)
                }
    MAX-ACCESS  read-write
    STATUS      current
    DESCRIPTION
        "This is an action object to reset an VMAP Remark entry. A value of
        other(1) is always returned when this object is read."
    ::= { vmapNewCfgEntry 47 }

vmapNewCfgRemarkInprofReset OBJECT-TYPE
    SYNTAX      INTEGER {
                    other(1),
                    reset(2)
                }
    MAX-ACCESS  read-write
    STATUS      current
    DESCRIPTION
        "This is an action object to reset an VMAP Remark Inprof entry. A value of
        other(1) is always returned when this object is read."
    ::= { vmapNewCfgEntry 48 }

vmapNewCfgRemarkOutprofReset OBJECT-TYPE
    SYNTAX      INTEGER {
                    other(1),
                    reset(2)
                }
    MAX-ACCESS  read-write
    STATUS      current
    DESCRIPTION
        "This is an action object to reset an VMAP Remark Outprof entry. A value of
        other(1) is always returned when this object is read."
    ::= { vmapNewCfgEntry 49 }

vmapNewCfgPktfmtReset OBJECT-TYPE
    SYNTAX      INTEGER {
                    other(1),
                    reset(2)
                }
    MAX-ACCESS  read-write
    STATUS      current
    DESCRIPTION
        "This is an action object to reset an VMAP Pktfmt entry. A value of
        other(1) is always returned when this object is read."
    ::= { vmapNewCfgEntry 50 }

vmapNewCfgMirrorPort  OBJECT-TYPE
    SYNTAX  Integer32
    MAX-ACCESS  read-write
    STATUS  current
    DESCRIPTION
        "Set port in the VMAP for mirroring.
            n > 0 - the represented port is configured for mirroring.
            0     - the represented port is not configured for mirroring."
    ::= { vmapNewCfgEntry 51 }



-- ------------------------------------------------------------------------- --
-- New VMAP Configuration Table (end)                                      }
-- ------------------------------------------------------------------------- --

-- ------------------------------------------------------------------------- --
-- Current VLAN VMAP Non-Server Ports Configuration Table                    {
-- ------------------------------------------------------------------------- --
vmapVlanCurCfgNonServerPortsTable OBJECT-TYPE
    SYNTAX          SEQUENCE OF VmapVlanCurCfgNonServerPortsTableEntry
    MAX-ACCESS      not-accessible
    STATUS          current
    DESCRIPTION
        "The table of the current configuration
         of vmaps for the non-server ports of vlans."
    ::= { vmapVlanCfgNonServerPorts 1 }

vmapVlanCurCfgNonServerPortsTableEntry    OBJECT-TYPE
    SYNTAX          VmapVlanCurCfgNonServerPortsTableEntry
    MAX-ACCESS      not-accessible
    STATUS          current
    DESCRIPTION
        "A row in the table of current configuration
         of vmaps for the non-server ports of vlans."
    INDEX { vmapVlanCurCfgNonServerPortsVlanIdx }
    ::= { vmapVlanCurCfgNonServerPortsTable 1 }

VmapVlanCurCfgNonServerPortsTableEntry ::= SEQUENCE {
    vmapVlanCurCfgNonServerPortsVlanIdx       Integer32,
    vmapVlanCurCfgNonServerPortsVmapBitmap    OCTET STRING
    }

vmapVlanCurCfgNonServerPortsVlanIdx   OBJECT-TYPE
    SYNTAX          Integer32
    MAX-ACCESS      read-only
    STATUS          current
    DESCRIPTION
        "The vlan id in the table of configured
         vmaps for the non-server ports of vlan"
    ::= { vmapVlanCurCfgNonServerPortsTableEntry 1 }

vmapVlanCurCfgNonServerPortsVmapBitmap    OBJECT-TYPE
    SYNTAX          OCTET STRING
    MAX-ACCESS      read-only
    STATUS          current
    DESCRIPTION
        "The bitmap of vmaps configured for the non-server
         ports of the vlan given as arguments.
         The vmaps are presented in bitmap format in receiving order:

             OCTET 1  OCTET 2  .....
             xxxxxxxx xxxxxxxx .....
             ||    || |_ vmap 9
             ||    ||
             ||    ||___ vmap 8
             ||    |____ vmap 7
             ||      .    .   .
             ||_________ vmap 2
             |__________ vmap 1

         where x : 1 - The represented vmap is active in
                       the specified context
                   0 - The represented vmap is NOT active
                       in the specified context"
    ::= { vmapVlanCurCfgNonServerPortsTableEntry 2 }
-- ------------------------------------------------------------------------- --
-- Current VLAN VMAP Non-Server Ports Configuration Table (end)              }
-- ------------------------------------------------------------------------- --

-- ------------------------------------------------------------------------- --
-- New VLAN VMAP Non Server Ports Configuration Table                        {
-- ------------------------------------------------------------------------- --
vmapVlanNewCfgNonServerPortsTable OBJECT-TYPE
    SYNTAX          SEQUENCE OF VmapVlanNewCfgNonServerPortsTableEntry
    MAX-ACCESS      not-accessible
    STATUS          current
    DESCRIPTION
        "The table of the new configuration
         of vmaps for non-server ports of vlans."
    ::= { vmapVlanCfgNonServerPorts 2 }

vmapVlanNewCfgNonServerPortsTableEntry    OBJECT-TYPE
    SYNTAX          VmapVlanNewCfgNonServerPortsTableEntry
    MAX-ACCESS      not-accessible
    STATUS          current
    DESCRIPTION
        "A row in the table of new configuration
         of vmaps for the non-server ports of vlans."
    INDEX { vmapVlanNewCfgNonServerPortsVlanIdx }
    ::= { vmapVlanNewCfgNonServerPortsTable 1 }

VmapVlanNewCfgNonServerPortsTableEntry ::= SEQUENCE {
    vmapVlanNewCfgNonServerPortsVlanIdx       Integer32,
    vmapVlanNewCfgNonServerPortsVmapBitmap    OCTET STRING,
    vmapVlanNewCfgNonServerPortsAddVmap       Unsigned32,
    vmapVlanNewCfgNonServerPortsRemVmap       Unsigned32
    }

vmapVlanNewCfgNonServerPortsVlanIdx   OBJECT-TYPE
    SYNTAX          Integer32
    MAX-ACCESS      read-only
    STATUS          current
    DESCRIPTION
        "The vlan id in the table of configured
         vmaps for the non-server ports of vlan"
    ::= { vmapVlanNewCfgNonServerPortsTableEntry 1 }

vmapVlanNewCfgNonServerPortsVmapBitmap    OBJECT-TYPE
    SYNTAX          OCTET STRING
    MAX-ACCESS      read-only
    STATUS          current
    DESCRIPTION
        "The bitmap of vmaps configured for the non-server
         ports of the vlan given as arguments.
         The vmaps are presented in bitmap format in receiving order:

             OCTET 1  OCTET 2  .....
             xxxxxxxx xxxxxxxx .....
             ||    || |_ vmap 9
             ||    ||
             ||    ||___ vmap 8
             ||    |____ vmap 7
             ||      .    .   .
             ||_________ vmap 2
             |__________ vmap 1

         where x : 1 - The represented vmap is active in
                       the specified context
                   0 - The represented vmap is NOT active
                       in the specified context"
    ::= { vmapVlanNewCfgNonServerPortsTableEntry 2 }

vmapVlanNewCfgNonServerPortsAddVmap   OBJECT-TYPE
    SYNTAX          Unsigned32
    MAX-ACCESS      read-write
    STATUS          current
    DESCRIPTION
        "Add a new vmap to the non-server ports of the vlan"
    ::= { vmapVlanNewCfgNonServerPortsTableEntry 3 }

vmapVlanNewCfgNonServerPortsRemVmap   OBJECT-TYPE
    SYNTAX          Unsigned32
    MAX-ACCESS      read-write
    STATUS          current
    DESCRIPTION
        "Remove a vmap from the non-server ports of the vlan"
    ::= { vmapVlanNewCfgNonServerPortsTableEntry 4 }
-- ------------------------------------------------------------------------- --
-- New VLAN VMAP Non-server Ports Configuration Table (end)                  }
-- ------------------------------------------------------------------------- --

-- ------------------------------------------------------------------------- --
-- Current VLAN VMAP Internal Ports Configuration Table                    {
-- ------------------------------------------------------------------------- --
vmapVlanCurCfgServerPortsTable OBJECT-TYPE
    SYNTAX          SEQUENCE OF VmapVlanCurCfgServerPortsTableEntry
    MAX-ACCESS      not-accessible
    STATUS          current
    DESCRIPTION
        "The table of the current configuration
         of vmaps for server ports of vlans."
    ::= { vmapVlanCfgServerPorts 1 }

vmapVlanCurCfgServerPortsTableEntry    OBJECT-TYPE
    SYNTAX          VmapVlanCurCfgServerPortsTableEntry
    MAX-ACCESS      not-accessible
    STATUS          current
    DESCRIPTION
        "A row in the table of current configuration
         of vmaps for the server ports of vlans."
    INDEX { vmapVlanCurCfgServerPortsVlanIdx }
    ::= { vmapVlanCurCfgServerPortsTable 1 }

VmapVlanCurCfgServerPortsTableEntry ::= SEQUENCE {
    vmapVlanCurCfgServerPortsVlanIdx       Integer32,
    vmapVlanCurCfgServerPortsVmapBitmap    OCTET STRING
    }

vmapVlanCurCfgServerPortsVlanIdx   OBJECT-TYPE
    SYNTAX          Integer32
    MAX-ACCESS      read-only
    STATUS          current
    DESCRIPTION
        "The vlan id in the table of configured
         vmaps for the server ports of vlan"
    ::= { vmapVlanCurCfgServerPortsTableEntry 1 }

vmapVlanCurCfgServerPortsVmapBitmap    OBJECT-TYPE
    SYNTAX          OCTET STRING
    MAX-ACCESS      read-only
    STATUS          current
    DESCRIPTION
        "The bitmap of vmaps configured for the server
         ports of the vlan given as arguments.
         The vmaps are presented in bitmap format in receiving order:

             OCTET 1  OCTET 2  .....
             xxxxxxxx xxxxxxxx .....
             ||    || |_ vmap 9
             ||    ||
             ||    ||___ vmap 8
             ||    |____ vmap 7
             ||      .    .   .
             ||_________ vmap 2
             |__________ vmap 1

         where x : 1 - The represented vmap is active in
                       the specified context
                   0 - The represented vmap is NOT active
                       in the specified context"
    ::= { vmapVlanCurCfgServerPortsTableEntry 2 }
-- ------------------------------------------------------------------------- --
-- Current VLAN VMAP Server Ports Configuration Table (end)              }
-- ------------------------------------------------------------------------- --

-- ------------------------------------------------------------------------- --
-- New VLAN VMAP Server Ports Configuration Table                        {
-- ------------------------------------------------------------------------- --
vmapVlanNewCfgServerPortsTable OBJECT-TYPE
    SYNTAX          SEQUENCE OF VmapVlanNewCfgServerPortsTableEntry
    MAX-ACCESS      not-accessible
    STATUS          current
    DESCRIPTION
        "The table of the new configuration
         of vmaps for server ports of vlans."
    ::= { vmapVlanCfgServerPorts 2 }

vmapVlanNewCfgServerPortsTableEntry    OBJECT-TYPE
    SYNTAX          VmapVlanNewCfgServerPortsTableEntry
    MAX-ACCESS      not-accessible
    STATUS          current
    DESCRIPTION
        "A row in the table of new configuration
         of vmaps for the server ports of vlans."
    INDEX { vmapVlanNewCfgServerPortsVlanIdx }
    ::= { vmapVlanNewCfgServerPortsTable 1 }

VmapVlanNewCfgServerPortsTableEntry ::= SEQUENCE {
    vmapVlanNewCfgServerPortsVlanIdx       Integer32,
    vmapVlanNewCfgServerPortsVmapBitmap    OCTET STRING,
    vmapVlanNewCfgServerPortsAddVmap       Unsigned32,
    vmapVlanNewCfgServerPortsRemVmap       Unsigned32
    }

vmapVlanNewCfgServerPortsVlanIdx   OBJECT-TYPE
    SYNTAX          Integer32
    MAX-ACCESS      read-only
    STATUS          current
    DESCRIPTION
        "The vlan id in the table of configured
         vmaps for the server ports of vlan"
    ::= { vmapVlanNewCfgServerPortsTableEntry 1 }

vmapVlanNewCfgServerPortsVmapBitmap    OBJECT-TYPE
    SYNTAX          OCTET STRING
    MAX-ACCESS      read-only
    STATUS          current
    DESCRIPTION
        "The bitmap of vmaps configured for the server
         ports of the vlan given as arguments.
         The vmaps are presented in bitmap format in receiving order:

             OCTET 1  OCTET 2  .....
             xxxxxxxx xxxxxxxx .....
             ||    || |_ vmap 9
             ||    ||
             ||    ||___ vmap 8
             ||    |____ vmap 7
             ||      .    .   .
             ||_________ vmap 2
             |__________ vmap 1

         where x : 1 - The represented vmap is active in
                       the specified context
                   0 - The represented vmap is NOT active
                       in the specified context"
    ::= { vmapVlanNewCfgServerPortsTableEntry 2 }

vmapVlanNewCfgServerPortsAddVmap   OBJECT-TYPE
    SYNTAX          Unsigned32
    MAX-ACCESS      read-write
    STATUS          current
    DESCRIPTION
        "Add a new vmap to the server ports of the vlan"
    ::= { vmapVlanNewCfgServerPortsTableEntry 3 }

vmapVlanNewCfgServerPortsRemVmap   OBJECT-TYPE
    SYNTAX          Unsigned32
    MAX-ACCESS      read-write
    STATUS          current
    DESCRIPTION
        "Remove a vmap from the server ports of the vlan"
    ::= { vmapVlanNewCfgServerPortsTableEntry 4 }
-- ------------------------------------------------------------------------- --
-- New VLAN VMAP Server Ports Configuration Table (end)                  }
-- ------------------------------------------------------------------------- --


-- ------------------------------------------------------------------------- --
-- Current VLAN VMAP All Ports Configuration Table                         {
-- ------------------------------------------------------------------------- --
vmapVlanCurCfgAllPortsTable OBJECT-TYPE
    SYNTAX          SEQUENCE OF VmapVlanCurCfgAllPortsTableEntry
    MAX-ACCESS      not-accessible
    STATUS          current
    DESCRIPTION
        "The table of the current configuration
         of vmaps for all ports of vlans."
    ::= { vmapVlanCfgAllPorts 1 }

vmapVlanCurCfgAllPortsTableEntry    OBJECT-TYPE
    SYNTAX          VmapVlanCurCfgAllPortsTableEntry
    MAX-ACCESS      not-accessible
    STATUS          current
    DESCRIPTION
        "A row in the table of current configuration
         of vmaps for all ports of vlans."
    INDEX { vmapVlanCurCfgAllPortsVlanIdx }
    ::= { vmapVlanCurCfgAllPortsTable 1 }

VmapVlanCurCfgAllPortsTableEntry ::= SEQUENCE {
    vmapVlanCurCfgAllPortsVlanIdx       Integer32,
    vmapVlanCurCfgAllPortsVmapBitmap    OCTET STRING
    }

vmapVlanCurCfgAllPortsVlanIdx   OBJECT-TYPE
    SYNTAX          Integer32
    MAX-ACCESS      read-only
    STATUS          current
    DESCRIPTION
        "The vlan id in the table of configured
         vmaps for all ports of vlan"
    ::= { vmapVlanCurCfgAllPortsTableEntry 1 }

vmapVlanCurCfgAllPortsVmapBitmap    OBJECT-TYPE
    SYNTAX          OCTET STRING
    MAX-ACCESS      read-only
    STATUS          current
    DESCRIPTION
        "The bitmap of vmaps configured for the internal
         ports of the vlan given as arguments.
         The vmaps are presented in bitmap format in receiving order:

             OCTET 1  OCTET 2  .....
             xxxxxxxx xxxxxxxx .....
             ||    || |_ vmap 9
             ||    ||
             ||    ||___ vmap 8
             ||    |____ vmap 7
             ||      .    .   .
             ||_________ vmap 2
             |__________ vmap 1

         where x : 1 - The represented vmap is active in
                       the specified context
                   0 - The represented vmap is NOT active
                       in the specified context"
    ::= { vmapVlanCurCfgAllPortsTableEntry 2 }
-- ------------------------------------------------------------------------- --
-- Current VLAN VMAP All Ports Configuration Table (end)                   }
-- ------------------------------------------------------------------------- --

-- ------------------------------------------------------------------------- --
-- New VLAN VMAP All Ports Configuration Table                             {
-- ------------------------------------------------------------------------- --
vmapVlanNewCfgAllPortsTable OBJECT-TYPE
    SYNTAX          SEQUENCE OF VmapVlanNewCfgAllPortsTableEntry
    MAX-ACCESS      not-accessible
    STATUS          current
    DESCRIPTION
        "The table of the new configuration
         of vmaps for all ports of vlans."
    ::= { vmapVlanCfgAllPorts 2 }

vmapVlanNewCfgAllPortsTableEntry    OBJECT-TYPE
    SYNTAX          VmapVlanNewCfgAllPortsTableEntry
    MAX-ACCESS      not-accessible
    STATUS          current
    DESCRIPTION
        "A row in the table of new configuration
         of vmaps for all ports of vlans."
    INDEX { vmapVlanNewCfgAllPortsVlanIdx }
    ::= { vmapVlanNewCfgAllPortsTable 1 }

VmapVlanNewCfgAllPortsTableEntry ::= SEQUENCE {
    vmapVlanNewCfgAllPortsVlanIdx       Integer32,
    vmapVlanNewCfgAllPortsVmapBitmap    OCTET STRING,
    vmapVlanNewCfgAllPortsAddVmap       Unsigned32,
    vmapVlanNewCfgAllPortsRemVmap       Unsigned32
    }

vmapVlanNewCfgAllPortsVlanIdx   OBJECT-TYPE
    SYNTAX          Integer32
    MAX-ACCESS      read-only
    STATUS          current
    DESCRIPTION
        "The vlan id in the table of configured
         vmaps for all ports of vlan"
    ::= { vmapVlanNewCfgAllPortsTableEntry 1 }

vmapVlanNewCfgAllPortsVmapBitmap    OBJECT-TYPE
    SYNTAX          OCTET STRING
    MAX-ACCESS      read-only
    STATUS          current
    DESCRIPTION
        "The bitmap of vmaps configured for the internal
         ports of the vlan given as arguments.
         The vmaps are presented in bitmap format in receiving order:

             OCTET 1  OCTET 2  .....
             xxxxxxxx xxxxxxxx .....
             ||    || |_ vmap 9
             ||    ||
             ||    ||___ vmap 8
             ||    |____ vmap 7
             ||      .    .   .
             ||_________ vmap 2
             |__________ vmap 1

         where x : 1 - The represented vmap is active in
                       the specified context
                   0 - The represented vmap is NOT active
                       in the specified context"
    ::= { vmapVlanNewCfgAllPortsTableEntry 2 }

vmapVlanNewCfgAllPortsAddVmap   OBJECT-TYPE
    SYNTAX          Unsigned32
    MAX-ACCESS      read-write
    STATUS          current
    DESCRIPTION
        "Add a new vmap to all ports of the vlan"
    ::= { vmapVlanNewCfgAllPortsTableEntry 3 }

vmapVlanNewCfgAllPortsRemVmap   OBJECT-TYPE
    SYNTAX          Unsigned32
    MAX-ACCESS      read-write
    STATUS          current
    DESCRIPTION
        "Remove a vmap from all vlan ports"
    ::= { vmapVlanNewCfgAllPortsTableEntry 4 }
-- ------------------------------------------------------------------------- --
-- New VLAN VMAP All Ports Configuration Table (end)                       }
-- ------------------------------------------------------------------------- --

-- ------------------------------------------------------------------------- --
-- Current GROUP VMAP Non-server Ports Configuration Table                   {
-- ------------------------------------------------------------------------- --
vmapGroupCurCfgNonServerPortsTable    OBJECT-TYPE
    SYNTAX          SEQUENCE OF VmapGroupCurCfgNonServerPortsTableEntry
    MAX-ACCESS      not-accessible
    STATUS          current
    DESCRIPTION
        "The table of the current configuration
         of vmaps for non-server ports of vm groups."
    ::= { vmapGroupCfgNonServerPorts 1 }

vmapGroupCurCfgNonServerPortsTableEntry   OBJECT-TYPE
    SYNTAX          VmapGroupCurCfgNonServerPortsTableEntry
    MAX-ACCESS      not-accessible
    STATUS          current
    DESCRIPTION
        "A row in the table of current configuration
         of vmaps for the non-server ports of vm groups."
    INDEX { vmapGroupCurCfgNonServerPortsGroupIdx }
    ::= { vmapGroupCurCfgNonServerPortsTable 1 }

VmapGroupCurCfgNonServerPortsTableEntry ::= SEQUENCE {
    vmapGroupCurCfgNonServerPortsGroupIdx      Integer32,
    vmapGroupCurCfgNonServerPortsVmapBitmap    OCTET STRING
    }

vmapGroupCurCfgNonServerPortsGroupIdx     OBJECT-TYPE
    SYNTAX          Integer32
    MAX-ACCESS      read-only
    STATUS          current
    DESCRIPTION
        "The vm group id in the table of configured
         vmaps for the non-server ports of vm group"
    ::= { vmapGroupCurCfgNonServerPortsTableEntry 1 }

vmapGroupCurCfgNonServerPortsVmapBitmap   OBJECT-TYPE
    SYNTAX          OCTET STRING
    MAX-ACCESS      read-only
    STATUS          current
    DESCRIPTION
        "The bitmap of vmaps configured for the non-server
         ports of the vm group given as arguments.
         The vmaps are presented in bitmap format in receiving order:

             OCTET 1  OCTET 2  .....
             xxxxxxxx xxxxxxxx .....
             ||    || |_ vmap 9
             ||    ||
             ||    ||___ vmap 8
             ||    |____ vmap 7
             ||      .    .   .
             ||_________ vmap 2
             |__________ vmap 1

         where x : 1 - The represented vmap is active in
                       the specified context
                   0 - The represented vmap is NOT active
                       in the specified context"
    ::= { vmapGroupCurCfgNonServerPortsTableEntry 2 }
-- ------------------------------------------------------------------------- --
-- Current GROUP VMAP NonServerernal Ports Configuration Table (end)             }
-- ------------------------------------------------------------------------- --

-- ------------------------------------------------------------------------- --
-- New GROUP VMAP NonServerernal Ports Configuration Table                       {
-- ------------------------------------------------------------------------- --
vmapGroupNewCfgNonServerPortsTable    OBJECT-TYPE
    SYNTAX          SEQUENCE OF VmapGroupNewCfgNonServerPortsTableEntry
    MAX-ACCESS      not-accessible
    STATUS          current
    DESCRIPTION
        "The table of the new configuration
         of vmaps for non-server ports of vm groups."
    ::= { vmapGroupCfgNonServerPorts 2 }

vmapGroupNewCfgNonServerPortsTableEntry   OBJECT-TYPE
    SYNTAX          VmapGroupNewCfgNonServerPortsTableEntry
    MAX-ACCESS      not-accessible
    STATUS          current
    DESCRIPTION
        "A row in the table of new configuration
         of vmaps for the non-server ports of vm groups."
    INDEX { vmapGroupNewCfgNonServerPortsGroupIdx }
    ::= { vmapGroupNewCfgNonServerPortsTable 1 }

VmapGroupNewCfgNonServerPortsTableEntry ::= SEQUENCE {
    vmapGroupNewCfgNonServerPortsGroupIdx      Integer32,
    vmapGroupNewCfgNonServerPortsVmapBitmap    OCTET STRING,
    vmapGroupNewCfgNonServerPortsAddVmap       Unsigned32,
    vmapGroupNewCfgNonServerPortsRemVmap       Unsigned32
    }

vmapGroupNewCfgNonServerPortsGroupIdx     OBJECT-TYPE
    SYNTAX          Integer32
    MAX-ACCESS      read-only
    STATUS          current
    DESCRIPTION
        "The vm group id in the table of configured
         vmaps for the non-server ports of vm group"
    ::= { vmapGroupNewCfgNonServerPortsTableEntry 1 }

vmapGroupNewCfgNonServerPortsVmapBitmap   OBJECT-TYPE
    SYNTAX          OCTET STRING
    MAX-ACCESS      read-only
    STATUS          current
    DESCRIPTION
        "The bitmap of vmaps configured for the non-server
         ports of the vm group given as arguments.
         The vmaps are presented in bitmap format in receiving order:

             OCTET 1  OCTET 2  .....
             xxxxxxxx xxxxxxxx .....
             ||    || |_ vmap 9
             ||    ||
             ||    ||___ vmap 8
             ||    |____ vmap 7
             ||      .    .   .
             ||_________ vmap 2
             |__________ vmap 1

         where x : 1 - The represented vmap is active in
                       the specified context
                   0 - The represented vmap is NOT active
                       in the specified context"
    ::= { vmapGroupNewCfgNonServerPortsTableEntry 2 }

vmapGroupNewCfgNonServerPortsAddVmap      OBJECT-TYPE
    SYNTAX          Unsigned32
    MAX-ACCESS      read-write
    STATUS          current
    DESCRIPTION
        "Add a new vmap to the non-server ports of the vm group"
    ::= { vmapGroupNewCfgNonServerPortsTableEntry 3 }

vmapGroupNewCfgNonServerPortsRemVmap      OBJECT-TYPE
    SYNTAX          Unsigned32
    MAX-ACCESS      read-write
    STATUS          current
    DESCRIPTION
        "Remove a vmap from the non-server ports of the vm group"
    ::= { vmapGroupNewCfgNonServerPortsTableEntry 4 }
-- ------------------------------------------------------------------------- --
-- New GROUP VMAP External Ports Configuration Table (end)                 }
-- ------------------------------------------------------------------------- --

-- ------------------------------------------------------------------------- --
-- Current GROUP VMAP Server Ports Configuration Table                   {
-- ------------------------------------------------------------------------- --
vmapGroupCurCfgServerPortsTable    OBJECT-TYPE
    SYNTAX          SEQUENCE OF VmapGroupCurCfgServerPortsTableEntry
    MAX-ACCESS      not-accessible
    STATUS          current
    DESCRIPTION
        "The table of the current configuration
         of vmaps for server ports of vm groups."
    ::= { vmapGroupCfgServerPorts 1 }

vmapGroupCurCfgServerPortsTableEntry   OBJECT-TYPE
    SYNTAX          VmapGroupCurCfgServerPortsTableEntry
    MAX-ACCESS      not-accessible
    STATUS          current
    DESCRIPTION
        "A row in the table of current configuration
         of vmaps for the server ports of vm groups."
    INDEX { vmapGroupCurCfgServerPortsGroupIdx }
    ::= { vmapGroupCurCfgServerPortsTable 1 }

VmapGroupCurCfgServerPortsTableEntry ::= SEQUENCE {
    vmapGroupCurCfgServerPortsGroupIdx      Integer32,
    vmapGroupCurCfgServerPortsVmapBitmap    OCTET STRING
    }

vmapGroupCurCfgServerPortsGroupIdx     OBJECT-TYPE
    SYNTAX          Integer32
    MAX-ACCESS      read-only
    STATUS          current
    DESCRIPTION
        "The vm group id in the table of configured
         vmaps for the server ports of vm group"
    ::= { vmapGroupCurCfgServerPortsTableEntry 1 }

vmapGroupCurCfgServerPortsVmapBitmap   OBJECT-TYPE
    SYNTAX          OCTET STRING
    MAX-ACCESS      read-only
    STATUS          current
    DESCRIPTION
        "The bitmap of vmaps configured for the server
         ports of the vm group given as arguments.
         The vmaps are presented in bitmap format in receiving order:

             OCTET 1  OCTET 2  .....
             xxxxxxxx xxxxxxxx .....
             ||    || |_ vmap 9
             ||    ||
             ||    ||___ vmap 8
             ||    |____ vmap 7
             ||      .    .   .
             ||_________ vmap 2
             |__________ vmap 1

         where x : 1 - The represented vmap is active in
                       the specified context
                   0 - The represented vmap is NOT active
                       in the specified context"
    ::= { vmapGroupCurCfgServerPortsTableEntry 2 }
-- ------------------------------------------------------------------------- --
-- Current GROUP VMAP Server Ports Configuration Table (end)             }
-- ------------------------------------------------------------------------- --

-- ------------------------------------------------------------------------- --
-- New GROUP VMAP Server Ports Configuration Table                       {
-- ------------------------------------------------------------------------- --
vmapGroupNewCfgServerPortsTable    OBJECT-TYPE
    SYNTAX          SEQUENCE OF VmapGroupNewCfgServerPortsTableEntry
    MAX-ACCESS      not-accessible
    STATUS          current
    DESCRIPTION
        "The table of the new configuration
         of vmaps for server ports of vm groups."
    ::= { vmapGroupCfgServerPorts 2 }

vmapGroupNewCfgServerPortsTableEntry   OBJECT-TYPE
    SYNTAX          VmapGroupNewCfgServerPortsTableEntry
    MAX-ACCESS      not-accessible
    STATUS          current
    DESCRIPTION
        "A row in the table of new configuration
         of vmaps for the server ports of vm groups."
    INDEX { vmapGroupNewCfgServerPortsGroupIdx }
    ::= { vmapGroupNewCfgServerPortsTable 1 }

VmapGroupNewCfgServerPortsTableEntry ::= SEQUENCE {
    vmapGroupNewCfgServerPortsGroupIdx     Integer32,
    vmapGroupNewCfgServerPortsVmapBitmap   OCTET STRING,
    vmapGroupNewCfgServerPortsAddVmap      Unsigned32,
    vmapGroupNewCfgServerPortsRemVmap      Unsigned32
    }

vmapGroupNewCfgServerPortsGroupIdx     OBJECT-TYPE
    SYNTAX          Integer32
    MAX-ACCESS      read-only
    STATUS          current
    DESCRIPTION
        "The vm group id in the table of configured
         vmaps for the server ports of vm group"
    ::= { vmapGroupNewCfgServerPortsTableEntry 1 }

vmapGroupNewCfgServerPortsVmapBitmap   OBJECT-TYPE
    SYNTAX          OCTET STRING
    MAX-ACCESS      read-only
    STATUS          current
    DESCRIPTION
        "The bitmap of vmaps configured for the server
         ports of the vm group given as arguments.
         The vmaps are presented in bitmap format in receiving order:

             OCTET 1  OCTET 2  .....
             xxxxxxxx xxxxxxxx .....
             ||    || |_ vmap 9
             ||    ||
             ||    ||___ vmap 8
             ||    |____ vmap 7
             ||      .    .   .
             ||_________ vmap 2
             |__________ vmap 1

         where x : 1 - The represented vmap is active in
                       the specified context
                   0 - The represented vmap is NOT active
                       in the specified context"
    ::= { vmapGroupNewCfgServerPortsTableEntry 2 }

vmapGroupNewCfgServerPortsAddVmap      OBJECT-TYPE
    SYNTAX          Unsigned32
    MAX-ACCESS      read-write
    STATUS          current
    DESCRIPTION
        "Add a new vmap to the server ports of the vm group"
    ::= { vmapGroupNewCfgServerPortsTableEntry 3 }

vmapGroupNewCfgServerPortsRemVmap      OBJECT-TYPE
    SYNTAX          Unsigned32
    MAX-ACCESS      read-write
    STATUS          current
    DESCRIPTION
        "Remove a vmap from the server ports of the vm group"
    ::= { vmapGroupNewCfgServerPortsTableEntry 4 }
-- ------------------------------------------------------------------------- --
-- New GROUP VMAP Server Ports Configuration Table (end)                 }
-- ------------------------------------------------------------------------- --

-- ------------------------------------------------------------------------- --
-- Current GROUP VMAP All Ports Configuration Table                        {
-- ------------------------------------------------------------------------- --
vmapGroupCurCfgAllPortsTable    OBJECT-TYPE
    SYNTAX          SEQUENCE OF VmapGroupCurCfgAllPortsTableEntry
    MAX-ACCESS      not-accessible
    STATUS          current
    DESCRIPTION
        "The table of the current configuration
         of vmaps for all ports of vm groups."
    ::= { vmapGroupCfgAllPorts 1 }

vmapGroupCurCfgAllPortsTableEntry   OBJECT-TYPE
    SYNTAX          VmapGroupCurCfgAllPortsTableEntry
    MAX-ACCESS      not-accessible
    STATUS          current
    DESCRIPTION
        "A row in the table of current configuration
         of vmaps for all ports of vm groups."
    INDEX { vmapGroupCurCfgAllPortsGroupIdx }
    ::= { vmapGroupCurCfgAllPortsTable 1 }

VmapGroupCurCfgAllPortsTableEntry ::= SEQUENCE {
    vmapGroupCurCfgAllPortsGroupIdx     Integer32,
    vmapGroupCurCfgAllPortsVmapBitmap   OCTET STRING
    }

vmapGroupCurCfgAllPortsGroupIdx     OBJECT-TYPE
    SYNTAX          Integer32
    MAX-ACCESS      read-only
    STATUS          current
    DESCRIPTION
        "The vm group id in the table of configured
         vmaps for all ports of vm group"
    ::= { vmapGroupCurCfgAllPortsTableEntry 1 }

vmapGroupCurCfgAllPortsVmapBitmap   OBJECT-TYPE
    SYNTAX          OCTET STRING
    MAX-ACCESS      read-only
    STATUS          current
    DESCRIPTION
        "The bitmap of vmaps configured for the internal
         ports of the vm group given as arguments.
         The vmaps are presented in bitmap format in receiving order:

             OCTET 1  OCTET 2  .....
             xxxxxxxx xxxxxxxx .....
             ||    || |_ vmap 9
             ||    ||
             ||    ||___ vmap 8
             ||    |____ vmap 7
             ||      .    .   .
             ||_________ vmap 2
             |__________ vmap 1

         where x : 1 - The represented vmap is active in
                       the specified context
                   0 - The represented vmap is NOT active
                       in the specified context"
    ::= { vmapGroupCurCfgAllPortsTableEntry 2 }
-- ------------------------------------------------------------------------- --
-- Current GROUP VMAP All Ports Configuration Table (end)                  }
-- ------------------------------------------------------------------------- --

-- ------------------------------------------------------------------------- --
-- New GROUP VMAP All Ports Configuration Table                            {
-- ------------------------------------------------------------------------- --
vmapGroupNewCfgAllPortsTable    OBJECT-TYPE
    SYNTAX          SEQUENCE OF VmapGroupNewCfgAllPortsTableEntry
    MAX-ACCESS      not-accessible
    STATUS          current
    DESCRIPTION
        "The table of the new configuration
         of vmaps for all ports of vm groups."
    ::= { vmapGroupCfgAllPorts 2 }

vmapGroupNewCfgAllPortsTableEntry   OBJECT-TYPE
    SYNTAX          VmapGroupNewCfgAllPortsTableEntry
    MAX-ACCESS      not-accessible
    STATUS          current
    DESCRIPTION
        "A row in the table of new configuration
         of vmaps for all ports of vm groups."
    INDEX { vmapGroupNewCfgAllPortsGroupIdx }
    ::= { vmapGroupNewCfgAllPortsTable 1 }

VmapGroupNewCfgAllPortsTableEntry ::= SEQUENCE {
    vmapGroupNewCfgAllPortsGroupIdx     Integer32,
    vmapGroupNewCfgAllPortsVmapBitmap   OCTET STRING,
    vmapGroupNewCfgAllPortsAddVmap      Unsigned32,
    vmapGroupNewCfgAllPortsRemVmap      Unsigned32
    }

vmapGroupNewCfgAllPortsGroupIdx     OBJECT-TYPE
    SYNTAX          Integer32
    MAX-ACCESS      read-only
    STATUS          current
    DESCRIPTION
        "The vm group id in the table of configured
         vmaps for all ports of vm group"
    ::= { vmapGroupNewCfgAllPortsTableEntry 1 }

vmapGroupNewCfgAllPortsVmapBitmap   OBJECT-TYPE
    SYNTAX          OCTET STRING
    MAX-ACCESS      read-only
    STATUS          current
    DESCRIPTION
        "The bitmap of vmaps configured for the internal
         ports of the vm group given as arguments.
         The vmaps are presented in bitmap format in receiving order:

             OCTET 1  OCTET 2  .....
             xxxxxxxx xxxxxxxx .....
             ||    || |_ vmap 9
             ||    ||
             ||    ||___ vmap 8
             ||    |____ vmap 7
             ||      .    .   .
             ||_________ vmap 2
             |__________ vmap 1

         where x : 1 - The represented vmap is active in
                       the specified context
                   0 - The represented vmap is NOT active
                       in the specified context"
    ::= { vmapGroupNewCfgAllPortsTableEntry 2 }

vmapGroupNewCfgAllPortsAddVmap      OBJECT-TYPE
    SYNTAX          Unsigned32
    MAX-ACCESS      read-write
    STATUS          current
    DESCRIPTION
        "Add a new vmap to all ports of the vm group"
    ::= { vmapGroupNewCfgAllPortsTableEntry 3 }

vmapGroupNewCfgAllPortsRemVmap      OBJECT-TYPE
    SYNTAX          Unsigned32
    MAX-ACCESS      read-write
    STATUS          current
    DESCRIPTION
        "Remove a vmap from all vm group ports"
    ::= { vmapGroupNewCfgAllPortsTableEntry 4 }
-- ------------------------------------------------------------------------- --
-- New GROUP VMAP All Ports Configuration Table (end)                      }
-- ------------------------------------------------------------------------- --

-- ------------------------------------------------------------------------- --
-- VMAP Configuration (end)                                                }
-- ------------------------------------------------------------------------- --

-- ----------------------------------------------------------------------------
-- } INSERT:  acl
-- ----------------------------------------------------------------------------



cee                     OBJECT IDENTIFIER ::= { g8264T-mgmt 13 }
-- ----------------------------------------------------------------------------
-- { INSERT:  cee
-- ----------------------------------------------------------------------------
ceeConfig      OBJECT IDENTIFIER ::= { cee 1 }

-- General Configuration for CEE


ceeCurCfgState OBJECT-TYPE
    SYNTAX  INTEGER {
	on(1),
	off(2)
	}
    MAX-ACCESS  read-only
    STATUS  current
    DESCRIPTION
        "CEE is currently on or off." 
    ::= { ceeConfig 1 }



ceeNewCfgState OBJECT-TYPE
    SYNTAX  INTEGER {
	on(1),
	off(2)
	}
    MAX-ACCESS  read-create
    STATUS  current
    DESCRIPTION
        "Turn CEE on or off." 
    ::= { ceeConfig 2 }


fcoe                    OBJECT IDENTIFIER ::= { g8264T-mgmt 14 }

-- ----------------------------------------------------------------------------
-- { INSERT:  fcoe
-- ----------------------------------------------------------------------------
fcoeConfig       OBJECT IDENTIFIER ::= { fcoe 1 }
fcoeStats        OBJECT IDENTIFIER ::= { fcoe 2 }
fcoeInfo         OBJECT IDENTIFIER ::= { fcoe 3 }
fcoeOper         OBJECT IDENTIFIER ::= { fcoe 4 }

fipsCfg  	        OBJECT IDENTIFIER ::= { fcoeConfig 3 }
fipsInfo                OBJECT IDENTIFIER ::= { fcoeInfo 1 }
fipsOper                OBJECT IDENTIFIER ::= { fcoeOper 1 }

fipsInfoFcf      OBJECT IDENTIFIER ::= { fipsInfo 2 }
fipsInfoFcoe     OBJECT IDENTIFIER ::= { fipsInfo 3 }
fipsInfoVlans     OBJECT IDENTIFIER ::= { fipsInfo 4 }

-- General Configuration for fcoe


fipsCurCfgState OBJECT-TYPE
    SYNTAX  INTEGER {
	on(1),
	off(2)
	}
    MAX-ACCESS  read-only
    STATUS  current
    DESCRIPTION
        "FIP snooping is currently on or off." 
    ::= { fipsCfg 1 }



fipsNewCfgState OBJECT-TYPE
    SYNTAX  INTEGER {
	on(1),
	off(2)
	}
    MAX-ACCESS  read-create
    STATUS  current
    DESCRIPTION
        "Turn FIP snooping on or off." 
    ::= { fipsCfg 2 }



fipsCurAclTimeout OBJECT-TYPE
    SYNTAX  INTEGER {
	enabled(1),
	disabled(2)
	}
    MAX-ACCESS  read-only
    STATUS  current
    DESCRIPTION
        "The removal of acls when FCF and FCOE connections timed out is enabled or disabled." 
    ::= { fipsCfg 3 }



fipsNewAclTimeout OBJECT-TYPE
    SYNTAX  INTEGER {
	enabled(1),
	disabled(2)
	}
    MAX-ACCESS  read-create
    STATUS  current
    DESCRIPTION
        "Enable or disable the removal of acls when FCF and FCOE connections timed out." 
    ::= { fipsCfg 4 }



fipsCurAutoVlan OBJECT-TYPE
    SYNTAX  INTEGER {
	enabled(1),
	disabled(2)
	}
    MAX-ACCESS  read-only
    STATUS  current
    DESCRIPTION
        "The automatic creation of FCOE vlans is enabled or disabled." 
    ::= { fipsCfg 5 }



fipsNewAutoVlan OBJECT-TYPE
    SYNTAX  INTEGER {
	enabled(1),
	disabled(2)
	}
    MAX-ACCESS  read-create
    STATUS  current
    DESCRIPTION
        "Enable or disable the automatic creation of FCOE vlans." 
    ::= { fipsCfg 6 }


-- FIPS current config table

fipsPortCurCfgTable OBJECT-TYPE
    SYNTAX SEQUENCE OF FipsPortCurCfgEntry
    MAX-ACCESS not-accessible
    STATUS current
    DESCRIPTION
        "The table of FIP Snooping port current config."
    ::= { fipsCfg 7 }


fipsPortCurCfgEntry OBJECT-TYPE
    SYNTAX FipsPortCurCfgEntry
    MAX-ACCESS not-accessible
    STATUS current
    DESCRIPTION
        "FIP Config for a particular port."
    INDEX { fipsPortCurCfgIndex }
    ::= { fipsPortCurCfgTable 1 }
 
FipsPortCurCfgEntry ::= SEQUENCE {
    fipsPortCurCfgIndex          PortNumber,
    fipsPortCurCfgFcfMode        INTEGER,
    fipsPortCurCfgFipsEna        INTEGER
    }


fipsPortCurCfgIndex OBJECT-TYPE
    SYNTAX  PortNumber
    MAX-ACCESS  read-only
    STATUS  current
    DESCRIPTION
        "The port number" 
    ::= { fipsPortCurCfgEntry 1 }

fipsPortCurCfgFcfMode OBJECT-TYPE
    SYNTAX  INTEGER {
	auto(0),
	on(1),
        off(2)
	}
    MAX-ACCESS  read-only
    STATUS  current
    DESCRIPTION
        "Weither the port is set to have FCF auto detection, on, or off." 
    ::= { fipsPortCurCfgEntry 2 }

fipsPortCurCfgFipsEna OBJECT-TYPE 
    SYNTAX  INTEGER {
	enabled(1),
	disabled(2)
	}
    MAX-ACCESS  read-only 
    STATUS  current 
    DESCRIPTION 
        "FIP snooping enabled or disabled on this port."  
    ::= { fipsPortCurCfgEntry 3 }






-- FIPS new config table

fipsPortNewCfgTable OBJECT-TYPE
    SYNTAX SEQUENCE OF FipsPortNewCfgEntry
    MAX-ACCESS not-accessible
    STATUS current
    DESCRIPTION
        "The table of FIP Snooping port new config."
    ::= { fipsCfg 8 }


fipsPortNewCfgEntry OBJECT-TYPE
    SYNTAX FipsPortNewCfgEntry
    MAX-ACCESS not-accessible
    STATUS current
    DESCRIPTION
        "FIP Config for a particular port."
    INDEX { fipsPortNewCfgIndex }
    ::= { fipsPortNewCfgTable 1 }
 
FipsPortNewCfgEntry ::= SEQUENCE {
    fipsPortNewCfgIndex          PortNumber,
    fipsPortNewCfgFcfMode        INTEGER,
    fipsPortNewCfgFipsEna        INTEGER
    }


fipsPortNewCfgIndex OBJECT-TYPE
    SYNTAX  PortNumber
    MAX-ACCESS  read-only
    STATUS  current
    DESCRIPTION
        "The port number" 
    ::= { fipsPortNewCfgEntry 1 }

fipsPortNewCfgFcfMode OBJECT-TYPE
    SYNTAX  INTEGER {
	auto(0),
	on(1),
        off(2)
	}
    MAX-ACCESS  read-create
    STATUS  current
    DESCRIPTION
        "Set this port to have FCF on, off, or auto detection." 
    ::= { fipsPortNewCfgEntry 2 }

fipsPortNewCfgFipsEna OBJECT-TYPE 
    SYNTAX  INTEGER {
	enabled(1),
	disabled(2)
	}
    MAX-ACCESS  read-create 
    STATUS  current 
    DESCRIPTION 
        "Enable or disable FIP snooping on this port."  
    ::= { fipsPortNewCfgEntry 3 }





-- fips Information Table

fipsInfoPortTable OBJECT-TYPE
    SYNTAX SEQUENCE OF FipsInfoPortEntry
    MAX-ACCESS  not-accessible
    STATUS  current
    DESCRIPTION
        "The table of fips port run-time information."
    ::= { fipsInfo 1 }

fipsInfoPortEntry OBJECT-TYPE
    SYNTAX  FipsInfoPortEntry
    MAX-ACCESS  not-accessible
    STATUS  current
    DESCRIPTION
        "A port in the fips information table."
    INDEX   { fipsInfoPortIndex, fipsInfoAclSequencer}
    ::= { fipsInfoPortTable 1 }
 
FipsInfoPortEntry ::= SEQUENCE {
    fipsInfoPortIndex           PortNumber,
    fipsInfoAclSequencer        Integer32,
    fipsInfoAcl                 DisplayString
    }

fipsInfoPortIndex OBJECT-TYPE
    SYNTAX  PortNumber
    MAX-ACCESS  read-only
    STATUS  current
    DESCRIPTION
        "The port index for fips" 
    ::= { fipsInfoPortEntry 1 }

fipsInfoAclSequencer OBJECT-TYPE
    SYNTAX  Integer32
    MAX-ACCESS  read-only
    STATUS  current
    DESCRIPTION
        "The fip sequence number for an acl in this port" 
    ::= { fipsInfoPortEntry 2 }

fipsInfoAcl OBJECT-TYPE
    SYNTAX  DisplayString (SIZE(0..31))
    MAX-ACCESS  read-only
    STATUS  current
    DESCRIPTION
        "An FIPS ACL entry" 
    ::= { fipsInfoPortEntry 3 }

-- info fcf detected 

fipsInfoFcfCount OBJECT-TYPE
    SYNTAX Integer32
    MAX-ACCESS  read-only
    STATUS  current
    DESCRIPTION
        "Total number of FCFs detected"
    ::= { fipsInfoFcf 1 }

fipsInfoFcfTable OBJECT-TYPE
    SYNTAX SEQUENCE OF FipsInfoFcfEntry
    MAX-ACCESS  not-accessible
    STATUS  current
    DESCRIPTION
        "The table of fips FCF detected."
    ::= { fipsInfoFcf 2 }

fipsInfoFcfEntry OBJECT-TYPE
    SYNTAX  FipsInfoFcfEntry
    MAX-ACCESS  not-accessible
    STATUS  current
    DESCRIPTION
        "A FCF in the fips information table."
    INDEX   { fipsInfoFcfIndex }
    ::= { fipsInfoFcfTable 1 }

FipsInfoFcfEntry ::= SEQUENCE {
    fipsInfoFcfIndex            Integer32,
    fipsInfoFcfMac              DisplayString,
    fipsInfoFcfPort             DisplayString,
    fipsInfoFcfVlan             Integer32 
}

fipsInfoFcfIndex OBJECT-TYPE
    SYNTAX Integer32
    MAX-ACCESS  read-only
    STATUS  current
    DESCRIPTION
        "FCF index"
    ::= { fipsInfoFcfEntry 1 }

fipsInfoFcfMac OBJECT-TYPE
    SYNTAX DisplayString
    MAX-ACCESS  read-only
    STATUS  current
    DESCRIPTION
        "FCF MAC"
    ::= { fipsInfoFcfEntry 2 }

fipsInfoFcfPort OBJECT-TYPE
    SYNTAX DisplayString 
    MAX-ACCESS  read-only
    STATUS  current
    DESCRIPTION
        "FCF Port"
    ::= { fipsInfoFcfEntry 3 }

fipsInfoFcfVlan OBJECT-TYPE
    SYNTAX Integer32
    MAX-ACCESS  read-only
    STATUS  current
    DESCRIPTION
        "FCF Vlan"
    ::= { fipsInfoFcfEntry 4 }

fipsInfoVlansTable OBJECT-TYPE
    SYNTAX SEQUENCE OF FipsInfoVlansEntry
    MAX-ACCESS  not-accessible
    STATUS  current
    DESCRIPTION
        "The table of FCOE VLANs detected."
    ::= { fipsInfoVlans 1 }

fipsInfoVlansEntry OBJECT-TYPE
    SYNTAX  FipsInfoVlansEntry
    MAX-ACCESS  not-accessible
    STATUS  current
    DESCRIPTION
        "A FCOE VLAN in the fipsInfoVlans information table."
    INDEX   { fipsInfoVlansId, fipsInfoVlansFeatureIndex}
    ::= { fipsInfoVlansTable 1 }

FipsInfoVlansEntry ::= SEQUENCE {
    fipsInfoVlansId                  INTEGER,
    fipsInfoVlansFeatureIndex        INTEGER,
    fipsInfoVlansCreator             DisplayString,
    fipsInfoVlansPorts               OCTET STRING,
    fipsInfoVlansTrunks              DisplayString
}

fipsInfoVlansId OBJECT-TYPE
    SYNTAX  INTEGER  (1..4095)
    MAX-ACCESS  read-only
    STATUS  current
    DESCRIPTION
        "FCoE Vlan index"
    ::= { fipsInfoVlansEntry 1 }

fipsInfoVlansFeatureIndex OBJECT-TYPE
    SYNTAX INTEGER  (0..8)
    MAX-ACCESS  read-only
    STATUS  current
    DESCRIPTION
        "FCoE Vlan feature index. The feature index will accept values
         from 1 to maximum SPAR ID(8) for the VLANs created by SPAR and
         0 for the other types of VLANs."
    ::= { fipsInfoVlansEntry 2 }

fipsInfoVlansCreator OBJECT-TYPE
    SYNTAX  DisplayString (SIZE(0..32))
    MAX-ACCESS  read-only
    STATUS  current
    DESCRIPTION
        "The FCoE VLAN Creator."
    ::= { fipsInfoVlansEntry 3 }

fipsInfoVlansPorts OBJECT-TYPE
    SYNTAX  OCTET STRING
    MAX-ACCESS  read-only
    STATUS  current
    DESCRIPTION
        "The port list information in the VLAN. The ports are presented
         in bitmap format.
         in receiving order:

             OCTET 1  OCTET 2  .....
             xxxxxxxx xxxxxxxx .....
             ||    || |_ port 8
             ||    ||
             ||    ||___ port 7
             ||    |____ port 6
             ||      .    .   .
             ||_________ port 1
             |__________ reserved

         where x : 1 - The represented port belongs to the VLAN
                   0 - The represented port does not belong to the VLAN"
    ::= { fipsInfoVlansEntry 4 }

fipsInfoVlansTrunks OBJECT-TYPE
    SYNTAX  DisplayString 
    MAX-ACCESS  read-only
    STATUS  current
    DESCRIPTION
        "The FCoE VLAN trunk list."
    ::= { fipsInfoVlansEntry 5 }

fipsInfoFcoeCount OBJECT-TYPE
    SYNTAX Integer32
    MAX-ACCESS  read-only
    STATUS  current
    DESCRIPTION
        "Total number of FCOE connections"
    ::= { fipsInfoFcoe 1 }

fipsInfoFcoeTable OBJECT-TYPE
    SYNTAX SEQUENCE OF FipsInfoFcoeEntry
    MAX-ACCESS  not-accessible
    STATUS  current
    DESCRIPTION
        "The table of fips FCOE connections."
    ::= { fipsInfoFcoe 2 }

fipsInfoFcoeEntry OBJECT-TYPE
    SYNTAX  FipsInfoFcoeEntry
    MAX-ACCESS  not-accessible
    STATUS  current
    DESCRIPTION
        "A FCOE connection in the fips information table."
    INDEX   { fipsInfoFcoeIndex }
    ::= { fipsInfoFcoeTable 1 }

FipsInfoFcoeEntry ::= SEQUENCE {
    fipsInfoFcoeIndex           Integer32,
    fipsInfoFcoeVNPortMac       DisplayString,
    fipsInfoFcoeFcfMac          DisplayString,
    fipsInfoFcoePort            DisplayString,
    fipsInfoFcoeVlan            Integer32     
}

fipsInfoFcoeIndex OBJECT-TYPE
    SYNTAX Integer32
    MAX-ACCESS  read-only
    STATUS  current
    DESCRIPTION
        "FCOE connection index"
    ::= { fipsInfoFcoeEntry 1 }

fipsInfoFcoeVNPortMac OBJECT-TYPE
    SYNTAX DisplayString
    MAX-ACCESS  read-only
    STATUS  current
    DESCRIPTION
        "FCOE connection VNPort MAC"
    ::= { fipsInfoFcoeEntry 2 }

fipsInfoFcoeFcfMac OBJECT-TYPE
    SYNTAX DisplayString
    MAX-ACCESS  read-only
    STATUS  current
    DESCRIPTION
        "FCOE connection FCF MAC"
    ::= { fipsInfoFcoeEntry 3 }

fipsInfoFcoePort OBJECT-TYPE
    SYNTAX DisplayString 
    MAX-ACCESS  read-only
    STATUS  current
    DESCRIPTION
        "FCOE connection Port"
    ::= { fipsInfoFcoeEntry 4 }

fipsInfoFcoeVlan OBJECT-TYPE
    SYNTAX Integer32
    MAX-ACCESS  read-only
    STATUS  current
    DESCRIPTION
        "FCOE connection Vlan"
    ::= { fipsInfoFcoeEntry 5 }

-- FIPS Operational command


fipsOperFcfDelete OBJECT-TYPE
    SYNTAX  DisplayString (SIZE(0..31))
    MAX-ACCESS  read-write
    STATUS  current
    DESCRIPTION
        "Delete an FCF. Take an fcf mac address as the only parameter
         to delete this fcf from all vlans. Optionally take a vlan 
         number as 2nd parameter to delete fcf from just this vlan.  
         The 2 parameters are seperated by comma with no space allowed." 
    ::= { fipsOper 1 }

-- fipsOperFcoeDelete OBJECT-TYPE
--     SYNTAX  DisplayString (SIZE(0..127))
--     MAX-ACCESS  read-write
--     STATUS  current
--     DESCRIPTION
--         "Delete an FCOE connection.  Take 3 parameters seperated by comma: assigned VN_PORT mac address, FCF mac address, and vlan number.  No space is allowed." 
--     ::= { fipsOper 2 }



-- Stats for fcoe

fcoeStatsTable OBJECT-TYPE
    SYNTAX SEQUENCE OF FcoeStatstEntry
    MAX-ACCESS  not-accessible
    STATUS  current
    DESCRIPTION
        "The table of fcoe statistics per switch unit."
    ::= { fcoeStats 1 }

fcoeStatsEntry OBJECT-TYPE
    SYNTAX  FcoeStatstEntry
    MAX-ACCESS  not-accessible
    STATUS  current
    DESCRIPTION
        "A switch unit."
    INDEX   { fcoeStatsIndex }
    ::= { fcoeStatsTable 1 }
 
 FcoeStatstEntry ::= SEQUENCE {
    fcoeStatsIndex          INTEGER,
    fcoeStatsFcfAdded       INTEGER,
    fcoeStatsFcfRemoved     INTEGER, 
    fcoeStatsFcoeAdded      INTEGER,
    fcoeStatsFcoeRemoved    INTEGER
    }

fcoeStatsIndex OBJECT-TYPE
    SYNTAX  INTEGER
    MAX-ACCESS  read-only
    STATUS  current
    DESCRIPTION
        "The switch index for fips statistics" 
    ::= { fcoeStatsEntry 1 }

fcoeStatsFcfAdded OBJECT-TYPE
    SYNTAX  INTEGER 
    MAX-ACCESS  read-only
    STATUS  current
    DESCRIPTION
        "The number of FCF added to the FCOE database." 
    ::= { fcoeStatsEntry 2 }


fcoeStatsFcfRemoved OBJECT-TYPE
    SYNTAX  INTEGER 
    MAX-ACCESS  read-only
    STATUS  current
    DESCRIPTION
        "The number of FCF removed to the FCOE database." 
    ::= { fcoeStatsEntry 3 }


fcoeStatsFcoeAdded OBJECT-TYPE
    SYNTAX  INTEGER 
    MAX-ACCESS  read-only
    STATUS  current
    DESCRIPTION
        "The number of FCOE connection added to the FCOE database." 
    ::= { fcoeStatsEntry 4 }


fcoeStatsFcoeRemoved OBJECT-TYPE
    SYNTAX  INTEGER 
    MAX-ACCESS  read-only
    STATUS  current
    DESCRIPTION
        "The number of FCOE connection removed to the FCOE database." 
    ::= { fcoeStatsEntry 5 }


fcoeStatsKeepAliveTable OBJECT-TYPE
    SYNTAX SEQUENCE OF FcoeStatsKeepAliveEntry
    MAX-ACCESS  not-accessible
    STATUS  current
    DESCRIPTION
        "The table of fcoe Keep-Alive statistics."
    ::= { fcoeStats 2 }

fcoeStatsKeepAliveEntry OBJECT-TYPE
    SYNTAX  FcoeStatsKeepAliveEntry
    MAX-ACCESS  not-accessible
    STATUS  current
    DESCRIPTION
        "A FCF Keep Alive entry."
    INDEX   { fcoeStatsKeepAliveIndex }
    ::= { fcoeStatsKeepAliveTable 1 }

FcoeStatsKeepAliveEntry ::= SEQUENCE {
    fcoeStatsKeepAliveIndex     INTEGER,
    fcoeStatsKeepAliveFcfMac    DisplayString,
    fcoeStatsKeepAliveCount     INTEGER
    }

fcoeStatsKeepAliveIndex OBJECT-TYPE
    SYNTAX  INTEGER
    MAX-ACCESS  read-only
    STATUS  current
    DESCRIPTION
        "The FCF index"
    ::= { fcoeStatsKeepAliveEntry 1 }

fcoeStatsKeepAliveFcfMac OBJECT-TYPE
    SYNTAX  DisplayString
    MAX-ACCESS  read-only
    STATUS  current
    DESCRIPTION
        "Detected FCF MAC address."
    ::= { fcoeStatsKeepAliveEntry 2 }

fcoeStatsKeepAliveCount OBJECT-TYPE
    SYNTAX  INTEGER
    MAX-ACCESS  read-only
    STATUS  current
    DESCRIPTION
        "FCF MAC Keep Alive count."
    ::= { fcoeStatsKeepAliveEntry 3 }

fcoeStatsResetAllCounters OBJECT-TYPE
    SYNTAX  INTEGER {
    reset(1),
    others(2)
    }
    MAX-ACCESS  read-write
    STATUS  current
    DESCRIPTION
        "Reset all FCOE statistics counters." 
    ::= { fcoeStats 3 }




virt                    OBJECT IDENTIFIER ::= { g8264T-mgmt 15 }

-- ----------------------------------------------------------------------------
-- { INSERT:  virt    
-- ----------------------------------------------------------------------------

virtGeneral OBJECT IDENTIFIER ::= { virt 1 }

vmGroups    OBJECT IDENTIFIER ::= { virt 2 }

vmPolicy    OBJECT IDENTIFIER ::= { virt 3 }

vmbw        OBJECT IDENTIFIER ::= { vmPolicy 1 }

vmProfiles  OBJECT IDENTIFIER ::= { virt 4 }
virtVMware  OBJECT IDENTIFIER ::= { virt 5 }



vmCheck     OBJECT IDENTIFIER ::= { virt 7 }

vmReadyMisc OBJECT IDENTIFIER ::= { virt 8 }

-- ---------------------------------------------------------- --
-- VM General Configuration
-- ---------------------------------------------------------- --

virtCurCfgState   OBJECT-TYPE
    SYNTAX      INTEGER {
        enabled(1),
        disabled(2)
        }
    MAX-ACCESS read-only
    STATUS current
    DESCRIPTION
    "VM groups global state."
    ::= { virtGeneral 1}

virtNewCfgState   OBJECT-TYPE
    SYNTAX      INTEGER {
        enabled(1),
        disabled(2)
        }
    MAX-ACCESS read-write
    STATUS current
    DESCRIPTION
    "Enable/Disable Virtual Machine Groups"
    ::= { virtGeneral 2}

virtCurCfgHbPort  OBJECT-TYPE
    SYNTAX      INTEGER (1..65535)
    MAX-ACCESS read-only
    STATUS current
    DESCRIPTION
    "Current esx/esxi server to vcenter heartbeat UDP port"
    ::= { virtGeneral 3}

virtNewCfgHbPort  OBJECT-TYPE
    SYNTAX      INTEGER (1..65535)
    MAX-ACCESS read-write
    STATUS current
    DESCRIPTION
    "Set new esx/esxi server to vcenter heartbeat UDP port"
    ::= { virtGeneral 4}

-- ------------------------------------------------------------------------- --
-- VM Virtual Center Configuration                                         {
-- ------------------------------------------------------------------------- --
virtCurCfgVirtCenterIp OBJECT-TYPE
    SYNTAX  IpAddress
    MAX-ACCESS  read-only
    STATUS  current
    DESCRIPTION
        "The IP address of the Virtual Center."
    ::= { virtGeneral 5}

virtNewCfgVirtCenterIp  OBJECT-TYPE
    SYNTAX  IpAddress
    MAX-ACCESS  read-write
    STATUS  current
    DESCRIPTION
        "The IP address of the Virtual Center."
    ::= { virtGeneral 6 }

virtCurCfgVirtCenterUser OBJECT-TYPE
    SYNTAX  DisplayString(SIZE(0..64))
    MAX-ACCESS  read-only
    STATUS  current
    DESCRIPTION
        "Virtual Center username."
    ::= { virtGeneral 7 }

virtNewCfgVirtCenterUser OBJECT-TYPE
    SYNTAX  DisplayString(SIZE(0..64))
    MAX-ACCESS  read-write
    STATUS  current
    DESCRIPTION
        "Virtual Center username."
    ::= { virtGeneral 8 }

virtCurCfgVirtCenterSSLAuth OBJECT-TYPE
    SYNTAX  INTEGER {
        enabled(1),
        disabled(2)
        }
    MAX-ACCESS  read-only
    STATUS  current
    DESCRIPTION
	"Authenticate SSL Certificate."
    ::= { virtGeneral 9 }

virtNewCfgVirtCenterSSLAuth OBJECT-TYPE
    SYNTAX  INTEGER {
        enabled(1),
        disabled(2)
        }
    MAX-ACCESS  read-write
    STATUS  current
    DESCRIPTION
	"Authenticate SSL Certificate."
    ::= { virtGeneral 10 }

virtNewCfgVirtCenterPasswd OBJECT-TYPE
    SYNTAX DisplayString(SIZE(0..129))
    MAX-ACCESS read-write
    STATUS current
    DESCRIPTION
        "Virtual Center password."
    ::= { virtGeneral 11 }

virtNewCfgVirtCenterDelete OBJECT-TYPE
    SYNTAX  INTEGER {
        none(1),
        delete(2)
        }
    MAX-ACCESS  read-write
    STATUS  current
    DESCRIPTION
        "Delete Virtual Center specifications"
    ::= { virtGeneral 12 }
-- ------------------------------------------------------------------------- --
-- VM Virtual Center Configuration (end)                                     } 
-- ------------------------------------------------------------------------- --

vmCurCfgGroupTable  OBJECT-TYPE
    SYNTAX SEQUENCE OF VmCurCfgGroupEntry
    MAX-ACCESS not-accessible
    STATUS current
    DESCRIPTION
      "The table of VM groups in the current config"
    ::= { vmGroups 1 }

vmCurCfgGroupEntry OBJECT-TYPE
    SYNTAX VmCurCfgGroupEntry
    MAX-ACCESS not-accessible
    STATUS current
    DESCRIPTION
      "Information about VM on a group in current config."
    INDEX { vmCurCfgGroupIndex }
    ::= { vmCurCfgGroupTable 1 }

vmNewCfgGroupTable  OBJECT-TYPE
    SYNTAX SEQUENCE OF VmNewCfgGroupEntry
    MAX-ACCESS not-accessible
    STATUS current
    DESCRIPTION
      "The table of VM groups in the new config"
    ::= { vmGroups 2 }

vmNewCfgGroupEntry OBJECT-TYPE
    SYNTAX VmNewCfgGroupEntry
    MAX-ACCESS not-accessible
    STATUS current
    DESCRIPTION
      "Information about VM on a group in new config."
    INDEX { vmNewCfgGroupIndex }
    ::= { vmNewCfgGroupTable 1 }

VmCurCfgGroupEntry ::= SEQUENCE {
    vmCurCfgGroupIndex       Integer32,
    vmCurCfgGroupVlan        INTEGER,
    vmCurCfgGroupPorts       OCTET STRING,

    vmCurCfgGroupTagState     INTEGER,
    vmCurCfgGroupProfileName  DisplayString,  
    vmCurCfgGroupValidateMode   INTEGER,
    vmCurCfgGroupStg        INTEGER
    }

vmCurCfgGroupIndex OBJECT-TYPE
    SYNTAX  Integer32
    MAX-ACCESS  read-only
    STATUS  current
    DESCRIPTION
        "The index of the vm group table."
    ::= { vmCurCfgGroupEntry 1}

vmCurCfgGroupVlan OBJECT-TYPE
    SYNTAX  INTEGER
    MAX-ACCESS  read-only
    STATUS  current
    DESCRIPTION
        "Current Vlan used by the group."
    ::= { vmCurCfgGroupEntry 2}

vmCurCfgGroupPorts OBJECT-TYPE
    SYNTAX  OCTET STRING
    MAX-ACCESS  read-only
    STATUS  current
    DESCRIPTION
        "The port list in the VM Group.  The ports are presented in bitmap format.
         in receiving order:

             OCTET 1  OCTET 2  .....
             xxxxxxxx xxxxxxxx .....
             ||    || |_ port 8
             ||    ||
             ||    ||___ port 7
             ||    |____ port 6
             ||      .    .   .
             ||_________ port 1
             |__________ reserved

         where x : 1 - The represented port belongs to the VM Group 
                   0 - The represented port does not belong to the VM Group"
   ::= { vmCurCfgGroupEntry 3}


vmCurCfgGroupTagState OBJECT-TYPE
    SYNTAX  INTEGER {
        enabled(1),
        disabled(0)
        }
    MAX-ACCESS  read-only
    STATUS  current
    DESCRIPTION
        "Enable VLAN tagging on all VM group ports."
    ::= { vmCurCfgGroupEntry 4}

vmCurCfgGroupStg OBJECT-TYPE
    SYNTAX  INTEGER
    MAX-ACCESS  read-only
    STATUS  current
    DESCRIPTION
        "Current stg of the group vlan."
    ::= { vmCurCfgGroupEntry 5}


vmCurCfgGroupProfileName OBJECT-TYPE
    SYNTAX  DisplayString (SIZE(0..40))
    MAX-ACCESS  read-only
    STATUS  current
    DESCRIPTION
        "Current profile name used by the group."
    ::= { vmCurCfgGroupEntry 17}



vmCurCfgGroupValidateMode OBJECT-TYPE
    SYNTAX  INTEGER
    MAX-ACCESS  read-only
    STATUS  current
    DESCRIPTION
        "Current validation mode used by the group."
    ::= { vmCurCfgGroupEntry 18}


VmNewCfgGroupEntry ::= SEQUENCE {
    vmNewCfgGroupIndex      Integer32,
    vmNewCfgGroupVlan       INTEGER,
    vmNewCfgGroupPorts      OCTET STRING,
    vmNewCfgGroupAddVm      DisplayString,
    vmNewCfgGroupRemVm      DisplayString,
    vmNewCfgGroupAddVmIdx   INTEGER,
    vmNewCfgGroupRemVmIdx   INTEGER,
    vmNewCfgGroupAddPort    PortNumber,
    vmNewCfgGroupRemPort    PortNumber,
    vmNewCfgGroupAddTrunk   INTEGER,
    vmNewCfgGroupRemTrunk   INTEGER,
    vmNewCfgGroupTagState   INTEGER,
    vmNewCfgGroupAddLacpKey Unsigned32,
    vmNewCfgGroupRemLacpKey Unsigned32,
    vmNewCfgGroupAddProfile DisplayString,
    vmNewCfgGroupRemProfile INTEGER,
    vmNewCfgGroupProfileName  DisplayString,
    vmNewCfgGroupDelete     INTEGER,
    vmNewCfgGroupValidateMode  INTEGER,
    vmNewCfgGroupStg        INTEGER
    }

vmNewCfgGroupIndex OBJECT-TYPE
    SYNTAX  Integer32
    MAX-ACCESS  read-only
    STATUS  current
    DESCRIPTION
        "The index of the vm group table."
    ::= { vmNewCfgGroupEntry 1}

vmNewCfgGroupVlan OBJECT-TYPE
    SYNTAX  INTEGER
    MAX-ACCESS  read-write
    STATUS  current
    DESCRIPTION
        "Set Vlan to be used by the group."
    ::= { vmNewCfgGroupEntry 2}

vmNewCfgGroupAddVm OBJECT-TYPE
    SYNTAX  DisplayString
    MAX-ACCESS  read-write
    STATUS  current
    DESCRIPTION
        "Add a virtual machine to the group by 
         UUID / Name / IP / MAC Address
         Note: MAC address format xx:xx:xx:xx:xx:xx"
    ::= { vmNewCfgGroupEntry 4}

vmNewCfgGroupRemVm OBJECT-TYPE
    SYNTAX  DisplayString
    MAX-ACCESS  read-write
    STATUS  current
    DESCRIPTION
        "Remove a virtual machine from the group by 
         UUID / Name / IP / MAC Address
         Note: MAC address format xx:xx:xx:xx:xx:xx"
    ::= { vmNewCfgGroupEntry 5}
    
vmNewCfgGroupAddVmIdx OBJECT-TYPE
    SYNTAX  INTEGER
    MAX-ACCESS  read-write
    STATUS  current
    DESCRIPTION
        "Add virtual MAC address by index to the group."
    ::= { vmNewCfgGroupEntry 6}

vmNewCfgGroupRemVmIdx OBJECT-TYPE
    SYNTAX  INTEGER
    MAX-ACCESS  read-write
    STATUS  current
    DESCRIPTION
        "Remove a virtual MAC address by index from the group."
    ::= { vmNewCfgGroupEntry 7}

vmNewCfgGroupAddPort OBJECT-TYPE
    SYNTAX  PortNumber
    MAX-ACCESS  read-write
    STATUS  current
    DESCRIPTION
        "Add a port to the group."
    ::= { vmNewCfgGroupEntry 8}

vmNewCfgGroupRemPort OBJECT-TYPE
    SYNTAX  PortNumber
    MAX-ACCESS  read-write
    STATUS  current
    DESCRIPTION
        "Remove a port from the group."
    ::= { vmNewCfgGroupEntry 9}

vmNewCfgGroupAddTrunk OBJECT-TYPE
    SYNTAX  INTEGER
    MAX-ACCESS  read-write
    STATUS  current
    DESCRIPTION
        "Add trunk to the group."
    ::= { vmNewCfgGroupEntry 10}

vmNewCfgGroupRemTrunk OBJECT-TYPE
    SYNTAX  INTEGER
    MAX-ACCESS  read-write
    STATUS  current
    DESCRIPTION
        "Remove trunk from the group."
    ::= { vmNewCfgGroupEntry 11}

vmNewCfgGroupTagState OBJECT-TYPE
    SYNTAX  INTEGER {
        enabled(1),
        disabled(0)
        }
    MAX-ACCESS  read-write
    STATUS  current
    DESCRIPTION
        "Enable VLAN tagging on all VM group ports."
    ::= { vmNewCfgGroupEntry 12}

vmNewCfgGroupAddLacpKey OBJECT-TYPE
    SYNTAX  Unsigned32 (1..65535)
    MAX-ACCESS  read-write
    STATUS  current
    DESCRIPTION
        "Add LACP trunk to the group."
    ::= { vmNewCfgGroupEntry 13}

vmNewCfgGroupRemLacpKey OBJECT-TYPE
    SYNTAX  Unsigned32 (1..65535)
    MAX-ACCESS  read-write
    STATUS  current
    DESCRIPTION
        "Remove LACP trunk from the group."
    ::= { vmNewCfgGroupEntry 14}


vmNewCfgGroupAddProfile OBJECT-TYPE
    SYNTAX  DisplayString (SIZE(0..40))
    MAX-ACCESS  read-write
    STATUS  current
    DESCRIPTION
        "Add VM Profile to the group."
    ::= { vmNewCfgGroupEntry 15}

vmNewCfgGroupRemProfile OBJECT-TYPE
    SYNTAX  INTEGER {
        remove(1)
        }
    MAX-ACCESS  read-write
    STATUS      current
    DESCRIPTION
        "Remove any VM profile associated with the group."
    ::= { vmNewCfgGroupEntry 16 }

vmNewCfgGroupProfileName OBJECT-TYPE
    SYNTAX  DisplayString (SIZE(0..40))
    MAX-ACCESS  read-only
    STATUS  current
    DESCRIPTION
        "New profile name to be used by the group."
    ::= { vmNewCfgGroupEntry 17}


vmNewCfgGroupDelete OBJECT-TYPE
    SYNTAX  INTEGER {
        delete(1)
        }
    MAX-ACCESS  read-write
    STATUS  current
    DESCRIPTION
        "Delete VM Group."
    ::= { vmNewCfgGroupEntry 18}

vmNewCfgGroupStg OBJECT-TYPE
    SYNTAX  INTEGER
    MAX-ACCESS  read-write
    STATUS  current
    DESCRIPTION
        "Set group vlan spanning tree group."
    ::= { vmNewCfgGroupEntry 19}

vmNewCfgGroupPorts OBJECT-TYPE
    SYNTAX  OCTET STRING
    MAX-ACCESS  read-only
    STATUS  current
    DESCRIPTION
        "The port list in the VM Group.  The ports are presented in bitmap format.
         in receiving order:

             OCTET 1  OCTET 2  .....
             xxxxxxxx xxxxxxxx .....
             ||    || |_ port 8
             ||    ||
             ||    ||___ port 7
             ||    |____ port 6
             ||      .    .   .
             ||_________ port 1
             |__________ reserved

         where x : 1 - The represented port belongs to the VM Group 
                   0 - The represented port does not belong to the VM Group"
   ::= { vmNewCfgGroupEntry 3}


vmNewCfgGroupValidateMode OBJECT-TYPE
    SYNTAX  INTEGER {
        noValidation(0),
        basicCheck(1),
        advancedCheck(2)
    }

    MAX-ACCESS  read-write
    STATUS  current
    DESCRIPTION
        "Set group validation mode:
         noValidation : no validation will be performed.
         basicCheck: validate ESX port.
         advancedCheck: validate ESX port and VM UUID."
    ::= { vmNewCfgGroupEntry 20}


vmCurCfgGroupMacTable OBJECT-TYPE
    SYNTAX SEQUENCE OF VmCurCfgGroupMaclistEntry
    MAX-ACCESS not-accessible
    STATUS current
    DESCRIPTION
        "Virtual machine group current configuration table."
    ::= {vmGroups 3 }

vmCurCfgGroupMaclistEntry OBJECT-TYPE
    SYNTAX VmCurCfgGroupMaclistEntry
    MAX-ACCESS not-accessible
    STATUS current
    DESCRIPTION
         "Information about virtual machine group configuration. Indexes are:
          - vmCurCfgGroupMacGroupIndex - group number
          - vmCurCfgGroupMacVMIndex - virtual machine config index"

    INDEX { vmCurCfgGroupMacGroupIndex, vmCurCfgGroupMacVMIndex}
    ::= { vmCurCfgGroupMacTable  1 }

VmCurCfgGroupMaclistEntry ::= SEQUENCE {
    vmCurCfgGroupMacGroupIndex Unsigned32,
    vmCurCfgGroupMacVMIndex    Unsigned32,
    vmCurCfgGroupMacVMMac      PhysAddress
    }

vmCurCfgGroupMacGroupIndex OBJECT-TYPE
    SYNTAX Unsigned32
    MAX-ACCESS read-only
    STATUS current
    DESCRIPTION
        "The group number for which the info is related."
    ::= { vmCurCfgGroupMaclistEntry 1 }

vmCurCfgGroupMacVMIndex OBJECT-TYPE
    SYNTAX Unsigned32
    MAX-ACCESS read-only
    STATUS current
    DESCRIPTION
        "The virtual machine number for which the info is related."
    ::= { vmCurCfgGroupMaclistEntry 2 }

vmCurCfgGroupMacVMMac OBJECT-TYPE
    SYNTAX PhysAddress
    MAX-ACCESS read-only
    STATUS current
    DESCRIPTION
        "virtual machine MAC address."
    ::= {vmCurCfgGroupMaclistEntry 3}

vmNewCfgGroupMacTable OBJECT-TYPE
    SYNTAX SEQUENCE OF VmNewCfgGroupMaclistEntry
    MAX-ACCESS not-accessible
    STATUS current
    DESCRIPTION
        "virtual machine group new configuration table."
    ::= { vmGroups 4 }


vmNewCfgGroupMaclistEntry OBJECT-TYPE
    SYNTAX VmNewCfgGroupMaclistEntry
    MAX-ACCESS not-accessible
    STATUS current
    DESCRIPTION
         "Information about virtual machine group"
    INDEX { vmNewCfgGroupMacGroupIndex, vmNewCfgGroupMacVMIndex}
    ::= { vmNewCfgGroupMacTable  1 }

VmNewCfgGroupMaclistEntry ::= SEQUENCE {
    vmNewCfgGroupMacGroupIndex Unsigned32,
    vmNewCfgGroupMacVMIndex    Unsigned32,
    vmNewCfgGroupMacVMMac      PhysAddress
    }

vmNewCfgGroupMacGroupIndex OBJECT-TYPE
    SYNTAX Unsigned32
    MAX-ACCESS read-only
    STATUS current
    DESCRIPTION
        "The group number for which the info is related."
    ::= { vmNewCfgGroupMaclistEntry 1 }
vmNewCfgGroupMacVMIndex OBJECT-TYPE
    SYNTAX Unsigned32
    MAX-ACCESS read-only
    STATUS current
    DESCRIPTION
        "The virtual machine number for which the info is related."
    ::= { vmNewCfgGroupMaclistEntry 2 }

vmNewCfgGroupMacVMMac OBJECT-TYPE
    SYNTAX PhysAddress
    MAX-ACCESS read-only
    STATUS current
    DESCRIPTION
        "The virtual machine MAC address."
    ::= {vmNewCfgGroupMaclistEntry 3 }


-- ------------------------------------------------------------------------- --
-- VM Policy Configuration                                                 {
-- ------------------------------------------------------------------------- --

-- ------------------------------------------------------------------------- --
-- VM Bandwidth Current Configuration                                      {
-- ------------------------------------------------------------------------- --
vmbwCurCfgTable OBJECT-TYPE
    SYNTAX      SEQUENCE OF VmbwCurCfgEntry
    MAX-ACCESS  not-accessible
    STATUS      current
    DESCRIPTION
        "The table of current VM Bandwidth configuration."
    ::= { vmbw 1 }

vmbwCurCfgEntry OBJECT-TYPE
    SYNTAX      VmbwCurCfgEntry
    MAX-ACCESS  not-accessible
    STATUS      current
    DESCRIPTION
        "A row in the current VM bandwidth table."
    INDEX   { vmbwCurCfgMac }
    ::= { vmbwCurCfgTable 1 }

VmbwCurCfgEntry ::= SEQUENCE {
    vmbwCurCfgMac       MacAddress,
    vmbwCurCfgTxRate    Unsigned32,
    vmbwCurCfgTxBurst   Unsigned32,
    vmbwCurCfgTxAclId   Unsigned32,
    vmbwCurCfgRxRate    Unsigned32,
    vmbwCurCfgRxBurst   Unsigned32,
    vmbwCurCfgCtrl      INTEGER
    }

vmbwCurCfgMac OBJECT-TYPE
    SYNTAX      MacAddress
    MAX-ACCESS  read-only
    STATUS      current
    DESCRIPTION
        "MAC address of VM for which bandwidth control information is related."
    ::= { vmbwCurCfgEntry 1 }

vmbwCurCfgTxRate OBJECT-TYPE
    SYNTAX      Unsigned32
    MAX-ACCESS  read-only
    STATUS      current
    DESCRIPTION
        "VM transmit bandwidth committed rate in kbps (ingress for switch)."
    ::= { vmbwCurCfgEntry 2 }

vmbwCurCfgTxBurst OBJECT-TYPE
    SYNTAX      Unsigned32
    MAX-ACCESS  read-only
    STATUS      current
    DESCRIPTION
        "VM transmit bandwidth max burst size in kilobits (ingress for switch)."
    ::= { vmbwCurCfgEntry 3 }

vmbwCurCfgTxAclId OBJECT-TYPE
    SYNTAX      Unsigned32
    MAX-ACCESS  read-only
    STATUS      current
    DESCRIPTION
        "ACL used for VM transmit bandwidth."
    ::= { vmbwCurCfgEntry 4 }

vmbwCurCfgRxRate OBJECT-TYPE
    SYNTAX      Unsigned32
    MAX-ACCESS  read-only
    STATUS      current
    DESCRIPTION
        "VM receive bandwidth committed rate in kbps (egress for switch)."
    ::= { vmbwCurCfgEntry 5 }

vmbwCurCfgRxBurst OBJECT-TYPE
    SYNTAX      Unsigned32
    MAX-ACCESS  read-only
    STATUS      current
    DESCRIPTION
        "VM receive bandwidth max burst size in kilobits (egress for switch)."
    ::= { vmbwCurCfgEntry 6 }

vmbwCurCfgCtrl OBJECT-TYPE
    SYNTAX  INTEGER {
        enabled(1),
        disabled(2)
        }
    MAX-ACCESS  read-only
    STATUS      current
    DESCRIPTION
        "Enable/Disable VM bandwidth control entry."
    ::= { vmbwCurCfgEntry 7 }
-- ------------------------------------------------------------------------- --
-- VM Bandwidth Current Configuration (end)                                }
-- ------------------------------------------------------------------------- --

-- ------------------------------------------------------------------------- --
-- VM Bandwidth New Configuration                                          {
-- ------------------------------------------------------------------------- --
vmbwNewCfgTable OBJECT-TYPE
    SYNTAX      SEQUENCE OF VmbwNewCfgEntry
    MAX-ACCESS  not-accessible
    STATUS      current
    DESCRIPTION
        "The table of new VM Bandwidth configuration."
    ::= { vmbw 2 }

vmbwNewCfgEntry OBJECT-TYPE
    SYNTAX  VmbwNewCfgEntry
    MAX-ACCESS  not-accessible
    STATUS      current
    DESCRIPTION
        "A row in the new VM bandwidth table."
    INDEX   { vmbwNewCfgMac }
    ::= { vmbwNewCfgTable 1 }

VmbwNewCfgEntry ::= SEQUENCE {
    vmbwNewCfgMac       MacAddress,
    vmbwNewCfgTxRate    Unsigned32,
    vmbwNewCfgTxBurst   Unsigned32,
    vmbwNewCfgTxAclId   Unsigned32,
    vmbwNewCfgRxRate    Unsigned32,
    vmbwNewCfgRxBurst   Unsigned32,
    vmbwNewCfgCtrl      INTEGER,
    vmbwNewCfgDelete    INTEGER
    }

vmbwNewCfgMac OBJECT-TYPE
    SYNTAX      MacAddress
    MAX-ACCESS  read-only
    STATUS      current
    DESCRIPTION
        "MAC address of VM for which bandwidth control information is related."
    ::= { vmbwNewCfgEntry 1 }

vmbwNewCfgTxRate OBJECT-TYPE
    SYNTAX      Unsigned32
    MAX-ACCESS  read-write
    STATUS      current
    DESCRIPTION
        "VM transmit bandwidth committed rate in kbps (ingress for switch).
         Set this to zero to disable transmit bandwidth control."
    ::= { vmbwNewCfgEntry 2 }

vmbwNewCfgTxBurst OBJECT-TYPE
    SYNTAX      Unsigned32
    MAX-ACCESS  read-write
    STATUS      current
    DESCRIPTION
        "VM transmit bandwidth max burst size in kilobits (ingress for switch).
         Set this to zero to disable transmit bandwidth control."
    ::= { vmbwNewCfgEntry 3 }

vmbwNewCfgTxAclId OBJECT-TYPE
    SYNTAX      Unsigned32
    MAX-ACCESS  read-write
    STATUS      current
    DESCRIPTION
        "ACL used for VM transmit bandwidth.
         This is optional parameter. If set to zero the system will choose
         one ACL for tx bandwidth control."
    ::= { vmbwNewCfgEntry 4 }

vmbwNewCfgRxRate OBJECT-TYPE
    SYNTAX      Unsigned32
    MAX-ACCESS  read-write
    STATUS      current
    DESCRIPTION
        "VM receive bandwidth committed rate in kbps (egress for switch).
         Set this to zero to disable receive bandwidth control."
    ::= { vmbwNewCfgEntry 5 }

vmbwNewCfgRxBurst OBJECT-TYPE
    SYNTAX      Unsigned32
    MAX-ACCESS  read-write
    STATUS      current
    DESCRIPTION
        "VM receive bandwidth max burst size in kilobits (egress for switch).
         Set this to zero to disable receive bandwidth control."
    ::= { vmbwNewCfgEntry 6 }

vmbwNewCfgCtrl OBJECT-TYPE
    SYNTAX  INTEGER {
        enabled(1),
        disabled(2)
        }
    MAX-ACCESS  read-write
    STATUS      current
    DESCRIPTION
        "VM bandwidth control entry status"
    ::= { vmbwNewCfgEntry 7 }

vmbwNewCfgDelete OBJECT-TYPE
    SYNTAX  INTEGER {
        other(1),
        delete(2)
        }
    MAX-ACCESS  read-write
    STATUS      current
    DESCRIPTION
        "This is an action object to delete a VM Bandwidth entry.
         other(1) is returned always when read.
         To delete an entry enter delete(2)."
    ::= { vmbwNewCfgEntry 8 }
-- ------------------------------------------------------------------------- --
-- VM Bandwidth New Configuration (end)                                    }
-- ------------------------------------------------------------------------- --

-- ------------------------------------------------------------------------- --
-- VM Policy Configuration (end)                                           }
-- ------------------------------------------------------------------------- --


-- ------------------------------------------------------------------------- --
-- VM Check Configuration                                                 {
-- ------------------------------------------------------------------------- --

vmCurCfgCheck OBJECT IDENTIFIER
    ::= { vmCheck 1 }
vmNewCfgCheck OBJECT IDENTIFIER
    ::= { vmCheck 2 }

vmCurCfgCheckActionBasic OBJECT-TYPE
    SYNTAX INTEGER {
        log(1),
        link(2)
        }
    MAX-ACCESS read-only 
    STATUS current
    DESCRIPTION
      "Current settings for basic checking mode"
    ::= { vmCurCfgCheck 1 }

vmCurCfgCheckActionAdvanced OBJECT-TYPE
    SYNTAX INTEGER {
        log(1),
        link(2),
        acl(3)
        }
    MAX-ACCESS read-only
    STATUS current
    DESCRIPTION
      "Current settings for advanced checking mode"
    ::= { vmCurCfgCheck 2 }


vmCurCfgCheckAclsMax OBJECT-TYPE
    SYNTAX Integer32
    MAX-ACCESS read-only
    STATUS current
    DESCRIPTION
      "Current value for the maximum number of ACLs that can be used by Mac Spoofing Check feature"
    ::= { vmCurCfgCheck 3 }

vmCurCfgCheckTrust OBJECT-TYPE
    SYNTAX  OCTET STRING
    MAX-ACCESS read-only
    STATUS  current
    DESCRIPTION
        "Current value for the configured trusted port list. The ports are presented in bitmap format.
         in receiving order:

             OCTET 1  OCTET 2  .....
             xxxxxxxx xxxxxxxx .....
             ||    || |_ port 8
             ||    ||
             ||    ||___ port 7
             ||    |____ port 6
             ||      .    .   .
             ||_________ port 1
             |__________ reserved

         where x : 1 - The represented port belongs to the trusted ports list
                   0 - The represented port does not belong to the trusted ports list"
    ::= { vmCurCfgCheck 4 }

vmNewCfgCheckActionBasic OBJECT-TYPE
    SYNTAX INTEGER {
        log(1),
        link(2)
        }
    MAX-ACCESS read-write
    STATUS current
    DESCRIPTION
      "New settings for basic checking mode"
    ::= { vmNewCfgCheck 1 }

vmNewCfgCheckActionAdvanced OBJECT-TYPE
    SYNTAX INTEGER {
        log(1),
        link(2),
        acl(3)
        }
    MAX-ACCESS read-write
    STATUS current
    DESCRIPTION
      "New settings for advanced checking mode"
    ::= { vmNewCfgCheck 2 }


vmNewCfgCheckAclsMax OBJECT-TYPE
    SYNTAX Integer32
    MAX-ACCESS read-write
    STATUS current
    DESCRIPTION
      "New value for the maximum number of ACLs that can be used by Mac Spoofing Check feature"
    ::= { vmNewCfgCheck 3 }

vmNewCfgCheckTrust OBJECT-TYPE
    SYNTAX  OCTET STRING
    MAX-ACCESS  read-only
    STATUS current
    DESCRIPTION
        "New value for the configured trusted port list. The ports are presented in bitmap format.
         in receiving order:

             OCTET 1  OCTET 2  .....
             xxxxxxxx xxxxxxxx .....
             ||    || |_ port 8
             ||    ||
             ||    ||___ port 7
             ||    |____ port 6
             ||      .    .   .
             ||_________ port 1
             |__________ reserved

         where x : 1 - The represented port belongs to the trusted ports list
                   0 - The represented port does not belong to the trusted ports list"
    ::= { vmNewCfgCheck 4 }


vmNewCfgCheckTrustAddPort OBJECT-TYPE
    SYNTAX  PortNumber
    MAX-ACCESS  read-write
    STATUS current
    DESCRIPTION
        "Add port to the configured trusted port list."
    ::= { vmNewCfgCheck 5 }


vmNewCfgCheckTrustRemPort OBJECT-TYPE
    SYNTAX  PortNumber
    MAX-ACCESS  read-write
    STATUS current
    DESCRIPTION
        "Remove port from the configured trusted port list."
    ::= { vmNewCfgCheck 6 }



-- ------------------------------------------------------------------------- --
-- VM Profiles Configuration                                                 {
-- ------------------------------------------------------------------------- --
vmCurCfgProfilesTable  OBJECT-TYPE
    SYNTAX SEQUENCE OF VmCurCfgProfileEntry
    MAX-ACCESS not-accessible
    STATUS current
    DESCRIPTION
      "The table of VM profiles in the current config"
    ::= { vmProfiles 1 }

vmCurCfgProfileEntry OBJECT-TYPE
    SYNTAX VmCurCfgProfileEntry
    MAX-ACCESS not-accessible
    STATUS current
    DESCRIPTION
      "Information about a VM profile in current config."
    INDEX { vmCurCfgProfileIndex }
    ::= { vmCurCfgProfilesTable 1 }

VmCurCfgProfileEntry ::= SEQUENCE {
    vmCurCfgProfileIndex            Integer32,
    vmCurCfgProfileName             DisplayString,
    vmCurCfgProfileVlan             INTEGER,
    vmCurCfgProfileShapingAverage   Integer32,
    vmCurCfgProfileShapingBurst     Integer32,
	vmCurCfgProfileShapingPeak      Integer32
	, vmCurCfgProfileEgressShapingAverage   Integer32,
    vmCurCfgProfileEgressShapingBurst     Integer32,
    vmCurCfgProfileEgressShapingPeak      Integer32
    }

vmCurCfgProfileIndex OBJECT-TYPE
    SYNTAX  Integer32
    MAX-ACCESS  read-only
    STATUS  current
    DESCRIPTION
        "The index of the vm profiles table (1..32)."
    ::= { vmCurCfgProfileEntry 1}

vmCurCfgProfileName OBJECT-TYPE
    SYNTAX  DisplayString (SIZE(0..40))
    MAX-ACCESS  read-only
    STATUS  current
    DESCRIPTION
        "VM Profile name."
    ::= { vmCurCfgProfileEntry 2}

vmCurCfgProfileVlan OBJECT-TYPE
    SYNTAX  INTEGER
    MAX-ACCESS  read-only
    STATUS  current
    DESCRIPTION
        "Current VM Profile VLAN Id"
    ::= { vmCurCfgProfileEntry 3}

vmCurCfgProfileShapingAverage OBJECT-TYPE
    SYNTAX  Integer32 
    MAX-ACCESS  read-only
    STATUS  current
    DESCRIPTION
        "Current VM Profile Shaping Average."
    ::= { vmCurCfgProfileEntry 4}

vmCurCfgProfileShapingBurst OBJECT-TYPE
    SYNTAX  Integer32 
    MAX-ACCESS  read-only
    STATUS  current
    DESCRIPTION
        "Current VM Profile Shaping Burst."
    ::= { vmCurCfgProfileEntry 5}

vmCurCfgProfileShapingPeak OBJECT-TYPE
    SYNTAX  Integer32 
    MAX-ACCESS  read-only
    STATUS  current
    DESCRIPTION
        "Current VM Profile Shaping Peak."
    ::= { vmCurCfgProfileEntry 6}

vmCurCfgProfileEgressShapingAverage OBJECT-TYPE
    SYNTAX  Integer32
    MAX-ACCESS  read-only
    STATUS  current
    DESCRIPTION
        "Current VM Profile Egress Shaping Average."
    ::= { vmCurCfgProfileEntry 7}

vmCurCfgProfileEgressShapingBurst OBJECT-TYPE
    SYNTAX  Integer32
    MAX-ACCESS  read-only
    STATUS  current
    DESCRIPTION
        "Current VM Profile Egress Shaping Burst."
    ::= { vmCurCfgProfileEntry 8}

vmCurCfgProfileEgressShapingPeak OBJECT-TYPE
    SYNTAX  Integer32
    MAX-ACCESS  read-only
    STATUS  current
    DESCRIPTION
        "Current VM Profile Egress Shaping Peak."
    ::= { vmCurCfgProfileEntry 9}

vmNewCfgProfilesTable  OBJECT-TYPE
    SYNTAX SEQUENCE OF VmNewCfgProfileEntry
    MAX-ACCESS not-accessible
    STATUS current
    DESCRIPTION
      "The table of VM profiles in the current config"
    ::= { vmProfiles 2 }

vmNewCfgProfileEntry OBJECT-TYPE
    SYNTAX VmNewCfgProfileEntry
    MAX-ACCESS not-accessible
    STATUS current
    DESCRIPTION
      "Information about a VM profile in current config."
    INDEX { vmNewCfgProfileIndex }
    ::= { vmNewCfgProfilesTable 1 }

VmNewCfgProfileEntry ::= SEQUENCE {
    vmNewCfgProfileIndex      Integer32,
    vmNewCfgProfileName       DisplayString,
    vmNewCfgProfileVlan       INTEGER,
    vmNewCfgProfileShapingAverage  Integer32,
    vmNewCfgProfileShapingBurst    Integer32,
    vmNewCfgProfileShapingPeak     Integer32,
    vmNewCfgProfileDelete          INTEGER
	, vmNewCfgProfileEgressShapingAverage  Integer32,
    vmNewCfgProfileEgressShapingBurst    Integer32,
    vmNewCfgProfileEgressShapingPeak     Integer32
    }

vmNewCfgProfileIndex OBJECT-TYPE
    SYNTAX  Integer32
    MAX-ACCESS  read-only
    STATUS  current
    DESCRIPTION
        "The index of the vm profiles table (1..32)."
    ::= { vmNewCfgProfileEntry 1}

vmNewCfgProfileName OBJECT-TYPE
    SYNTAX  DisplayString (SIZE(1..39))
    MAX-ACCESS  read-write
    STATUS  current
    DESCRIPTION
        "VM Profile name."
    ::= { vmNewCfgProfileEntry 2}
 

vmNewCfgProfileVlan OBJECT-TYPE
    SYNTAX  INTEGER
    MAX-ACCESS  read-write
    STATUS  current
    DESCRIPTION
        "Vlan to be used by the VM profile."
    ::= { vmNewCfgProfileEntry 3}

vmNewCfgProfileShapingAverage OBJECT-TYPE
    SYNTAX  Integer32 
    MAX-ACCESS  read-write
    STATUS  current
    DESCRIPTION
        "Shaping average to be used by the VM profile."
    ::= { vmNewCfgProfileEntry 4}

vmNewCfgProfileShapingBurst OBJECT-TYPE
    SYNTAX  Integer32 
    MAX-ACCESS  read-write
    STATUS  current
    DESCRIPTION
        "Shaping burst to be used by the VM profile."
    ::= { vmNewCfgProfileEntry 5}

vmNewCfgProfileShapingPeak OBJECT-TYPE
    SYNTAX  Integer32 
    MAX-ACCESS  read-write
    STATUS  current
    DESCRIPTION
        "Shaping peak to be used by the VM profile."
    ::= { vmNewCfgProfileEntry 6}

vmNewCfgProfileDelete  OBJECT-TYPE
    SYNTAX  INTEGER {
        none(1),
        delete(2)
        }
    MAX-ACCESS  read-write
    STATUS  current
    DESCRIPTION
        "Delete VM Profile."
    ::= { vmNewCfgProfileEntry 7}

vmNewCfgProfileEgressShapingAverage OBJECT-TYPE
    SYNTAX  Integer32
    MAX-ACCESS  read-write
    STATUS  current
    DESCRIPTION
        "Egress shaping average to be used by the VM profile."
    ::= { vmNewCfgProfileEntry 8}

vmNewCfgProfileEgressShapingBurst OBJECT-TYPE
    SYNTAX  Integer32
    MAX-ACCESS  read-write
    STATUS  current
    DESCRIPTION
        "Egress shaping burst to be used by the VM profile."
    ::= { vmNewCfgProfileEntry 9}

vmNewCfgProfileEgressShapingPeak OBJECT-TYPE
    SYNTAX  Integer32
    MAX-ACCESS  read-write
    STATUS  current
    DESCRIPTION
        "Egress shaping peak to be used by the VM profile."
    ::= { vmNewCfgProfileEntry 10}


-- ------------------------------------------------------------------------- --
-- VM Profiles Configuration (end)                                           }
-- ------------------------------------------------------------------------- --

-- ------------------------------------------------------------------------- --
-- VMware information
-- ------------------------------------------------------------------------- --

virtVMwareNameTableUpdate OBJECT-TYPE
    SYNTAX  INTEGER {
        ok(1),
        get(2)
        }
    MAX-ACCESS  read-write
    STATUS  current
    DESCRIPTION
    "This is an action object to get information from the Virtual Center.

     Set this value to get(2) to update the host and VM name tables:
        virtVMwareHostNameTable,
        virtVMwareVMNameTable
     with information from the Virtual Center.

     These two tables can be querried by subsequent Get operations
     without accessing the Virtual Center.
     To refresh these two tables, set virtVMwareNameTableUpdate again.

     ok(1) is returned always when read."
    ::= { virtVMware 1 }

virtVMwareHostNameTable  OBJECT-TYPE
    SYNTAX SEQUENCE OF VirtVMwareHostNameEntry
    MAX-ACCESS not-accessible
    STATUS current
    DESCRIPTION
      "The table of names of VMware hosts in the Virtual Center."
    ::= { virtVMware 2 }

virtVMwareHostNameEntry OBJECT-TYPE
    SYNTAX VirtVMwareHostNameEntry
    MAX-ACCESS not-accessible
    STATUS current
    DESCRIPTION
      "Information about names of VMware hosts in the Data Center."
    INDEX { virtVMwareHostNameIndex }
    ::= { virtVMwareHostNameTable 1 }

VirtVMwareHostNameEntry ::= SEQUENCE {
    virtVMwareHostNameIndex      Integer32,
    virtVMwareHostNameUUID       DisplayString,
    virtVMwareHostNameIpAddress  DisplayString,
    virtVMwareHostNameName       DisplayString
    }

virtVMwareHostNameIndex OBJECT-TYPE
    SYNTAX  Integer32
    MAX-ACCESS  read-only
    STATUS  current
    DESCRIPTION
        "The index of the virtVMwareHostNameTable table."
    ::= { virtVMwareHostNameEntry 1}

virtVMwareHostNameUUID OBJECT-TYPE
    SYNTAX  DisplayString(SIZE(0..64))
    MAX-ACCESS  read-only
    STATUS  current
    DESCRIPTION
        "The UUID of a VMware host."
    ::= { virtVMwareHostNameEntry 2}

virtVMwareHostNameIpAddress OBJECT-TYPE
    SYNTAX  DisplayString(SIZE(0..64))
    MAX-ACCESS  read-only
    STATUS  current
    DESCRIPTION
        "The IP address of a VMware host."
    ::= { virtVMwareHostNameEntry 3}

virtVMwareHostNameName OBJECT-TYPE
    SYNTAX  DisplayString(SIZE(0..64))
    MAX-ACCESS  read-only
    STATUS  current
    DESCRIPTION
        "The name of a VMware host."
    ::= { virtVMwareHostNameEntry 4}

virtVMwareVMNameTable  OBJECT-TYPE
    SYNTAX SEQUENCE OF VirtVMwareVMNameEntry
    MAX-ACCESS not-accessible
    STATUS current
    DESCRIPTION
      "The table of VMware virtual machines in the Data Center."
    ::= { virtVMware 3 }

virtVMwareVMNameEntry OBJECT-TYPE
    SYNTAX VirtVMwareVMNameEntry
    MAX-ACCESS not-accessible
    STATUS current
    DESCRIPTION
      "Information about VMware virtual machines in the Data Center."
    INDEX { virtVMwareVMNameIndex }
    ::= { virtVMwareVMNameTable 1 }

VirtVMwareVMNameEntry ::= SEQUENCE {
    virtVMwareVMNameIndex      Integer32,
    virtVMwareVMNameUUID       DisplayString,
    virtVMwareVMNameVMwareName DisplayString,
    virtVMwareVMNameOsName     DisplayString,
    virtVMwareVMNameIpAddress  DisplayString
    }

virtVMwareVMNameIndex OBJECT-TYPE
    SYNTAX  Integer32
    MAX-ACCESS  read-only
    STATUS  current
    DESCRIPTION
        "The index of the VMware virtual machine table in the Data Center."
    ::= { virtVMwareVMNameEntry 1}

virtVMwareVMNameUUID OBJECT-TYPE
    SYNTAX  DisplayString(SIZE(0..64))
    MAX-ACCESS  read-only
    STATUS  current
    DESCRIPTION
        "The UUID of a virtual machine."
    ::= { virtVMwareVMNameEntry 2}

virtVMwareVMNameVMwareName OBJECT-TYPE
    SYNTAX  DisplayString(SIZE(0..64))
    MAX-ACCESS  read-only
    STATUS  current
    DESCRIPTION
        "The name of a virtual machine given by VMware."
    ::= { virtVMwareVMNameEntry 3}

virtVMwareVMNameOsName OBJECT-TYPE
    SYNTAX  DisplayString(SIZE(0..64))
    MAX-ACCESS  read-only
    STATUS  current
    DESCRIPTION
        "The name of a virtual machine given by the host OS."
    ::= { virtVMwareVMNameEntry 4}

virtVMwareVMNameIpAddress OBJECT-TYPE
    SYNTAX  DisplayString(SIZE(0..64))
    MAX-ACCESS  read-only
    STATUS  current
    DESCRIPTION
        "The IP address of a virtual machine."
    ::= { virtVMwareVMNameEntry 5}

virtVMwareHost OBJECT-TYPE
    SYNTAX  DisplayString
    MAX-ACCESS  read-write
    STATUS  current
    DESCRIPTION
    "VMware host ID

     This is an action object to get information about a specific
     host from the Virtual Center.

     This object specifies the host ID by
     UUID / IP Address / Name.

     Setting this objects populates the following 3 tables:
        virtVMwareHostVswitchTable,
        virtVMwareHostPGTable,
        virtVMwareHostDetailInfoTable
     with the host's networking information from the Virtul
     Center.

     These three tables can be querried by subsequent Get
     operations without accessing the Virtual Center.
     To refresh these tables, set this object to the target host."
    ::= { virtVMware 4 }

virtVMwareHostVswitchTable  OBJECT-TYPE
    SYNTAX SEQUENCE OF VirtVMwareHostVswitchEntry
    MAX-ACCESS not-accessible
    STATUS current
    DESCRIPTION
      "The table of Vswitches available on the specified host."
    ::= { virtVMware 5 }

virtVMwareHostVswitchEntry OBJECT-TYPE
    SYNTAX VirtVMwareHostVswitchEntry
    MAX-ACCESS not-accessible
    STATUS current
    DESCRIPTION
      "Information about Vswitches available on the specified host."
    INDEX { virtVMwareHostVswitchIndex }
    ::= { virtVMwareHostVswitchTable 1 }

VirtVMwareHostVswitchEntry ::= SEQUENCE {
    virtVMwareHostVswitchIndex    Integer32,
    virtVMwareHostVswitchName     DisplayString
    }

virtVMwareHostVswitchIndex OBJECT-TYPE
    SYNTAX  Integer32
    MAX-ACCESS  read-only
    STATUS  current
    DESCRIPTION
        "The index of the Vswitch table on the specified host."
    ::= { virtVMwareHostVswitchEntry 1}

virtVMwareHostVswitchName OBJECT-TYPE
    SYNTAX  DisplayString
    MAX-ACCESS  read-only
    STATUS  current
    DESCRIPTION
        "The name of a Vswitch on the specified host."
    ::= { virtVMwareHostVswitchEntry 2}

virtVMwareHostPGTable  OBJECT-TYPE
    SYNTAX SEQUENCE OF VirtVMwareHostPGEntry
    MAX-ACCESS not-accessible
    STATUS current
    DESCRIPTION
      "The table of Port Groups available on the specified host."
    ::= { virtVMware 6 }

virtVMwareHostPGEntry OBJECT-TYPE
    SYNTAX VirtVMwareHostPGEntry
    MAX-ACCESS not-accessible
    STATUS current
    DESCRIPTION
      "Information about Port Groups available on the specified host."
    INDEX { virtVMwareHostPGIndex }
    ::= { virtVMwareHostPGTable 1 }

VirtVMwareHostPGEntry ::= SEQUENCE {
    virtVMwareHostPGIndex       Integer32,
    virtVMwareHostPGName        DisplayString,
    virtVMwareHostPGVswitchName DisplayString
    }

virtVMwareHostPGIndex OBJECT-TYPE
    SYNTAX  Integer32
    MAX-ACCESS  read-only
    STATUS  current
    DESCRIPTION
        "The index of the Port Group table on the specified host."
    ::= { virtVMwareHostPGEntry 1}

virtVMwareHostPGName OBJECT-TYPE
    SYNTAX  DisplayString
    MAX-ACCESS  read-only
    STATUS  current
    DESCRIPTION
        "The name of a Port Group on the specified host."
    ::= { virtVMwareHostPGEntry 2}

virtVMwareHostPGVswitchName OBJECT-TYPE
    SYNTAX  DisplayString
    MAX-ACCESS  read-only
    STATUS  current
    DESCRIPTION
        "The name of a Vswitch on the specified host."
    ::= { virtVMwareHostPGEntry 3}

virtVMwareHostDetailInfoTable  OBJECT-TYPE
    SYNTAX SEQUENCE OF VirtVMwareHostDetailInfoEntry
    MAX-ACCESS not-accessible
    STATUS current
    DESCRIPTION
      "The table of detailed information available on the specified 
       host/VM interface."
    ::= { virtVMware 7 }

virtVMwareHostDetailInfoEntry OBJECT-TYPE
    SYNTAX VirtVMwareHostDetailInfoEntry
    MAX-ACCESS not-accessible
    STATUS current
    DESCRIPTION
      "Detailed information available on the specified host/VM interface."
    INDEX { virtVMwareHostDetailInfoIndex }
    ::= { virtVMwareHostDetailInfoTable 1 }

VirtVMwareHostDetailInfoEntry ::= SEQUENCE {
    virtVMwareHostDetailInfoIndex         Integer32,
    virtVMwareHostDetailInfoMACAddr       DisplayString,
    virtVMwareHostDetailInfoPort          DisplayString,
    virtVMwareHostDetailInfoType          DisplayString,
    virtVMwareHostDetailInfoIPAddr        DisplayString,
    virtVMwareHostDetailInfoUUID          DisplayString,
    virtVMwareHostDetailInfoVswitch       DisplayString,
    virtVMwareHostDetailInfoPortGroup     DisplayString,
    virtVMwareHostDetailInfoVlanID        DisplayString,
    virtVMwareHostDetailInfoHostName      DisplayString,
    virtVMwareHostDetailInfoVMVCenterName DisplayString,
    virtVMwareHostDetailInfoVMOSHostName  DisplayString,
    virtVMwareHostDetailInfoVMCurrentHost DisplayString
    }

virtVMwareHostDetailInfoIndex OBJECT-TYPE
    SYNTAX  Integer32
    MAX-ACCESS  read-only
    STATUS  current
    DESCRIPTION
        "The index of the detailed information table on the specified
         host/VM interface."
    ::= { virtVMwareHostDetailInfoEntry 1}

virtVMwareHostDetailInfoMACAddr OBJECT-TYPE
    SYNTAX  DisplayString
    MAX-ACCESS  read-only
    STATUS  current
    DESCRIPTION
        "The MAC address of the host/VM interface."
    ::= { virtVMwareHostDetailInfoEntry 2}

virtVMwareHostDetailInfoPort OBJECT-TYPE
    SYNTAX  DisplayString
    MAX-ACCESS  read-only
    STATUS  current
    DESCRIPTION
        "The port number of the specified host/VM interface."
    ::= { virtVMwareHostDetailInfoEntry 3}

virtVMwareHostDetailInfoType OBJECT-TYPE
    SYNTAX  DisplayString
    MAX-ACCESS  read-only
    STATUS  current
    DESCRIPTION
        "Interface type"
    ::= { virtVMwareHostDetailInfoEntry 4}

virtVMwareHostDetailInfoIPAddr OBJECT-TYPE
    SYNTAX  DisplayString
    MAX-ACCESS  read-only
    STATUS  current
    DESCRIPTION
        "The IP address of the specified host/VM interface."
    ::= { virtVMwareHostDetailInfoEntry 5}

virtVMwareHostDetailInfoUUID OBJECT-TYPE
    SYNTAX  DisplayString
    MAX-ACCESS  read-only
    STATUS  current
    DESCRIPTION
        "The UUID of the specified host/VM interface."
    ::= { virtVMwareHostDetailInfoEntry 6}

virtVMwareHostDetailInfoVswitch OBJECT-TYPE
    SYNTAX  DisplayString
    MAX-ACCESS  read-only
    STATUS  current
    DESCRIPTION
        "The name of the virtual switch of the specified host/VM interface."
    ::= { virtVMwareHostDetailInfoEntry 7}

virtVMwareHostDetailInfoPortGroup OBJECT-TYPE
    SYNTAX  DisplayString
    MAX-ACCESS  read-only
    STATUS  current
    DESCRIPTION
        "The name of the port group of the specified host/VM interface."
    ::= { virtVMwareHostDetailInfoEntry 8}

virtVMwareHostDetailInfoVlanID OBJECT-TYPE
    SYNTAX  DisplayString
    MAX-ACCESS  read-only
    STATUS  current
    DESCRIPTION
        "The VLAN ID of the specified host/VM interface."
    ::= { virtVMwareHostDetailInfoEntry 9}

virtVMwareHostDetailInfoHostName OBJECT-TYPE
    SYNTAX  DisplayString
    MAX-ACCESS  read-only
    STATUS  current
    DESCRIPTION
        "The name of the specified host interface.
         N/A for VMs."
    ::= { virtVMwareHostDetailInfoEntry 10}

virtVMwareHostDetailInfoVMVCenterName OBJECT-TYPE
    SYNTAX  DisplayString
    MAX-ACCESS  read-only
    STATUS  current
    DESCRIPTION
        "The name of the Virtual Center of the specified VM interface.
         N/A for host interfaces."
    ::= { virtVMwareHostDetailInfoEntry 11}

virtVMwareHostDetailInfoVMOSHostName OBJECT-TYPE
    SYNTAX  DisplayString
    MAX-ACCESS  read-only
    STATUS  current
    DESCRIPTION
        "The name of the VM set by the host operating system.
         N/A for host interfaces."
    ::= { virtVMwareHostDetailInfoEntry 12}

virtVMwareHostDetailInfoVMCurrentHost OBJECT-TYPE
    SYNTAX  DisplayString
    MAX-ACCESS  read-only
    STATUS  current
    DESCRIPTION
        "The name of the host of the specified VM.
         N/A for host interfaces."
    ::= { virtVMwareHostDetailInfoEntry 13}

virtVMwareVM OBJECT-TYPE
    SYNTAX  DisplayString
    MAX-ACCESS  read-write
    STATUS  current
    DESCRIPTION
    "VMware virtual machine ID

     This is an action object to get information about a specific
     virtual machine from the Virtual Center.

     This object specifies the VM ID by by 
     UUID / IP Address / Name.

     Setting this object populates the virtVMwareVMInfoTable
     table with networking information for this VM from the
     Virtual Center.

     This table can be querried by subsequent Get operations
     without accessing the Virtual Center.
     To refresh the table, set this object to the target VM. "
    ::= { virtVMware 8 }

virtVMwareVMInfoTable  OBJECT-TYPE
    SYNTAX SEQUENCE OF VirtVMwareVMInfoEntry
    MAX-ACCESS not-accessible
    STATUS current
    DESCRIPTION
      "The table of networking information available on the 
       specified VM."
    ::= { virtVMware 9 }

virtVMwareVMInfoEntry OBJECT-TYPE
    SYNTAX VirtVMwareVMInfoEntry
    MAX-ACCESS not-accessible
    STATUS current
    DESCRIPTION
      "Detailed information available on the specified VM."
    INDEX { virtVMwareVMInfoIndex }
    ::= { virtVMwareVMInfoTable 1 }

VirtVMwareVMInfoEntry ::= SEQUENCE {
    virtVMwareVMInfoIndex         Integer32,
    virtVMwareVMInfoMACAddr       DisplayString,
    virtVMwareVMInfoPort          DisplayString,
    virtVMwareVMInfoType          DisplayString,
    virtVMwareVMInfoIPAddr        DisplayString,
    virtVMwareVMInfoUUID          DisplayString,
    virtVMwareVMInfoVswitch       DisplayString,
    virtVMwareVMInfoPortGroup     DisplayString,
    virtVMwareVMInfoVlanID        DisplayString,
    virtVMwareVMInfoVMVCenterName DisplayString,
    virtVMwareVMInfoVMOSHostName  DisplayString,
    virtVMwareVMInfoVMCurrentHost DisplayString
    }

virtVMwareVMInfoIndex OBJECT-TYPE
    SYNTAX  Integer32
    MAX-ACCESS  read-only
    STATUS  current
    DESCRIPTION
        "The index of the table with information on the
         specified VM."
    ::= { virtVMwareVMInfoEntry 1}

virtVMwareVMInfoMACAddr OBJECT-TYPE
    SYNTAX  DisplayString
    MAX-ACCESS  read-only
    STATUS  current
    DESCRIPTION
        "The MAC address of the specified VM."
    ::= { virtVMwareVMInfoEntry 2}

virtVMwareVMInfoPort OBJECT-TYPE
    SYNTAX  DisplayString
    MAX-ACCESS  read-only
    STATUS  current
    DESCRIPTION
        "The port number of the specified VM."
    ::= { virtVMwareVMInfoEntry 3}

virtVMwareVMInfoType OBJECT-TYPE
    SYNTAX  DisplayString
    MAX-ACCESS  read-only
    STATUS  current
    DESCRIPTION
        "Interface type"
    ::= { virtVMwareVMInfoEntry 4}

virtVMwareVMInfoIPAddr OBJECT-TYPE
    SYNTAX  DisplayString
    MAX-ACCESS  read-only
    STATUS  current
    DESCRIPTION
        "The IP address of the specified VM."
    ::= { virtVMwareVMInfoEntry 5}

virtVMwareVMInfoUUID OBJECT-TYPE
    SYNTAX  DisplayString
    MAX-ACCESS  read-only
    STATUS  current
    DESCRIPTION
        "The UUID of the specified VM."
    ::= { virtVMwareVMInfoEntry 6}

virtVMwareVMInfoVswitch OBJECT-TYPE
    SYNTAX  DisplayString
    MAX-ACCESS  read-only
    STATUS  current
    DESCRIPTION
        "The name of the virtual switch of the specified VM."
    ::= { virtVMwareVMInfoEntry 7}

virtVMwareVMInfoPortGroup OBJECT-TYPE
    SYNTAX  DisplayString
    MAX-ACCESS  read-only
    STATUS  current
    DESCRIPTION
        "The name of the port group of the specified VM."
    ::= { virtVMwareVMInfoEntry 8}

virtVMwareVMInfoVlanID OBJECT-TYPE
    SYNTAX  DisplayString
    MAX-ACCESS  read-only
    STATUS  current
    DESCRIPTION
        "The VLAN ID of the specified VM."
    ::= { virtVMwareVMInfoEntry 9}

virtVMwareVMInfoVMVCenterName OBJECT-TYPE
    SYNTAX  DisplayString
    MAX-ACCESS  read-only
    STATUS  current
    DESCRIPTION
        "The name of the Virtual Center of the specified VM."
    ::= { virtVMwareVMInfoEntry 10}

virtVMwareVMInfoVMOSHostName OBJECT-TYPE
    SYNTAX  DisplayString
    MAX-ACCESS  read-only
    STATUS  current
    DESCRIPTION
        "The name of the VM set by the host operating system."
    ::= { virtVMwareVMInfoEntry 11}

virtVMwareVMInfoVMCurrentHost OBJECT-TYPE
    SYNTAX  DisplayString
    MAX-ACCESS  read-only
    STATUS  current
    DESCRIPTION
        "The name of the host of the specified VM."
    ::= { virtVMwareVMInfoEntry 12}



virtCurCfgVMwareHello     OBJECT IDENTIFIER ::= { virtVMware  10 }
virtNewCfgVMwareHello     OBJECT IDENTIFIER ::= { virtVMware  11 }

virtCurCfgVMwareHelloEnable OBJECT-TYPE
    SYNTAX INTEGER {
        disabled(0),
        enabled(1)
        }
    MAX-ACCESS  read-only
    STATUS  current
    DESCRIPTION
        "Current value for hello advertising status"
    ::= { virtCurCfgVMwareHello 1 }


virtCurCfgVMwareHelloTimer OBJECT-TYPE
    SYNTAX Integer32
    MAX-ACCESS  read-only
    STATUS  current
    DESCRIPTION
        "Current hello packet send interval"
    ::= { virtCurCfgVMwareHello 2 }

virtCurCfgVMwareHelloPorts OBJECT-TYPE
    SYNTAX  OCTET STRING
    MAX-ACCESS  read-only
    STATUS  current
    DESCRIPTION
        "Current value for the configured hello port list. The ports are presented in bitmap format.
         in receiving order:

             OCTET 1  OCTET 2  .....
             xxxxxxxx xxxxxxxx .....
             ||    || |_ port 8
             ||    ||
             ||    ||___ port 7
             ||    |____ port 6
             ||      .    .   .
             ||_________ port 1
             |__________ reserved

         where x : 1 - The represented port belongs to the hello ports list
                   0 - The represented port does not belong to the hello ports list"
    ::= { virtCurCfgVMwareHello 3 }

virtCurCfgVMwareHelloAddr OBJECT-TYPE
    SYNTAX IpAddress
    MAX-ACCESS read-only
    STATUS current
    DESCRIPTION
        "Current VM hello IP address"
    ::= { virtCurCfgVMwareHello 4 }

virtNewCfgVMwareHelloEnable OBJECT-TYPE
    SYNTAX INTEGER {
        disabled(0),
        enabled(1)
        }
    MAX-ACCESS  read-write
    STATUS current
    DESCRIPTION
        "New value for hello advertising status"
    ::= { virtNewCfgVMwareHello 1 }
virtNewCfgVMwareHelloTimer OBJECT-TYPE
    SYNTAX Integer32
    MAX-ACCESS  read-write
    STATUS current
    DESCRIPTION
        "New hello packet send interval"
    ::= { virtNewCfgVMwareHello 2 }

virtNewCfgVMwareHelloPorts OBJECT-TYPE
    SYNTAX  OCTET STRING
    MAX-ACCESS  read-only
    STATUS  current
    DESCRIPTION
        "New value for the configured hello port list. The ports are presented in bitmap format.
         in receiving order:

             OCTET 1  OCTET 2  .....
             xxxxxxxx xxxxxxxx .....
             ||    || |_ port 8
             ||    ||
             ||    ||___ port 7
             ||    |____ port 6
             ||      .    .   .
             ||_________ port 1
             |__________ reserved

         where x : 1 - The represented port belongs to the hello ports list
                   0 - The represented port does not belong to the hello ports list"
    ::= { virtNewCfgVMwareHello 3 }

virtNewCfgVMwareHelloAddPort OBJECT-TYPE
    SYNTAX PortNumber 
    MAX-ACCESS  read-write
    STATUS current
    DESCRIPTION
        "Add a port to the hello port list"
    ::= { virtNewCfgVMwareHello 4 }

virtNewCfgVMwareHelloRemovePort OBJECT-TYPE
    SYNTAX PortNumber 
    MAX-ACCESS  read-write
    STATUS current
    DESCRIPTION
        "Remove a port from the hello port list"
    ::= { virtNewCfgVMwareHello 5 }


virtNewCfgVMwareHelloAddr OBJECT-TYPE
    SYNTAX IpAddress
    MAX-ACCESS read-write
    STATUS current
    DESCRIPTION
        "New VM hello IP address"
    ::= { virtNewCfgVMwareHello 6 }

-- ------------------------------------------------------------------------- --
-- VMware information (end)                                                   }
-- ------------------------------------------------------------------------- --


-- ----------------------------------------------------------------------------
-- VMReady Information                                                        {
-- ----------------------------------------------------------------------------

agVMGroupInfo   OBJECT IDENTIFIER ::= { agentInfo   12 }

vmGroupInfoTbl OBJECT-TYPE
    SYNTAX SEQUENCE OF VMGroupInfolistEntry
    MAX-ACCESS not-accessible
    STATUS current
    DESCRIPTION
        "Virtual MAC information table"
    ::= { agVMGroupInfo 1 }

vmGroupInfolistEntry OBJECT-TYPE
    SYNTAX VMGroupInfolistEntry
    MAX-ACCESS not-accessible
    STATUS current
    DESCRIPTION
        "The run-time information about a virtual machine"
    INDEX { vmGroupInfoIdx }
    ::= { vmGroupInfoTbl 1 }

VMGroupInfolistEntry ::= SEQUENCE {
        vmGroupInfoIdx         Unsigned32,
        vmGroupInfoMac         PhysAddress,
        vmGroupInfoIP          IpAddress,
        vmGroupInfoPort        PortNumber,
        vmGroupInfoGroup       Unsigned32,
        vmGroupInfoVlan        Unsigned32,
        vmGroupInfoIsESXSvcCon Unsigned32
        ,vmGroupInfoIsVMK       Unsigned32,
        vmGroupInfoName        DisplayString,
        vmGroupInfoUUID        DisplayString,
        vmGroupInfoVSwitch     DisplayString,
        vmGroupInfoPortGroup   DisplayString,
        vmGroupInfoHost        DisplayString
    }

vmGroupInfoIdx OBJECT-TYPE
    SYNTAX Unsigned32
    MAX-ACCESS read-only
    STATUS current
    DESCRIPTION
        "Table index, 1 based."
    ::= { vmGroupInfolistEntry 1 }

vmGroupInfoMac OBJECT-TYPE
    SYNTAX  PhysAddress
    MAX-ACCESS read-only
    STATUS current
    DESCRIPTION
        "The virtual machine MAC address."
    ::= {vmGroupInfolistEntry 2 }

vmGroupInfoIP OBJECT-TYPE
    SYNTAX IpAddress
    MAX-ACCESS read-only
    STATUS current
    DESCRIPTION
        "The virtual machine IP address."
    ::= {vmGroupInfolistEntry 3 }

vmGroupInfoPort OBJECT-TYPE
    SYNTAX PortNumber
    MAX-ACCESS read-only
    STATUS current
    DESCRIPTION
        "System port connected to the virtual machine."
    ::= { vmGroupInfolistEntry 4 }

vmGroupInfoGroup OBJECT-TYPE
    SYNTAX  Unsigned32
    MAX-ACCESS read-only
    STATUS current
    DESCRIPTION
        "The virtual machine group."
    ::= {vmGroupInfolistEntry 5 }

vmGroupInfoVlan OBJECT-TYPE
    SYNTAX  Unsigned32
    MAX-ACCESS read-only
    STATUS current
    DESCRIPTION
        "The virtual machine VLAN"
    ::= {vmGroupInfolistEntry 6 }

vmGroupInfoIsESXSvcCon OBJECT-TYPE
    SYNTAX  Unsigned32
    MAX-ACCESS read-only
    STATUS current
    DESCRIPTION
        "Set to 1 if ESX Service Console Interface, else 0."
    ::= {vmGroupInfolistEntry 7 }

vmGroupInfoIsVMK OBJECT-TYPE
    SYNTAX  Unsigned32
    MAX-ACCESS read-only
    STATUS current
    DESCRIPTION
        "Set to 1 if VM Kernel Interface, else 0."
    ::= {vmGroupInfolistEntry 8 }

vmGroupInfoName OBJECT-TYPE
    SYNTAX DisplayString
    MAX-ACCESS read-only
    STATUS current
    DESCRIPTION
        "Virtual Machine Name, if available."
    ::= {vmGroupInfolistEntry 9 }

vmGroupInfoUUID OBJECT-TYPE
    SYNTAX DisplayString
    MAX-ACCESS read-only
    STATUS current
    DESCRIPTION
        "Virtual Machine UUID, if available."
    ::= {vmGroupInfolistEntry 10 }

vmGroupInfoVSwitch OBJECT-TYPE
    SYNTAX DisplayString
    MAX-ACCESS read-only
    STATUS current
    DESCRIPTION
        "Virtual Machine VSwitch, if available."
    ::= {vmGroupInfolistEntry 11 }

vmGroupInfoPortGroup OBJECT-TYPE
    SYNTAX DisplayString
    MAX-ACCESS read-only
    STATUS current
    DESCRIPTION
        "Virtual Machine Port Group, if available."
    ::= {vmGroupInfolistEntry 12 }

vmGroupInfoHost OBJECT-TYPE
    SYNTAX DisplayString
    MAX-ACCESS read-only
    STATUS current
    DESCRIPTION
        "Virtual Machine Host, if available."
    ::= {vmGroupInfolistEntry 13 }

-- ----------------------------------------------------------------------------
-- VMReady Information                                                        }
-- ----------------------------------------------------------------------------


-- ------------------------------------------------------------------------- --
-- VMReady Miscellaneous Configuration                                        {
-- ------------------------------------------------------------------------- --
vmReadyLocalAdmMac OBJECT-TYPE
    SYNTAX INTEGER {
        disabled(0),
        enabled(1)
        }
    MAX-ACCESS  read-write
    STATUS current
    DESCRIPTION
        "Treat locally administred MAC address as VMs"
    ::= { vmReadyMisc 1 }

vmReadyCurCfgOuiTbl OBJECT-TYPE
    SYNTAX      SEQUENCE OF VMReadyCurCfgOuiEntry
    MAX-ACCESS  not-accessible
    STATUS      current
    DESCRIPTION
        "The table of current VM Ready OUI configuration."
    ::= { vmReadyMisc 2 }

vmReadyCurCfgOuiEntry OBJECT-TYPE
    SYNTAX      VMReadyCurCfgOuiEntry
    MAX-ACCESS  not-accessible
    STATUS      current
    DESCRIPTION
        "A row in the current VM Ready OUI table."
    INDEX   { vmReadyCurCfgOuiMacIdx }
    ::= { vmReadyCurCfgOuiTbl 1 }

VMReadyCurCfgOuiEntry ::= SEQUENCE {
    vmReadyCurCfgOuiMacIdx Unsigned32,
    vmReadyCurCfgOuiMac    PhysAddress,
    vmReadyCurCfgVendor    DisplayString
    }

vmReadyCurCfgOuiMacIdx OBJECT-TYPE
    SYNTAX      Unsigned32
    MAX-ACCESS  read-only
    STATUS      current
    DESCRIPTION
        "OUI of locally administred MAC address"
    ::= { vmReadyCurCfgOuiEntry 1 }

vmReadyCurCfgOuiMac OBJECT-TYPE
    SYNTAX      PhysAddress
    MAX-ACCESS  read-only
    STATUS      current
    DESCRIPTION
        "OUI of locally administred MAC address"
    ::= { vmReadyCurCfgOuiEntry 2 }

vmReadyCurCfgVendor OBJECT-TYPE
    SYNTAX          DisplayString
    MAX-ACCESS      read-only
    STATUS          current
    DESCRIPTION
        "Vendor name of the OUI locally administred"
    ::= { vmReadyCurCfgOuiEntry 3 }

vmReadyNewCfgOuiTbl OBJECT-TYPE
    SYNTAX      SEQUENCE OF VMReadyNewCfgOuiEntry
    MAX-ACCESS  not-accessible
    STATUS      current
    DESCRIPTION
        "The table of new VM Ready OUI configuration."
    ::= { vmReadyMisc 3 }

vmReadyNewCfgOuiEntry OBJECT-TYPE
    SYNTAX      VMReadyNewCfgOuiEntry
    MAX-ACCESS  not-accessible
    STATUS      current
    DESCRIPTION
        "A row in the new VM Ready OUI table."
    INDEX   { vmReadyNewCfgOuiMacIdx }
    ::= { vmReadyNewCfgOuiTbl 1 }

VMReadyNewCfgOuiEntry ::= SEQUENCE {
    vmReadyNewCfgOuiMacIdx Unsigned32,
    vmReadyNewCfgOuiMac    DisplayString,
    vmReadyNewCfgVendor    DisplayString,
    vmReadyNewCfgDelete    INTEGER
    }

vmReadyNewCfgOuiMacIdx OBJECT-TYPE
    SYNTAX      Unsigned32
    MAX-ACCESS  read-only
    STATUS      current
    DESCRIPTION
        "OUI of locally administred MAC address"
    ::= { vmReadyNewCfgOuiEntry 1 }


vmReadyNewCfgOuiMac OBJECT-TYPE
    SYNTAX      DisplayString
    MAX-ACCESS  read-write
    STATUS      current
    DESCRIPTION
        "New OUI of locally administred MAC address
         Format xx:yy:zz "
    ::= { vmReadyNewCfgOuiEntry 2 }

vmReadyNewCfgVendor OBJECT-TYPE
    SYNTAX          DisplayString
    MAX-ACCESS      read-write
    STATUS          current
    DESCRIPTION
        "Vendor name of the OUI locally administred"
    ::= { vmReadyNewCfgOuiEntry 3 }

vmReadyNewCfgDelete OBJECT-TYPE
    SYNTAX INTEGER {
        other(0),
        delete(1)
        }
    MAX-ACCESS  read-write
    STATUS current
    DESCRIPTION
        "If set the OUI of the locally administred MAC would be deleted"
    ::= { vmReadyNewCfgOuiEntry 4 }


-- ------------------------------------------------------------------------- --
-- VMReady Miscellaneous Configuration(end)                                  }
-- ------------------------------------------------------------------------- --

-- ----------------------------------------------------------------------------
-- } INSERT: virt
-- ----------------------------------------------------------------------------


vnic                    OBJECT IDENTIFIER ::= { g8264T-mgmt 16 }
-- ----------------------------------------------------------------------------
-- { INSERT: vnic 
-- ----------------------------------------------------------------------------



vnicCurCfgState OBJECT-TYPE 
    SYNTAX      INTEGER {
        enabled(1),
        disabled(2)
        }
    MAX-ACCESS read-only
    STATUS current
    DESCRIPTION
    "VNIC global state."
    ::= { vnic 1 }

vnicNewCfgState OBJECT-TYPE 
    SYNTAX      INTEGER {
        enabled(1),
        disabled(2)
        }
    MAX-ACCESS read-write
    STATUS current
    DESCRIPTION
    "Enable/Disable vNIC."
    ::= { vnic 2 }

    
vnicCurCfgVnicTable OBJECT-TYPE
    SYNTAX SEQUENCE OF VnicCurCfgVnicEntry
    MAX-ACCESS not-accessible
    STATUS current
    DESCRIPTION
    "The table of vNICs"
    ::= { vnic 7 }

vnicCurCfgVnicEntry OBJECT-TYPE
    SYNTAX VnicCurCfgVnicEntry
    MAX-ACCESS not-accessible
    STATUS current
    DESCRIPTION
    "A vNIC in the vnicCurCfgVnicTable"
	INDEX { vnicCurCfgVnicPortIndex, vnicCurCfgVnicIndex }
    ::= { vnicCurCfgVnicTable 1 }

VnicCurCfgVnicEntry ::= SEQUENCE {
    vnicCurCfgVnicPortIndex   PortNumber,
    vnicCurCfgVnicIndex       INTEGER,
    vnicCurCfgVnicState       INTEGER,
    vnicCurCfgVnicBw          INTEGER,
    vnicCurCfgVnicType        INTEGER,
    vnicCurCfgVnicMAC         DisplayString
    }

vnicCurCfgVnicPortIndex OBJECT-TYPE
    SYNTAX   PortNumber
    MAX-ACCESS read-only
    STATUS current
    DESCRIPTION
    "The port number of the vNIC."
    ::= { vnicCurCfgVnicEntry 1 }    

vnicCurCfgVnicIndex OBJECT-TYPE
    SYNTAX   INTEGER 
    MAX-ACCESS read-only
    STATUS current
    DESCRIPTION
    "The vNIC number of the vNIC."
    ::= { vnicCurCfgVnicEntry 2 }    

vnicCurCfgVnicState OBJECT-TYPE
    SYNTAX   INTEGER {
        enabled(1),
        disabled(2)
        }
    MAX-ACCESS read-only
    STATUS current
    DESCRIPTION
    "The state the vNIC."
    ::= { vnicCurCfgVnicEntry 3 }    

vnicCurCfgVnicBw OBJECT-TYPE
    SYNTAX   INTEGER (1..100)
    MAX-ACCESS read-only
    STATUS current
    DESCRIPTION
    "The maximum bandwidth the vNIC."
    ::= { vnicCurCfgVnicEntry 4 }    

vnicCurCfgVnicType OBJECT-TYPE
    SYNTAX   INTEGER {
        default(1),
        fcoe(2),
	iscsi(3)
        }
    MAX-ACCESS read-only
    STATUS current
    DESCRIPTION
    "The type of the vNIC."
    ::= { vnicCurCfgVnicEntry 5 } 

vnicCurCfgVnicMAC OBJECT-TYPE
    SYNTAX   DisplayString
    MAX-ACCESS read-only
    STATUS current
    DESCRIPTION
    "The MAC address of the vNIC."
    ::= { vnicCurCfgVnicEntry 6 }    

vnicNewCfgVnicTable OBJECT-TYPE
    SYNTAX SEQUENCE OF VnicNewCfgVnicEntry
    MAX-ACCESS not-accessible
    STATUS current
    DESCRIPTION
    "The table of vNICs"
    ::= { vnic 8 }

vnicNewCfgVnicEntry OBJECT-TYPE
    SYNTAX VnicNewCfgVnicEntry
    MAX-ACCESS not-accessible
    STATUS current
    DESCRIPTION
    "A vNIC in the vnicNewCfgVnicTable"
	INDEX { vnicNewCfgVnicPortIndex, vnicNewCfgVnicIndex }
    ::= { vnicNewCfgVnicTable 1 }

VnicNewCfgVnicEntry ::= SEQUENCE {
    vnicNewCfgVnicPortIndex   PortNumber,
    vnicNewCfgVnicIndex       INTEGER,
    vnicNewCfgVnicState       INTEGER,
    vnicNewCfgVnicBw          INTEGER
    }

vnicNewCfgVnicPortIndex OBJECT-TYPE
    SYNTAX   PortNumber
    MAX-ACCESS read-only
    STATUS current
    DESCRIPTION
    "The port number of the vNIC."
    ::= { vnicNewCfgVnicEntry 1 }    

vnicNewCfgVnicIndex OBJECT-TYPE
    SYNTAX   INTEGER
    MAX-ACCESS read-only
    STATUS current
    DESCRIPTION
    "The vNIC number of the vNIC."
    ::= { vnicNewCfgVnicEntry 2 }    

vnicNewCfgVnicState OBJECT-TYPE
    SYNTAX   INTEGER {
        enabled(1),
        disabled(2)
        }
    MAX-ACCESS read-write
    STATUS current
    DESCRIPTION
    "The state the vNIC."
    ::= { vnicNewCfgVnicEntry 3 }    

vnicNewCfgVnicBw OBJECT-TYPE
    SYNTAX   INTEGER (1..100)
    MAX-ACCESS read-write
    STATUS current
    DESCRIPTION
    "The maximum bandwidth the vNIC."
    ::= { vnicNewCfgVnicEntry 4 } 

vnicCurCfgGroupTable OBJECT-TYPE
    SYNTAX SEQUENCE OF VnicCurCfgGroupEntry
    MAX-ACCESS not-accessible
    STATUS current
    DESCRIPTION
    "The table of vNIC Groups"
    ::= { vnic 9 }
	
vnicCurCfgGroupEntry OBJECT-TYPE
	SYNTAX VnicCurCfgGroupEntry
	MAX-ACCESS not-accessible
    STATUS current
    DESCRIPTION
    "A vNIC in the vnicCurCfgGroupTable"
	INDEX { vnicCurCfgGroupIndex }
    ::= { vnicCurCfgGroupTable 1}
	
VnicCurCfgGroupEntry ::= SEQUENCE {
    vnicCurCfgGroupIndex          INTEGER,
    vnicCurCfgGroupState          INTEGER,
    vnicCurCfgGroupVlan           INTEGER,
    vnicCurCfgGroupFailoverState  INTEGER,
    vnicCurCfgGroupVnics          DisplayString,
    vnicCurCfgGroupPorts          DisplayString,
    vnicCurCfgGroupTrunk          INTEGER
    }

vnicCurCfgGroupIndex OBJECT-TYPE
    SYNTAX   INTEGER 
    MAX-ACCESS read-only
    STATUS current
    DESCRIPTION
    "The vNIC group number."
    ::= { vnicCurCfgGroupEntry 1 }    

vnicCurCfgGroupState OBJECT-TYPE
    SYNTAX   INTEGER {
        enabled(1),
        disabled(2)
        }
    MAX-ACCESS read-only
    STATUS current
    DESCRIPTION
    "The vNIC group state."
    ::= { vnicCurCfgGroupEntry 2 }    

vnicCurCfgGroupVlan OBJECT-TYPE
    SYNTAX   INTEGER 
    MAX-ACCESS read-only
    STATUS current
    DESCRIPTION
    "The vNIC group vlan number."
    ::= { vnicCurCfgGroupEntry 3 }    

vnicCurCfgGroupFailoverState OBJECT-TYPE
    SYNTAX   INTEGER {
        enabled(1),
        disabled(2)
        }
    MAX-ACCESS read-only
    STATUS current
    DESCRIPTION
    "The vNIC group failover state."
    ::= { vnicCurCfgGroupEntry 4 }    

vnicCurCfgGroupVnics OBJECT-TYPE
    SYNTAX   DisplayString
    MAX-ACCESS read-only
    STATUS current
    DESCRIPTION
    "The vNICs in the vNIC group."
    ::= { vnicCurCfgGroupEntry 5 }    

vnicCurCfgGroupPorts OBJECT-TYPE
    SYNTAX   DisplayString
    MAX-ACCESS read-only
    STATUS current
    DESCRIPTION
    "Non-vNIC Ports and/or uplink port in the vNIC group."
    ::= { vnicCurCfgGroupEntry 6 }    

vnicCurCfgGroupTrunk OBJECT-TYPE
    SYNTAX   INTEGER
    MAX-ACCESS read-only
    STATUS current
    DESCRIPTION
    "Uplink trunk in the vNIC group."
    ::= { vnicCurCfgGroupEntry 7 }    


vnicNewCfgGroupTable OBJECT-TYPE
    SYNTAX SEQUENCE OF VnicNewCfgGroupEntry
    MAX-ACCESS not-accessible
    STATUS current
    DESCRIPTION
    "The table of vNIC Groups"
    ::= { vnic 10 }
	
vnicNewCfgGroupEntry OBJECT-TYPE
	SYNTAX VnicNewCfgGroupEntry
	MAX-ACCESS not-accessible
    STATUS current
    DESCRIPTION
    "A vNIC in the vnicNewCfgGroupTable"
	INDEX { vnicNewCfgGroupIndex }
    ::= { vnicNewCfgGroupTable 1}

VnicNewCfgGroupEntry ::= SEQUENCE {
    vnicNewCfgGroupIndex          INTEGER,
    vnicNewCfgGroupState          INTEGER,
    vnicNewCfgGroupVlan           INTEGER,
    vnicNewCfgGroupFailoverState  INTEGER,
    vnicNewCfgGroupAddVnic        DisplayString,
    vnicNewCfgGroupRemVnic        DisplayString,
    vnicNewCfgGroupAddPort        INTEGER,    
    vnicNewCfgGroupRemPort        INTEGER,
    vnicNewCfgGroupAddTrunk       INTEGER,    
    vnicNewCfgGroupRemTrunk       INTEGER,
    vnicNewCfgGroupDelete         INTEGER,
    vnicNewCfgGroupVnics          DisplayString,
    vnicNewCfgGroupPorts          DisplayString,
    vnicNewCfgGroupTrunk          INTEGER
    }

vnicNewCfgGroupIndex OBJECT-TYPE
    SYNTAX   INTEGER 
    MAX-ACCESS read-only
    STATUS current
    DESCRIPTION
    "The vNIC group number."
    ::= { vnicNewCfgGroupEntry 1 }    

vnicNewCfgGroupState OBJECT-TYPE
    SYNTAX   INTEGER {
        enabled(1),
        disabled(2)
        }
    MAX-ACCESS read-write
    STATUS current
    DESCRIPTION
    "Enable/disalbe the vNIC group."
    ::= { vnicNewCfgGroupEntry 2 }    

vnicNewCfgGroupVlan OBJECT-TYPE
    SYNTAX   INTEGER 
    MAX-ACCESS read-write
    STATUS current
    DESCRIPTION
    "Set the vNIC group vlan number."
    ::= { vnicNewCfgGroupEntry 3 }    

vnicNewCfgGroupFailoverState OBJECT-TYPE
    SYNTAX   INTEGER {
        enabled(1),
        disabled(2)
        }
    MAX-ACCESS read-write
    STATUS current
    DESCRIPTION
    "Set the vNIC group failover state."
    ::= { vnicNewCfgGroupEntry 4 }    

vnicNewCfgGroupAddVnic OBJECT-TYPE
    SYNTAX   DisplayString
    MAX-ACCESS read-write
    STATUS current
    DESCRIPTION
    "Add a vNIC to the vNIC group."
    ::= { vnicNewCfgGroupEntry 5 }    

vnicNewCfgGroupRemVnic OBJECT-TYPE
    SYNTAX   DisplayString
    MAX-ACCESS read-write
    STATUS current
    DESCRIPTION
    "Remove a vNIC to the vNIC group."
    ::= { vnicNewCfgGroupEntry 6 }    

vnicNewCfgGroupAddPort OBJECT-TYPE
    SYNTAX   INTEGER
    MAX-ACCESS read-write
    STATUS current
    DESCRIPTION
    "Add a non-vNIC port or a uplink port to the vNIC group."
    ::= { vnicNewCfgGroupEntry 7 }    

vnicNewCfgGroupRemPort OBJECT-TYPE
    SYNTAX   INTEGER
    MAX-ACCESS read-write
    STATUS current
    DESCRIPTION
    "Remove a non-vNIC port or a uplink port from the vNIC group."
    ::= { vnicNewCfgGroupEntry 8 }    

vnicNewCfgGroupAddTrunk OBJECT-TYPE
    SYNTAX   INTEGER
    MAX-ACCESS read-write
    STATUS current
    DESCRIPTION
    "Add a uplink trunk to the vNIC group."
    ::= { vnicNewCfgGroupEntry 9 }    

vnicNewCfgGroupRemTrunk OBJECT-TYPE
    SYNTAX   INTEGER {
        other(1),
        delete(2)
    }
    MAX-ACCESS read-write
    STATUS current
    DESCRIPTION
    "Remove the uplink trunk from the vNIC group.
    other(1) is returned always when read.
    The following values are writable: delete(2)...to delete the uplink trunk from the vNIC group"
    ::= { vnicNewCfgGroupEntry 10 }    


vnicNewCfgGroupDelete OBJECT-TYPE
    SYNTAX   INTEGER {
        other(1),
        delete(2)
    }
    MAX-ACCESS read-write
    STATUS current
    DESCRIPTION
    "Delete the vNIC group.
    other(1) is returned always when read.
    The following values are writable: delete(2)...to delete the vNIC group"
    ::= { vnicNewCfgGroupEntry 13 }    

vnicNewCfgGroupVnics OBJECT-TYPE
    SYNTAX   DisplayString
    MAX-ACCESS read-only
    STATUS current
    DESCRIPTION
    "The vNICs in the vNIC group."
    ::= { vnicNewCfgGroupEntry 14 }

vnicNewCfgGroupPorts OBJECT-TYPE
    SYNTAX   DisplayString
    MAX-ACCESS read-only
    STATUS current
    DESCRIPTION
    "Non-vNIC Ports and/or uplink port in the vNIC group."
    ::= { vnicNewCfgGroupEntry 15 }

vnicNewCfgGroupTrunk OBJECT-TYPE
    SYNTAX   INTEGER
    MAX-ACCESS read-only
    STATUS current
    DESCRIPTION
    "Uplink trunk in the vNIC group."
    ::= { vnicNewCfgGroupEntry 16 }


-- ----------------------------------------------------------------------------
-- } INSERT: vnic 
-- ----------------------------------------------------------------------------





-- ----------------------------------------------------------------------------
-- } INSERT:  bntRoot
-- ----------------------------------------------------------------------------

-- Access Switch for Blade OS TOR Private MIBs
-- tor-BladeSwitch     OBJECT IDENTIFIER ::= { blade 100 }
-- MIB definitions for Standalone BNT Private MIBs

-- Access "productID" group for Common Standalone BNT Private MIBs
ibmnos-BladeSwitch     OBJECT IDENTIFIER ::= { ibmnetwork 100 }




ibmnoscfa                  OBJECT IDENTIFIER ::= { ibmnos-BladeSwitch 27 }
-- ----------------------------------------------------------------------------
-- { INSERT: cfa
-- ----------------------------------------------------------------------------



      ibmIfBranch OBJECT IDENTIFIER ::= { ibmnoscfa 1 }



-- ifMainTable
-- This table is used for the management of all the interfaces in the
-- system. 
         
      ifMainTable          OBJECT-TYPE
         SYNTAX            SEQUENCE OF IfMainEntry
         MAX-ACCESS        not-accessible
         STATUS            current
         DESCRIPTION
            "A list of all the interface entries in the system. 
            This table contains objects which are applicable to all
            types of interfaces in the system. This table is a 
            proprietary extension to the standard ifTable and 
            ifXTable. The index to this table has the semantics of
            the MIB-2 ifIndex."
         ::= { ibmIfBranch 4 }

      ifMainEntry          OBJECT-TYPE
         SYNTAX            IfMainEntry
         MAX-ACCESS        not-accessible
         STATUS            current
         DESCRIPTION
            "An entry containing management information applicable
            to a particular interface."
         INDEX { ifMainIndex }
         ::= { ifMainTable 1 }

      IfMainEntry ::=
         SEQUENCE {
            ifMainIndex              InterfaceIndex,
            ifMainPortName           DisplayString
            }

      ifMainIndex          OBJECT-TYPE
         SYNTAX            InterfaceIndex
         MAX-ACCESS        not-accessible 
         STATUS            current
         DESCRIPTION
            "A unique value, greater than zero, for each
            interface. This object is identical to the ifIndex
            of the standard MIB-2 ifTable." 
         ::= { ifMainEntry 1 }


   
ifMainPortName  OBJECT-TYPE
    SYNTAX      DisplayString
    MAX-ACCESS  read-write
    STATUS      current
    DESCRIPTION
        "This is used to assign a alias to a port"
    ::= { ifMainEntry 9 }


-- ----------------------------------------------------------------------------
-- } INSERT: cfa
-- ----------------------------------------------------------------------------



ibmnos                     OBJECT IDENTIFIER ::= { ibmnos-BladeSwitch 81 }
-- ----------------------------------------------------------------------------
-- { INSERT: bos
-- ----------------------------------------------------------------------------



-- ==================================================================== 
-- groups in the MIB  
-- ====================================================================
 
      ibmnosSystem                OBJECT IDENTIFIER ::= { ibmnos 1 }
      ibmnosConfigControl         OBJECT IDENTIFIER ::= { ibmnos 2 }
-- ====================================================================

-- System Group 


   -- Configurtion Save related configuration / information

ibmnosConfigSaveOption  OBJECT-TYPE
    SYNTAX      INTEGER {
                            noSave(1),
                            flashSave(2),
                            remoteTftpSave(3),
                            startupConfig(4),
                            backupConfig(5),
                            remoteTftpRestore(6)
       }
   MAX-ACCESS  read-write
       STATUS      current
       DESCRIPTION
       "Specifies whether the configurations of the switch has to be
       saved or not.

       The value 'noSave' specifies that the configurations need
       not be saved.

       The value 'flashSave' specifies that the configurations need
       to be saved in flash in the specified file name issConfigSaveFileName.

       The value 'remoteSave' specifies that the configurations need
       to be saved in specified remote system.

       The value 'startupConfig' specifies that the configurations need
       to be saved in flash in the 'Startup Configuration File'.
       The value 'backupConfig' specifies that the configurations need
       to be saved in flash in the 'backup Configuration File'.

       The value 'remoteTftpRestore' specifies that the configurations need
       to be restored from remote system and saved in the file as indicated by
       'ibmnosConfigRemoteType'. This configuration are copied to configuration blocks
       and applied after restart."
       DEFVAL  { noSave }
   ::= { ibmnosSystem 10 }

ibmnosConfigSaveFileName OBJECT-TYPE
       SYNTAX      DisplayString (SIZE(1..128))
       MAX-ACCESS  read-write
       STATUS      current
       DESCRIPTION
       "Name of the file in which the switch configurations are
       to be saved.

       This object is valid only if 'issConfigSaveOption' is chosen
       to be 'flashSave' or 'remoteSave'."
       DEFVAL { "iss.conf" }
   ::= { ibmnosSystem 12 }

   ibmnosInitiateConfigSave  OBJECT-TYPE
       SYNTAX      TruthValue
       MAX-ACCESS  read-write
       STATUS      current
       DESCRIPTION
       "When set as 'true' switch configurations save operation is
       initiated.
       As soon as the configuration save operation is completed, the value
       of this object reverts back to 'false'.

       All the configurations made via the three interfaces
       viz.
       -> commandline interface
       -> Web Interface
       -> SNMP interface
       are saved either in 'Startup Configuration File' in the flash or
       in the specified 'issConfigSaveFileName' in the flash or
       in the chosen remote system, depending upon 'ConfigSaveOption'."
       DEFVAL  { false }
   ::= { ibmnosSystem 13 }



ibmnosConfigSaveStatus OBJECT-TYPE
   SYNTAX     INTEGER {
              saveInProgress(1),
              saveSuccessful(2),
              saveFailed(3),
              notInitiated(4),
              saveNotRequired(5)
             }
   MAX-ACCESS  read-only
   STATUS      current
   DESCRIPTION
      "Status of configuration save operation."
   DEFVAL  { notInitiated }
   ::= { ibmnosSystem 14 }

  ibmnosConfigRestoreOption  OBJECT-TYPE
       SYNTAX      INTEGER {
           factory(1),
               activeConfig(2),
               backupConfig(3)
       }
   MAX-ACCESS  read-write
       STATUS      current
       DESCRIPTION
       "Specifies whether the switch configurations have to be restored
       or not.

       The value 'factory' specifies that the switch configurations
       need not be restored when the system is restarted.

       The value 'activeConfig' specifies that the configurations
       need to be restored from the 'Startup Configuration File' in the flash
       when the system is restarted.

       The value 'backupConfig' specifies that the configurations
       need to be restored from the 'Backup Configuration File' in the flash
       when the system is restarted."
       DEFVAL  { factory }
   ::= { ibmnosSystem 15 }





   ibmnosLoggingOption OBJECT-TYPE
       SYNTAX      INTEGER {
           console(1)
       }
   MAX-ACCESS  read-write
       STATUS      current
       DESCRIPTION
       "The Logging option specifying whether the logging is to be
       done at console or to a file(system buffer) in the system."
       ::= { ibmnosSystem 26 }

-- Login Authentication mechanism

ibmnosLoginAuthentication OBJECT-TYPE
   SYNTAX      INTEGER {
               local(1),
               remoteRadius(2),
               remoteTacacs(3)
              }
   MAX-ACCESS  read-write
   STATUS      current
   DESCRIPTION
      "The mechanism by which the user login to access the GUI for 
       configuration has to be authenticated. Authentication is done 
       either locally or in the remote side through a RADIUS Server."
   ::= { ibmnosSystem 32 }


ibmnosConfigRestoreFileVersion OBJECT-TYPE 
   SYNTAX      DisplayString (SIZE(1..12))
   MAX-ACCESS  read-only
   STATUS      current
   DESCRIPTION 
      "Config Restoration file version. This version will be compared in each
       reboot against version stored in restoration file. Restoration 
       will occur only if the first field in restoration file is this OID and the
       RestoreFileVersion value also matches."
   ::= { ibmnosSystem 40 }



-- Config Control Group


-- Port Control Table 

ibmnosPortCtrlTable OBJECT-TYPE 
   SYNTAX      SEQUENCE OF IbmnosPortCtrlEntry
   MAX-ACCESS  not-accessible 
   STATUS      current 
   DESCRIPTION 
       "A table to control the port specific parameters of the device like speed,
        duplex mode, etc."
   ::= { ibmnosConfigControl 2 }

ibmnosPortCtrlEntry OBJECT-TYPE 
   SYNTAX      IbmnosPortCtrlEntry
   MAX-ACCESS  not-accessible 
   STATUS      current 
   DESCRIPTION 
       "An entry appears in this table for each interface in the system.
   
       Index to the table is the interface index of the port."

   INDEX { ibmnosPortCtrlIndex }
   ::= { ibmnosPortCtrlTable 1 }
   
IbmnosPortCtrlEntry ::= 
   SEQUENCE { 
      ibmnosPortCtrlIndex 
         Integer32, 
      ibmnosPortCtrlMode
         INTEGER, 
      ibmnosPortCtrlDuplex
         INTEGER,
      ibmnosPortCtrlSpeed
         INTEGER, 
      ibmnosPortCtrlFlowControl
         INTEGER
  }

ibmnosPortCtrlIndex OBJECT-TYPE 
   SYNTAX      Integer32 (1..65535)
   MAX-ACCESS  not-accessible 
   STATUS      current 
   DESCRIPTION 
      "Interface index of the port for which the configuration
      in this entry applies."
   
   ::= { ibmnosPortCtrlEntry 1 }

ibmnosPortCtrlMode OBJECT-TYPE 
   SYNTAX      INTEGER {
                 auto          (1),
                 noNegotiation (2)
              }
   MAX-ACCESS  read-write 
   STATUS      current 
   DESCRIPTION 
      "Speficies the mode in which the speed, duplex modes and flow control
       of the interface is determined.

       If set as 'auto', the hardware senses speed and negotiates with the port 
       on the other end of the link for data transfer operation as
       'full-duplex' or 'half-duplex' and about flow contol.
       
       If set as 'nonegotiation', the configured values for interface 
       speed, duplex mode and flow control will be effective."
       
   DEFVAL  { auto }
   ::= { ibmnosPortCtrlEntry 2 }

ibmnosPortCtrlDuplex OBJECT-TYPE 
   SYNTAX      INTEGER {
                 full  (1),
                 half  (2),
		 any   (3)
              }
   MAX-ACCESS  read-write 
   STATUS      current 
   DESCRIPTION 
      "Configures interface data transfer mode as full-duplex or half-duplex.
      
      This object can be configured only if the 'PortCtrlMode' is 'nonegotiation'. 
      If the 'PortCtrlMode' is 'auto', it obtains the value 'any'"

   ::= { ibmnosPortCtrlEntry 3 }

ibmnosPortCtrlSpeed OBJECT-TYPE 
   SYNTAX      INTEGER {
                 tenMBPS     (1),
                 hundredMBPS (2),
                 oneGB       (3),
                 tenGB       (4),
		 any         (5)	
              }
   MAX-ACCESS  read-write 
   STATUS      current 
   DESCRIPTION 
      "Configures interface speed.

      This object can be configured only if the 'PortCtrlMode' is 'nonegotiation'.
      If the 'PortCtrlMode' is 'auto', it obtains the value 'any'"
     
   ::= { ibmnosPortCtrlEntry 4 }


ibmnosPortCtrlFlowControl OBJECT-TYPE 
   SYNTAX      INTEGER {
                 enable     (1),
                 disable    (2),
		 send	    (3),
		 receive    (4)
              }
   MAX-ACCESS  read-write 
   STATUS      current 
   DESCRIPTION 
      "Enables / disables flow control for the interface.

      This object be configured only if the 'PortCtrlMode' is 'nonegotiation'.
      If the 'PortCtrlMode' is 'auto', it obtains the value from Hardware 
      after negotiating  with its peer"

   ::= { ibmnosPortCtrlEntry 5 }


-- ----------------------------------------------------------------------------
-- } INSERT: bos
-- ----------------------------------------------------------------------------


toraddon              OBJECT IDENTIFIER ::= { ibmnos-BladeSwitch
                                                                100
                                            }

-- ----------------------------------------------------------------------------
-- { INSERT: toraddon
-- ----------------------------------------------------------------------------

-- Module Group
--vlan              OBJECT IDENTIFIER ::= { toraddon  1 }
cfa               OBJECT IDENTIFIER ::= { toraddon  2 }
sys               OBJECT IDENTIFIER ::= { toraddon  7 }
ibmnosFdb            OBJECT IDENTIFIER ::= { toraddon  13 }
tor-switch         OBJECT IDENTIFIER ::= { toraddon  14 }

ibmnosBladeHarmony   OBJECT IDENTIFIER ::= { toraddon
                                                    17
                                        }

-- Blade Harmony Wrapper Objects (bosBladeHarmony)

dataCollection        OBJECT IDENTIFIER ::= { ibmnosBladeHarmony  1 }


imageConfigTransfer     OBJECT IDENTIFIER ::= { ibmnosBladeHarmony  3 }


ibmnosFdbTable OBJECT-TYPE
    SYNTAX  SEQUENCE OF IbmnosFdbEntry
    MAX-ACCESS  not-accessible
    STATUS  current
    DESCRIPTION
        "The table of FDB entries."
    ::= { ibmnosFdb 5 }

ibmnosFdbEntry OBJECT-TYPE
    SYNTAX  IbmnosFdbEntry
    MAX-ACCESS  not-accessible
    STATUS  current
    DESCRIPTION
        "A row in the FDB table"
    INDEX   { ibmnosFdbVlan, ibmnosFdbMacAddr }
    ::= { ibmnosFdbTable 1 }

IbmnosFdbEntry ::= SEQUENCE {
    ibmnosFdbVlan               Integer32,
    ibmnosFdbMacAddr            PhysAddress,
    ibmnosFdbMacAddrStr         DisplayString,
    ibmnosFdbVlanId             Integer32,
    ibmnosFdbSrcPort            Integer32,
    ibmnosFdbSrcTrunk           Integer32,
    ibmnosFdbState              INTEGER,
    ibmnosFdbStatus             Integer32,
    ibmnosFdbClearMac           INTEGER
   }

ibmnosFdbVlan OBJECT-TYPE
    SYNTAX  Integer32
    MAX-ACCESS  not-accessible
    STATUS  current
    DESCRIPTION
        "The VLAN ID for the FDB entry."
    ::= { ibmnosFdbEntry 1 }

ibmnosFdbMacAddr OBJECT-TYPE
    SYNTAX  PhysAddress
    MAX-ACCESS  not-accessible
    STATUS  current
    DESCRIPTION
        "The MAC address for the FDB entry."
    ::= { ibmnosFdbEntry 2 }

ibmnosFdbMacAddrStr OBJECT-TYPE
    SYNTAX DisplayString (SIZE (0..255))
    MAX-ACCESS read-only
    STATUS current
    DESCRIPTION
        "The MAC address in hex format for the FDB entry. This node is added for
        display purpose."
    ::={ ibmnosFdbEntry 3 }

ibmnosFdbVlanId OBJECT-TYPE
    SYNTAX  Integer32
    MAX-ACCESS read-only
    STATUS  current
    DESCRIPTION
        "The VLAN ID for the FDB entry. This node is added for display purpose."
    ::= { ibmnosFdbEntry 4 }

ibmnosFdbSrcPort OBJECT-TYPE
    SYNTAX  Integer32
    MAX-ACCESS  read-only
    STATUS  current
    DESCRIPTION
       "Either the value '0', or the port number of the port on which a frame
        having a source address equal to the value of the corresponding
        instance has been seen.  A value of '0' indicates that the port
        number has not been learned but that the bridge does have some
        forwarding/filtering information about this address."
    ::= { ibmnosFdbEntry 5 }

ibmnosFdbSrcTrunk OBJECT-TYPE
    SYNTAX  Integer32
    MAX-ACCESS  read-only
    STATUS  current
    DESCRIPTION
       "Either the value '0', or the trunk number of the trunk on which a frame
        having a source address equal to the value of the corresponding
        instance has been seen.  A value of '0' indicates that the source
        address is not associated with a trunk."
    ::= { ibmnosFdbEntry 6 }

ibmnosFdbState OBJECT-TYPE  
    SYNTAX  INTEGER {
 unknown(1),
 forward(2),
 trunk(3)
	}
    MAX-ACCESS  read-only  
    STATUS  current  
    DESCRIPTION  
        "The state of the FDB entry. The meanings of the values are :
         unknown(1) : the MAC address has not yet been learned by the switch
                      but has only been seen as a destination address
         forward(2) : the MAC address has been learned by the switch
         trunk(3)   : frames with this MAC address are forwarded to trunk
                      group"
    ::= { ibmnosFdbEntry 7 }


ibmnosFdbStatus OBJECT-TYPE
    SYNTAX  Integer32
    MAX-ACCESS  read-only
    STATUS  current
    DESCRIPTION
       "'1' if it is permanent 
        '0' if it is not permanent"
    ::= { ibmnosFdbEntry 10 }

ibmnosFdbClearMac OBJECT-TYPE
    SYNTAX  INTEGER {
        ok(1),
        clear(2)
        }
    MAX-ACCESS  read-write
    STATUS  current 
    DESCRIPTION
        "Setting this value to clear(2) clears the corresponding table entry in FDB."
    ::= { ibmnosFdbEntry 11 }



--  Interface mangager(CFA) objects

ibmnosPortCfgTable OBJECT-TYPE
    SYNTAX  SEQUENCE OF IbmnosPortCfgTableEntry
    MAX-ACCESS  not-accessible
    STATUS  current
    DESCRIPTION
        "The table of port configuration in the new_configuration block."
    ::= { cfa 1 }

ibmnosPortCfgTableEntry OBJECT-TYPE
    SYNTAX  IbmnosPortCfgTableEntry
    MAX-ACCESS  not-accessible
    STATUS  current
    DESCRIPTION
        "A row in the port configuration table in the new_configuration block."
    INDEX   {ibmnosPortCfgIndx }
    ::= {ibmnosPortCfgTable 1 }

IbmnosPortCfgTableEntry ::= SEQUENCE {
    ibmnosPortCfgIndx             Integer32,
    ibmnosPortCfgVlanTag          INTEGER
}

ibmnosPortCfgIndx OBJECT-TYPE
    SYNTAX  Integer32
    MAX-ACCESS  not-accessible
    STATUS  current
    DESCRIPTION
        "The index of the row in port configurations table."
    ::= { ibmnosPortCfgTableEntry 1 }

ibmnosPortCfgVlanTag OBJECT-TYPE
    SYNTAX  INTEGER {
	 enable(1),
	 disable(2)
	}
    MAX-ACCESS  read-write
    STATUS  current
    DESCRIPTION
        "VLAN tag configured for the port"
    ::= { ibmnosPortCfgTableEntry 2 }
    

agImageForNextReset OBJECT-TYPE
     SYNTAX  INTEGER{
		image1(2),
		image2(3)
	      }
    MAX-ACCESS  read-write
    STATUS  current
    DESCRIPTION
         "The software image to be booted from at next reset.

        The following values are writable:
             image1(2)...image 1
             image2(3)...image 2"
 
    ::= { sys 2 }
 


--- Switch Objects


hardwarePartNumber OBJECT-TYPE
    SYNTAX  DisplayString (SIZE(0..16))
    MAX-ACCESS  read-only
    STATUS  current
    DESCRIPTION
        "The hardware part number of the Blade Switch." 
    ::= { tor-switch 1 }

hardwareRevision OBJECT-TYPE
    SYNTAX DisplayString (SIZE(0..16))
    MAX-ACCESS read-only
    STATUS current
    DESCRIPTION
        "The hardware revision.  If the revision is not
         available, a zero length string should be returned."
    ::= { tor-switch 2 }
 
hardwareLastBoot OBJECT-TYPE
    SYNTAX INTEGER {
         unkownReason(0),
         powerCycle(1),
         resetFromConsole(2),
         resetFromTelnetOrSSH(3),
         resetFromSNMP(4),
         resetFromWEBUI(5),
         resetFromScheduled(6),
         resetFromWatchdogTimer(7),
         resetFromSWPANIC(8)
            }
    MAX-ACCESS read-only
    STATUS current
    DESCRIPTION
        "Reason of the last boot.
        "
    ::= { tor-switch 3 }

hardwareMACAddress OBJECT-TYPE
    SYNTAX DisplayString (SIZE(0..48))
    MAX-ACCESS read-only
    STATUS current
    DESCRIPTION
        "The MAC address."
    ::= { tor-switch 4 }

hardwareSwitchRunningSwVersion  OBJECT-TYPE
    SYNTAX DisplayString (SIZE(0..128))
    MAX-ACCESS read-only
    STATUS current
    DESCRIPTION
        "The switch software version."
    ::= { tor-switch 5 }

hardwareFlashConfiguration OBJECT-TYPE
    SYNTAX INTEGER {
         factory(0),
         active(1),
         backup(2)
            }
    MAX-ACCESS read-only
    STATUS current
    DESCRIPTION
        "The active flash configuration."
    ::= { tor-switch 6 }

hardwarePCBAPartNumber OBJECT-TYPE
    SYNTAX DisplayString (SIZE(0..128))
    MAX-ACCESS read-only
    STATUS current
    DESCRIPTION
        "The PCBA part number."
    ::= { tor-switch 7 }

hardwareFABNumber OBJECT-TYPE
    SYNTAX DisplayString (SIZE(0..128))
    MAX-ACCESS read-only
    STATUS current
    DESCRIPTION
        "FAB Number"
    ::= { tor-switch 8 }

hardwareSerialNumber OBJECT-TYPE
     SYNTAX DisplayString (SIZE(0..128))
     MAX-ACCESS read-only
     STATUS current
     DESCRIPTION
         "The switch serial number."
     ::= { tor-switch 9 }

hardwareManufacturingDate OBJECT-TYPE
     SYNTAX DisplayString (SIZE(0..128))
     MAX-ACCESS read-only
     STATUS current
     DESCRIPTION
         "The date of manufacturing."
     ::= { tor-switch 10 }

hwTemperatureSensor1 OBJECT-TYPE
    SYNTAX DisplayString (SIZE(0..128))
    MAX-ACCESS read-only
    STATUS current
    DESCRIPTION
        "The temperature sensor 1."
    ::= { tor-switch 11 }

hwTemperatureSensor2 OBJECT-TYPE
    SYNTAX DisplayString (SIZE(0..128))
    MAX-ACCESS read-only
    STATUS current
    DESCRIPTION
        "The temperature sensor 2."
    ::= { tor-switch 12 }
hwTemperatureSensor3 OBJECT-TYPE
    SYNTAX DisplayString (SIZE(0..128))
    MAX-ACCESS read-only
    STATUS current
    DESCRIPTION
        "The temperature sensor 3."
    ::= { tor-switch 13 }

hwFan1RPMValue OBJECT-TYPE
    SYNTAX DisplayString (SIZE(0..128))
    MAX-ACCESS read-only
    STATUS current
    DESCRIPTION
        "The Fan 1 RPM value."
    ::= { tor-switch 14 }

hwFan2RPMValue OBJECT-TYPE
    SYNTAX DisplayString (SIZE(0..48))
    MAX-ACCESS read-only
    STATUS current
    DESCRIPTION
        "The Fan 2 RPM value."
    ::= { tor-switch 15 }

hwFan3RPMValue OBJECT-TYPE
    SYNTAX DisplayString (SIZE(0..48))
    MAX-ACCESS read-only
    STATUS current
    DESCRIPTION
        "The Fan 3 RPM value."
    ::= { tor-switch 16 }

hwFan4RPMValue OBJECT-TYPE
    SYNTAX DisplayString (SIZE(0..48))
    MAX-ACCESS read-only
    STATUS current
    DESCRIPTION
        "The Fan 4 RPM value."
    ::= { tor-switch 17 }

hwFan5RPMValue OBJECT-TYPE
    SYNTAX DisplayString (SIZE(0..48))
    MAX-ACCESS read-only
    STATUS current
    DESCRIPTION
        "The Fan 5 RPM value."
    ::= { tor-switch 18 }	
	
hwBoardRevision OBJECT-TYPE
    SYNTAX DisplayString (SIZE(0..48))
    MAX-ACCESS read-only
    STATUS current
    DESCRIPTION
    "The Board revision number."
    ::= { tor-switch 19 }


hwPowerSupply1State OBJECT-TYPE
    SYNTAX INTEGER {
         off(0),
         on(1),
         absent(2)
            }
    MAX-ACCESS read-only
    STATUS current
    DESCRIPTION
        "The Power Supply 1 state."
    ::= { tor-switch 20 }

hwPowerSupply2State OBJECT-TYPE
    SYNTAX INTEGER {
         off(0),
         on(1),
         absent(2)
            }
    MAX-ACCESS read-only
    STATUS current
    DESCRIPTION
        "The Power Supply 2 state."
    ::= { tor-switch 21 }

ibmnosSfpInfoTable OBJECT-TYPE
    SYNTAX  SEQUENCE OF IbmnosSfpInfoTableEntry
    MAX-ACCESS  not-accessible
    STATUS  current
    DESCRIPTION
        "The table of external port SFP information."
    ::= { tor-switch 22 }

ibmnosSfpInfoTableEntry OBJECT-TYPE
    SYNTAX  IbmnosSfpInfoTableEntry
    MAX-ACCESS  not-accessible
    STATUS  current
    DESCRIPTION
        "A row in the external port SFP information table."
    INDEX   { ibmnosSfpInfoIndx }
    ::= { ibmnosSfpInfoTable 1 }

IbmnosSfpInfoTableEntry ::= SEQUENCE {
    ibmnosSfpInfoIndx                 Integer32, 
    ibmnosSfpInfoDescription          INTEGER,
    ibmnosSfpInfoSerialNumber         DisplayString,
    ibmnosSfpInfoPartNumber           DisplayString,
    ibmnosSfpInfoHWRevision           DisplayString 
    }

ibmnosSfpInfoIndx OBJECT-TYPE
    SYNTAX  Integer32
    MAX-ACCESS read-only 
    STATUS  current
    DESCRIPTION
        "Sfp Info index (port number)"
    ::= { ibmnosSfpInfoTableEntry 1 }

ibmnosSfpInfoDescription OBJECT-TYPE
    SYNTAX INTEGER {
       none(0),
       sfp(1),
       cx4(2), 
       sfpplus(3),
       dac(6)
       }
    MAX-ACCESS read-only
    STATUS current
    DESCRIPTION
	"Type Ethernet device (None(0), SFP(1), CX4(2), SFPplus(3), DAC(6))"
    ::= { ibmnosSfpInfoTableEntry 2 }

ibmnosSfpInfoSerialNumber OBJECT-TYPE
    SYNTAX DisplayString (SIZE(0..128))
    MAX-ACCESS read-only
    STATUS current
    DESCRIPTION
        "Serial Number."
    ::= { ibmnosSfpInfoTableEntry 3 }

ibmnosSfpInfoPartNumber OBJECT-TYPE
    SYNTAX DisplayString (SIZE(0..128))
    MAX-ACCESS read-only
    STATUS current
    DESCRIPTION
        "Part Number."
    ::= { ibmnosSfpInfoTableEntry 4 }

ibmnosSfpInfoHWRevision OBJECT-TYPE  
    SYNTAX DisplayString (SIZE(0..128))
    MAX-ACCESS  read-only  
    STATUS  current  
    DESCRIPTION  
        "Hardware Revision"
    ::= { ibmnosSfpInfoTableEntry 5 }



swImage1Version OBJECT-TYPE
    SYNTAX DisplayString (SIZE(0..128))
    MAX-ACCESS read-only
    STATUS current
    DESCRIPTION
        "Software image1 version"
    ::= { tor-switch 24 }

swImage2Version OBJECT-TYPE
    SYNTAX DisplayString (SIZE(0..128))
    MAX-ACCESS read-only
    STATUS current
    DESCRIPTION
        "Software image2 version"
    ::= { tor-switch 25 }

swBootVersion OBJECT-TYPE
    SYNTAX DisplayString (SIZE(0..128))
    MAX-ACCESS read-only
    STATUS current
    DESCRIPTION
        "Software boot version"
    ::= { tor-switch 26 }

hwFan6RPMValue OBJECT-TYPE
    SYNTAX DisplayString (SIZE(0..48))
    MAX-ACCESS read-only
    STATUS current
    DESCRIPTION
        "The Fan 6 RPM value."
    ::= { tor-switch 27 }

hwTemperatureSensor4 OBJECT-TYPE
    SYNTAX DisplayString (SIZE(0..128))
    MAX-ACCESS read-only
    STATUS current
    DESCRIPTION
        "The temperature sensor 4."
    ::= { tor-switch 32 }



hwFan7RPMValue OBJECT-TYPE
    SYNTAX DisplayString (SIZE(0..48))
    MAX-ACCESS read-only
    STATUS current
    DESCRIPTION
        "The Fan 7 RPM value."
    ::= { tor-switch 40 }

hwFan8RPMValue OBJECT-TYPE
    SYNTAX DisplayString (SIZE(0..48))
    MAX-ACCESS read-only
    STATUS current
    DESCRIPTION
        "The Fan 8 RPM value."
    ::= { tor-switch 41 }

hwBootTime OBJECT-TYPE
    SYNTAX DisplayString (SIZE(0..48))
    MAX-ACCESS read-only
    STATUS current
    DESCRIPTION
        "The hardware system boot time ."
    ::= { tor-switch 42 }



-- Similar to ifAvailableIndex
ibmnosPortTableMaxEnt OBJECT-TYPE
    SYNTAX  Integer32
    MAX-ACCESS  read-only
    STATUS  current
    DESCRIPTION
        "The maximum number of rows in the port configuration host table."
    ::= { dataCollection 1 }




-- Similar to swImage1Version
ibmnosImage1Ver OBJECT-TYPE
    SYNTAX  DisplayString (SIZE(0..128))
    MAX-ACCESS  read-only
    STATUS  current
    DESCRIPTION
    "The version of the software image stored in image 1 storage in the
    form of 'major.minor.bugfix'.  A zero length string is returned if
    version is not available or there is no valid software image."
    ::= { dataCollection 3 }

--  Similar to swImage2Version
ibmnosImage2Ver OBJECT-TYPE
    SYNTAX  DisplayString (SIZE(0..128))
    MAX-ACCESS  read-only
    STATUS  current
    DESCRIPTION
    "The version of the software image stored in image 2 storage in the
    form of 'major.minor.bugfix'.  A zero length string is returned if
    version is not available or there is no valid software image."
    ::= { dataCollection 4 }

hwSwitchSoftwareVersion OBJECT-TYPE
    SYNTAX DisplayString (SIZE(0..128))
    MAX-ACCESS read-only
    STATUS current
    DESCRIPTION
        "The switch software version."
    ::= { dataCollection 5 }


-- Similar to hwSerialNumber
hwSerialNum OBJECT-TYPE
    SYNTAX DisplayString (SIZE(0..48))
    MAX-ACCESS read-only
    STATUS current
    DESCRIPTION
    "The switch serial number."
    ::= { dataCollection 6 }

--  Already addedd with different data type. 
--hwLastBoot OBJECT-TYPE
--    SYNTAX DisplayString (SIZE(0..48))
--    MAX-ACCESS read-only
--    STATUS current
--    DESCRIPTION
--    "Time and reason of the last boot."
--    ::= { ibmnosBladeHarmony 7}


hwManufacturingDate OBJECT-TYPE
    SYNTAX DisplayString (SIZE(0..48))
    MAX-ACCESS read-only
    STATUS current
    DESCRIPTION
    "The date of manufacturing."
    ::= { dataCollection 7 }

-- Similar to issRestart
ibmnosReset OBJECT-TYPE
    SYNTAX  INTEGER {
        other(1),
        reset(2)
        }
    MAX-ACCESS  read-write
    STATUS  current
    DESCRIPTION
    "This is an action object to reboot the agent.
    other(1) is returned always when read."
    ::= { dataCollection 8 }

-- Similar to swBootVersion
ibmnosBootVer OBJECT-TYPE
    SYNTAX  DisplayString (SIZE(0..16))
    MAX-ACCESS  read-only
    STATUS  current
    DESCRIPTION
    "The version of the boot code in the form of 'major.minor.bugfix'.
    A zero length string is returned if version is not available."
    ::= { dataCollection 9 }

--Similar to ibmnosConfigRestoreOption
ibmnosConfigForNxtReset OBJECT-TYPE
    SYNTAX  INTEGER {
        active(2),
        backup(3),
        default(4)
        }
    MAX-ACCESS  read-write
    STATUS  current
    DESCRIPTION
    "The configuration information to be loaded from at next reset.
    The following values are writable:
    active(2)...active configuration block
    backup(3)...backup configuration block
    default(4)..default configuration block"
    ::= { dataCollection 10 }


ibmnosSoftwareVersion OBJECT-TYPE
    SYNTAX  DisplayString (SIZE(0..16))
    MAX-ACCESS  read-only
    STATUS  current
    DESCRIPTION
    "The version of the software image that is currently running on the
    system in the form of 'major.minor.maintenance.bugfix'.  A zero
    length string is returned if version is not available."
    ::= { dataCollection 11 }




agTftpServer OBJECT-TYPE
    SYNTAX  DisplayString (SIZE(0..128))
    MAX-ACCESS  read-write
    STATUS  current
    DESCRIPTION
    "The TFTP server IP address or domain name."
    ::= { imageConfigTransfer 1 }



-- ----------------------------------------------------------------------------
-- } INSERT: g8000
-- ----------------------------------------------------------------------------



-- ----------------------------------------------------------------------------
-- } INSERT:  blade
-- ----------------------------------------------------------------------------

END
