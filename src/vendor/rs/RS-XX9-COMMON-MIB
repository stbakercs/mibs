--
-- RS-XX9-COMMON-MIB.mi2
-- MIB generated by MG-SOFT Visual MIB Builder 2010 Version 8.0  Build 403
-- Monday, March 21, 2016 at 15:26:48
--

-- *****************************************************************************
-- *****************************************************************************
-- **
-- **  COPYRIGHT      (c) 2011 Rohde & Schwarz GmbH & Co. KG
-- **                          Muehldorfstrasse 15
-- **    R & S                 D-81671 Muenchen
-- **
-- *****************************************************************************
-- **
-- **  MODULE         RS-XX9-COMMON-MIB
-- **  
-- *****************************************************************************
-- *****************************************************************************

    RS-XX9-COMMON-MIB DEFINITIONS ::= BEGIN
 
        IMPORTS
            entPhysicalEntry            
                FROM ENTITY-MIB            
            InetAddress, InetAddressType            
                FROM INET-ADDRESS-MIB            
            rsXx9Common, rsXx9MibModule            
                FROM RS-XX9-SMI-MIB            
            Trigger, NotificationClass, NotificationMask, NotificationPriority, NotificationState, 
            EnableOption, Xx9SystemType, Xx9RedundancyMode, Xx9ModulationMode, IndexTransmitter, 
            Xx9AmplifierType, SwitchOnOff            
                FROM RS-XX9-TC-MIB            
            SnmpAdminString            
                FROM SNMP-FRAMEWORK-MIB            
            OBJECT-GROUP, MODULE-COMPLIANCE, NOTIFICATION-GROUP            
                FROM SNMPv2-CONF            
            sysName            
                FROM SNMPv2-MIB            
            Integer32, Unsigned32, Counter32, OBJECT-TYPE, MODULE-IDENTITY, 
            NOTIFICATION-TYPE            
                FROM SNMPv2-SMI            
            RowStatus, DateAndTime, DisplayString, TruthValue, TEXTUAL-CONVENTION            
                FROM SNMPv2-TC;
    
    
        rsXx9CommonMibModule MODULE-IDENTITY 
            LAST-UPDATED "201603211500Z"		-- March 21, 2016 at 15:00 GMT
            ORGANIZATION 
                "Rohde&Schwarz GmbH & Co. KG"
            CONTACT-INFO 
                "Rohde & Schwarz GmbH & Co. KG
                Broadcasting Division
                
                Muehldorfstrasse 15
                81671 Munich
                Germany
                
                customersupport@rohde-schwarz.com"
            DESCRIPTION 
                "This MIB defines general objects of XX9000 transmitting systems from Rohde & Schwarz.
                
                Use this MIB for things all transmitters support via SNMP, e.g.:
                - installation / configuration issues (date/time, software update etc.)
                
                The following MIBs are related to this:
                - RS-COMMON-MIB         - mandatory for this MIB.
                - RS-XX9-SMI-MIB        - mandatory for this MIB.
                - RS-XX9-TC-MIB         - mandatory for this MIB."
            REVISION "201603211500Z"		-- March 21, 2016 at 15:00 GMT
            DESCRIPTION 
                "added commonEntPhysicalHardwareStatus, commonEntPhysicalConfigurationStatus, commonEntPhysicalType
                added commonEnvSummary, commonEnvTemperature, commonEnvDewPoint
                added commonEnvironment subtree
                "
            REVISION "201602161000Z"		-- February 16, 2016 at 10:00 GMT
            DESCRIPTION 
                "added commonDevInfoFanState and commonDevInfoOvpState notifications
                added commonDevInfoConfigTable
                "
            REVISION "201511181500Z"		-- November 18, 2015 at 15:00 GMT
            DESCRIPTION 
                "added commonGpsConfGnssSelection, most nodes for GPS state and configuration are also valid for GLONASS"
            REVISION "201509090800Z"		-- September 09, 2015 at 08:00 GMT
            DESCRIPTION 
                "added commonDevInfoAcFail
                added commonDeviceInformation
                "
            REVISION "201508061600Z"		-- August 06, 2015 at 16:00 GMT
            DESCRIPTION 
                "added swUpdateRebootPending
                "
            REVISION "201507151700Z"		-- July 15, 2015 at 17:00 GMT
            DESCRIPTION 
                "added snmpUserConfiguration"
            REVISION "201504020800Z"		-- April 02, 2015 at 08:00 GMT
            DESCRIPTION 
                "renamed enum labels of upsInfoBatteryStatus
                "
            REVISION "201503040900Z"		-- March 04, 2015 at 09:00 GMT
            DESCRIPTION 
                "updated description texts"
            REVISION "201412221600Z"		-- December 22, 2014 at 16:00 GMT
            DESCRIPTION 
                "updated description texts
                "
            REVISION "201411281500Z"		-- November 28, 2014 at 15:00 GMT
            DESCRIPTION 
                "extend value range for commonGpsStAntennaState by notMonitored"
            REVISION "201407031500Z"		-- July 03, 2014 at 15:00 GMT
            DESCRIPTION 
                "added commonGpsStateMonitoring"
            REVISION "201403271000Z"		-- March 27, 2014 at 10:00 GMT
            DESCRIPTION 
                "add UPS (uninterruptable power system) information
                add GPS (global positioning system) configuration and status"
            REVISION "201402211100Z"		-- February 21, 2014 at 11:00 GMT
            DESCRIPTION 
                "update range of optionKeyIdx
                update Description of commonOptionKeyStatus
                "
            REVISION "201312021000Z"		-- December 02, 2013 at 10:00 GMT
            DESCRIPTION 
                "updated range for optionKeyStatus"
            REVISION "201309051700Z"		-- September 05, 2013 at 17:00 GMT
            DESCRIPTION 
                "changes regarding NTP:
                - obsoleting old commonTransmitterConfiguration/ntp section
                - obsoleting old commonNtpSync notification
                - creating new commonDateTime section (which includes NTP settings)
                - creating new commonDateTimeNtpState notification"
            REVISION "201108160800Z"		-- August 16, 2011 at 08:00 GMT
            DESCRIPTION 
                "Initial revision."
            ::= { rsXx9MibModule 2 }

        
    
--
-- Textual conventions
--
    
        IndexTceDevice ::= TEXTUAL-CONVENTION
            STATUS current
            DESCRIPTION 
                "Index of a TCE90x."
            SYNTAX Unsigned32 (1..32)

        GpsPowerSource ::= TEXTUAL-CONVENTION
            STATUS current
            DESCRIPTION 
                "Description."
            SYNTAX INTEGER
                {
                undefined(1),
                passive(2),
                active(3)
                }

    
--
-- Node definitions
--
    
        rsXx9CommonNotifications OBJECT IDENTIFIER ::= { rsXx9Common 0 }

        
        commonNtpSync NOTIFICATION-TYPE
            OBJECTS { commonNotificationAlarmClass, commonTxNotificationPriority, commonTxNotificationState }
            STATUS obsolete
            DESCRIPTION 
                "NTP synchronization state changed.
                
                Possible values:
                off(2)   - NTP synchronization is disabled.
                fault(3) - NTP synchronization failed.
                ok(5)    - successful NTP synchronization.
                
                Notification class: warning
                
                currently not implemented"
            ::= { rsXx9CommonNotifications 1 }

        
        commonSwUpdateStatus NOTIFICATION-TYPE
            OBJECTS { commonNotificationAlarmClass, commonTxNotificationPriority, commonTxNotificationState }
            STATUS current
            DESCRIPTION 
                "Indicates whether the TCE900 is ready for the device software update. 
                
                Possible values:
                off(2) - software update finished. The TCE900 cannot be found in the 
                network by the Software Distributor. It is not possible to update the 
                software. 
                ok(5)  - software update started. The TCE900 is listed in the update list 
                of the Software Distributor and the software can be updated. 
                
                Notification class: info"
            ::= { rsXx9CommonNotifications 2 }

        
        commonFwUpdateStatus NOTIFICATION-TYPE
            OBJECTS { commonNotificationAlarmClass, commonTxNotificationPriority, commonTxNotificationState }
            STATUS current
            DESCRIPTION 
                "Firmware update status.
                
                Possible values:
                off(2) - firmware update finished.
                warning(4)  - firmware update running.
                
                Notification class: warning"
            ::= { rsXx9CommonNotifications 3 }

        
        commonOptionKeyStatus NOTIFICATION-TYPE
            OBJECTS { commonNotificationAlarmClass, commonOpkNotificationPriority, commonOpkNotificationState }
            STATUS current
            DESCRIPTION 
                "Option key state in a device.
                
                Possible values:
                off(2)  - no option installed
                fault(3)   - an option expired
                warning(4) - an option will expire
                ok(5)      - all options ok
                
                Notification class: warning"
            ::= { rsXx9CommonNotifications 100 }

        
        commonTest NOTIFICATION-TYPE
            OBJECTS { sysName, commonTrapCounter }
            STATUS current
            DESCRIPTION 
                "This notification is sent to check whether the notification sink(s) receive any 
                notification from this agent.
                To trigger this trap, set 'sendTestNotification' to trigger(2)."
            ::= { rsXx9CommonNotifications 1000 }

        
        commonRising NOTIFICATION-TYPE
            OBJECTS { customNotificationVariable, customNotificationValue, customNotificationRisingThreshold, customNotificationPriority }
            STATUS current
            DESCRIPTION 
                "The SNMP trap that is generated when an notificationTable
                entry crosses its rising threshold."
            ::= { rsXx9CommonNotifications 1001 }

        
        commonFalling NOTIFICATION-TYPE
            OBJECTS { customNotificationVariable, customNotificationValue, customNotificationFallingThreshold, customNotificationPriority }
            STATUS current
            DESCRIPTION 
                "The SNMP trap that is generated when an notificationTable
                entry crosses its falling threshold."
            ::= { rsXx9CommonNotifications 1002 }

        
        commonChanging NOTIFICATION-TYPE
            OBJECTS { customNotificationVariable, customNotificationValue, customNotificationPriority }
            STATUS current
            DESCRIPTION 
                "The SNMP trap that is generated when an notificationTable
                entry changes its value."
            ::= { rsXx9CommonNotifications 1003 }

        
        commonDateTimeNtpState NOTIFICATION-TYPE
            OBJECTS { commonNotificationAlarmClass, commonDateTimeNotificationPriority, commonDateTimeNotificationState }
            STATUS current
            DESCRIPTION 
                "If NTP time synchronization is active, this parameter indicates 
                whether communication with the NTP server is functioning.
                 	
                Possible values:
                off(2) - NTP disabled
                fault(3) - NTP enabled and no server configured or NTP enabled and server not reachable
                ok(5) - NTP enabled and server reachable
                 	
                Notification class: warning
                "
            ::= { rsXx9CommonNotifications 2000 }

        
        commonGpsState NOTIFICATION-TYPE
            OBJECTS { commonNotificationAlarmClass, commonGpsNotificationPriority, commonGpsNotificationState }
            STATUS current
            DESCRIPTION 
                "The GNSS (GPS, GLONASS) receiver is not able to locate satellites. Check the antenna connection.
                 	
                Possible values:
                off(2) - 
                warning(4) - 
                ok(5) - 
                 	
                Notification class: info
                "
            ::= { rsXx9CommonNotifications 3000 }

        
        commonDevInfoAcFail NOTIFICATION-TYPE
            OBJECTS { commonNotificationAlarmClass, commonDevInfoNotificationPriority, commonDevInfoNotificationState }
            STATUS current
            DESCRIPTION 
                "Indicates if the capacitor battery is used to drive the device
                only valid for TLx devices equipped with a capacitor battery
                 	
                Possible values:
                off(2) - 
                warning(4) - 
                 	
                Notification class: warning
                "
            ::= { rsXx9CommonNotifications 4000 }

        
        commonDevInfoFanState NOTIFICATION-TYPE
            OBJECTS { commonNotificationAlarmClass, commonDevInfoNotificationPriority, commonDevInfoNotificationState }
            STATUS current
            DESCRIPTION 
                "Description."
            ::= { rsXx9CommonNotifications 4100 }

        
        commonDevInfoOvpState NOTIFICATION-TYPE
            OBJECTS { commonNotificationAlarmClass, commonDevInfoNotificationPriority, commonDevInfoNotificationState }
            STATUS current
            DESCRIPTION 
                "Description."
            ::= { rsXx9CommonNotifications 4200 }

        
        commonEnvSummary NOTIFICATION-TYPE
            OBJECTS { commonNotificationAlarmClass, commonEnvNotificationPriority, commonEnvNotificationState }
            STATUS current
            DESCRIPTION 
                "Description."
            ::= { rsXx9CommonNotifications 5000 }

        
        commonEnvTemperature NOTIFICATION-TYPE
            OBJECTS { commonNotificationAlarmClass, commonEnvNotificationPriority, commonEnvNotificationState }
            STATUS current
            DESCRIPTION 
                "Description."
            ::= { rsXx9CommonNotifications 5001 }

        
        commonEnvDewPoint NOTIFICATION-TYPE
            OBJECTS { commonNotificationAlarmClass, commonEnvNotificationPriority, commonEnvNotificationState }
            STATUS current
            DESCRIPTION 
                "Description."
            ::= { rsXx9CommonNotifications 5002 }

        
        rsXx9CommonObjects OBJECT IDENTIFIER ::= { rsXx9Common 1 }

        
        commonProductInformation OBJECT IDENTIFIER ::= { rsXx9CommonObjects 1 }

        
        commonEntPhysicalTable OBJECT-TYPE
            SYNTAX SEQUENCE OF CommonEntPhysicalEntry
            MAX-ACCESS not-accessible
            STATUS current
            DESCRIPTION
                "Expansion of the entPhysicalTable."
            ::= { commonProductInformation 1 }

        
        commonEntPhysicalEntry OBJECT-TYPE
            SYNTAX CommonEntPhysicalEntry
            MAX-ACCESS not-accessible
            STATUS current
            DESCRIPTION
                "An entry in the commonEntPhysicalTable."
            AUGMENTS { entPhysicalEntry }
            ::= { commonEntPhysicalTable 1 }

        
        CommonEntPhysicalEntry ::=
            SEQUENCE { 
                commonEntPhysicalSwFwBiosNumber
                    SnmpAdminString,
                commonEntPhysicalOperationHours
                    Counter32,
                commonEntPhysicalPowerUpCycles
                    Counter32,
                commonEntPhysicalHardwareStatus
                    NotificationState,
                commonEntPhysicalConfigurationStatus
                    NotificationState,
                commonEntPhysicalType
                    SnmpAdminString
             }

        commonEntPhysicalSwFwBiosNumber OBJECT-TYPE
            SYNTAX SnmpAdminString
            MAX-ACCESS read-only
            STATUS current
            DESCRIPTION
                "The Rohde&Schwarz identification number of the software/firmware/BIOS."
            ::= { commonEntPhysicalEntry 1 }

        
        commonEntPhysicalOperationHours OBJECT-TYPE
            SYNTAX Counter32
            UNITS "hour"
            MAX-ACCESS read-only
            STATUS current
            DESCRIPTION
                "Operating hours of the device."
            ::= { commonEntPhysicalEntry 2 }

        
        commonEntPhysicalPowerUpCycles OBJECT-TYPE
            SYNTAX Counter32
            MAX-ACCESS read-only
            STATUS current
            DESCRIPTION
                "Number of power up cycles of the device."
            ::= { commonEntPhysicalEntry 3 }

        
        commonEntPhysicalHardwareStatus OBJECT-TYPE
            SYNTAX NotificationState
            MAX-ACCESS read-only
            STATUS current
            DESCRIPTION
                "Description."
            ::= { commonEntPhysicalEntry 4 }

        
        commonEntPhysicalConfigurationStatus OBJECT-TYPE
            SYNTAX NotificationState
            MAX-ACCESS read-only
            STATUS current
            DESCRIPTION
                "Description."
            ::= { commonEntPhysicalEntry 5 }

        
        commonEntPhysicalType OBJECT-TYPE
            SYNTAX SnmpAdminString (SIZE (0..99))
            MAX-ACCESS read-only
            STATUS current
            DESCRIPTION
                "Description."
            ::= { commonEntPhysicalEntry 6 }

        
        commonTransmitterConfiguration OBJECT IDENTIFIER ::= { rsXx9CommonObjects 2 }

        
        commonDateAndTime OBJECT-TYPE
            SYNTAX DateAndTime
            MAX-ACCESS read-write
            STATUS current
            DESCRIPTION
                "The current date and time for the transmitter.
                
                Notes: The range of distance from UTC is -12h..+14h.
                       Omitting the optional UTC fields in a set-request results in keeping
                       the old UTC offset value."
            ::= { commonTransmitterConfiguration 1 }

        
        ntp OBJECT IDENTIFIER ::= { commonTransmitterConfiguration 2 }

        
        ntpMode OBJECT-TYPE
            SYNTAX INTEGER
                {
                unknown(1),
                disabled(2),
                slewAdjust(3),
                stepAdjust(4)
                }
            MAX-ACCESS read-only
            STATUS obsolete
            DESCRIPTION
                "Configures the working mode of the NTP client.
                unknown(1) - NTP mode is currently not determinable. This value must not be written.
                disabled(2) - No NTP synchronization will be done.
                stepAdjust(4) - Time will be synchronized every ntpSyncTimeInterval.
                
                currently not implemented"
            ::= { ntp 1 }

        
        ntpSyncTimeInterval OBJECT-TYPE
            SYNTAX Unsigned32 (6..1440)
            UNITS "minute"
            MAX-ACCESS read-only
            STATUS obsolete
            DESCRIPTION
                "Set the interval for synchronizing the NTP client with the NTP server. 
                Note: this is useful in step mode only.
                
                currently not implemented"
            ::= { ntp 2 }

        
        ntpServerAddrTable OBJECT-TYPE
            SYNTAX SEQUENCE OF NtpServerAddrEntry
            MAX-ACCESS not-accessible
            STATUS obsolete
            DESCRIPTION
                "Table with server adresses.
                Currently maximal one entry is allowed.
                
                currently not implemented"
            ::= { ntp 3 }

        
        ntpServerAddrEntry OBJECT-TYPE
            SYNTAX NtpServerAddrEntry
            MAX-ACCESS not-accessible
            STATUS obsolete
            DESCRIPTION
                "An entry for a ntpServerAddrTable."
            INDEX { ntpServerAddrIdx }
            ::= { ntpServerAddrTable 1 }

        
        NtpServerAddrEntry ::=
            SEQUENCE { 
                ntpServerAddrIdx
                    Unsigned32,
                ntpServerAddressType
                    InetAddressType,
                ntpServerAddress
                    InetAddress
             }

        ntpServerAddrIdx OBJECT-TYPE
            SYNTAX Unsigned32 (1)
            MAX-ACCESS read-only
            STATUS obsolete
            DESCRIPTION
                "index for table entry."
            ::= { ntpServerAddrEntry 1 }

        
        ntpServerAddressType OBJECT-TYPE
            SYNTAX InetAddressType
            MAX-ACCESS read-only
            STATUS obsolete
            DESCRIPTION
                "The type of ntpServerAddress."
            ::= { ntpServerAddrEntry 2 }

        
        ntpServerAddress OBJECT-TYPE
            SYNTAX InetAddress
            MAX-ACCESS read-only
            STATUS obsolete
            DESCRIPTION
                "The address of the NTP server.
                The address type is determined by the ntpServerAddressType value."
            ::= { ntpServerAddrEntry 3 }

        
        ntpState OBJECT-TYPE
            SYNTAX INTEGER
                {
                unknown(1),
                disabled(2),
                enabled(3),
                notRunning(4),
                syncFailed(5),
                synchronizing(6),
                syncOk(7)
                }
            MAX-ACCESS read-only
            STATUS obsolete
            DESCRIPTION
                "Shows the current state of NTP synchronization.
                
                currently not implemented"
            ::= { ntp 4 }

        
        ntpLastSync OBJECT-TYPE
            SYNTAX DateAndTime
            MAX-ACCESS read-only
            STATUS obsolete
            DESCRIPTION
                "The date/time of the last successful synchronization.
                
                currently not implemented"
            ::= { ntp 5 }

        
        softwareMaintenance OBJECT IDENTIFIER ::= { commonTransmitterConfiguration 3 }

        
        reboot OBJECT-TYPE
            SYNTAX Trigger
            MAX-ACCESS read-write
            STATUS current
            DESCRIPTION
                "Reboots the R&S TCE900.
                "
            ::= { softwareMaintenance 1 }

        
        softwareUpdate OBJECT IDENTIFIER ::= { softwareMaintenance 2 }

        
        swUpdateStart OBJECT-TYPE
            SYNTAX Trigger
            MAX-ACCESS read-write
            STATUS current
            DESCRIPTION
                "Starts the enable phase of a software update if 'Update Mode' is set to 'Manual'. 
                The enable phase is active for approx. 90 seconds. During this time, the R&S 
                TCE900 can be found in the network by the Software Distributor.
                "
            ::= { softwareUpdate 1 }

        
        swUpdateMode OBJECT-TYPE
            SYNTAX INTEGER
                {
                manual(1),
                permanent(2)
                }
            MAX-ACCESS read-write
            STATUS current
            DESCRIPTION
                "Indicates how the software of the TCE900 can be updated. 
                manual(1)    - The TCE900 can be found by the Software Distributor for approx. 
                               90 seconds after the 'Start Update' button is pressed. 
                permanent(2) - The TCE900 can be found by the Software Distributor at any 
                               time. The software can be updated at any time without the TCE900 
                               needing to be prepared for a software update. 
                
                The setting can be changed here.
                "
            ::= { softwareUpdate 2 }

        
        swUpdateDeviceName OBJECT-TYPE
            SYNTAX SnmpAdminString (SIZE (0..30))
            MAX-ACCESS read-write
            STATUS current
            DESCRIPTION
                "Shows the device name under which this R&S TCE900 appears 
                in the list of the Software Distributor. The setting can be 
                changed here.
                "
            ::= { softwareUpdate 3 }

        
        swUpdateDeviceGroup OBJECT-TYPE
            SYNTAX SnmpAdminString (SIZE (0..30))
            MAX-ACCESS read-write
            STATUS current
            DESCRIPTION
                "Shows the device group. The displayed device group must be the same 
                as the device group set in the Software Distributor so that this R&S 
                TCE900 is displayed in the list of devices found by the Software Distributor. 
                "
            ::= { softwareUpdate 4 }

        
        swUpdateRebootPending OBJECT-TYPE
            SYNTAX TruthValue
            MAX-ACCESS read-only
            STATUS current
            DESCRIPTION
                "Indicates, whether this device is updating the firmware of internal components. 
                After these updates are finished, the device will reboot.
                "
            ::= { softwareUpdate 5 }

        
        commonTxNotificationTable OBJECT-TYPE
            SYNTAX SEQUENCE OF CommonTxNotificationEntry
            MAX-ACCESS not-accessible
            STATUS current
            DESCRIPTION
                "The context information/configuration for the notifications
                commonSwUpdateStarted, commonFwUpdateStatus"
            ::= { commonTransmitterConfiguration 4 }

        
        commonTxNotificationEntry OBJECT-TYPE
            SYNTAX CommonTxNotificationEntry
            MAX-ACCESS not-accessible
            STATUS current
            DESCRIPTION
                "An entry in the commonTxNotificationTable."
            INDEX { commonTxNotificationIdx }
            ::= { commonTxNotificationTable 1 }

        
        CommonTxNotificationEntry ::=
            SEQUENCE { 
                commonTxNotificationIdx
                    Unsigned32,
                commonTxNotificationName
                    INTEGER,
                commonTxNotificationMask
                    NotificationMask,
                commonTxNotificationPriority
                    NotificationPriority,
                commonTxNotificationState
                    NotificationState
             }

        commonTxNotificationIdx OBJECT-TYPE
            SYNTAX Unsigned32 (1..3)
            MAX-ACCESS not-accessible
            STATUS current
            DESCRIPTION
                "The notification number as below rsXx9CommonNotifications.
                This is a helper column and therefore not-accessible."
            ::= { commonTxNotificationEntry 1 }

        
        commonTxNotificationName OBJECT-TYPE
            SYNTAX INTEGER
                {
                commonSwUpdateStatus(2),
                commonFwUpdateStatus(3)
                }
            MAX-ACCESS read-only
            STATUS current
            DESCRIPTION
                "The notification number as an enumeration.
                The enumeration correlates with the notifications under rsXx9CommonNotifications."
            ::= { commonTxNotificationEntry 2 }

        
        commonTxNotificationMask OBJECT-TYPE
            SYNTAX NotificationMask
            MAX-ACCESS read-write
            STATUS current
            DESCRIPTION
                "See TextualConvention for details."
            ::= { commonTxNotificationEntry 3 }

        
        commonTxNotificationPriority OBJECT-TYPE
            SYNTAX NotificationPriority
            MAX-ACCESS read-write
            STATUS current
            DESCRIPTION
                "See TextualConvention for details."
            ::= { commonTxNotificationEntry 4 }

        
        commonTxNotificationState OBJECT-TYPE
            SYNTAX NotificationState
            MAX-ACCESS read-only
            STATUS current
            DESCRIPTION
                "See TextualConvention for details."
            ::= { commonTxNotificationEntry 5 }

        
        commonTxFunctions OBJECT IDENTIFIER ::= { commonTransmitterConfiguration 5 }

        
        commonFuncSystemControl OBJECT-TYPE
            SYNTAX EnableOption
            MAX-ACCESS read-only
            STATUS current
            DESCRIPTION
                "If enabled, the device has system control functionality.
                Objects below commonSystemControl have meaningful values."
            ::= { commonTxFunctions 1 }

        
        commonFuncTxControl OBJECT-TYPE
            SYNTAX EnableOption
            MAX-ACCESS read-only
            STATUS current
            DESCRIPTION
                "If enabled, the device has transmitter control functionality.
                Objects below commonTxControl have meaningful values."
            ::= { commonTxFunctions 2 }

        
        commonFuncSignalProcessing OBJECT-TYPE
            SYNTAX EnableOption
            MAX-ACCESS read-only
            STATUS current
            DESCRIPTION
                "If enabled, the device has signal processing functionality."
            ::= { commonTxFunctions 3 }

        
        commonFuncCoolingControl OBJECT-TYPE
            SYNTAX EnableOption
            MAX-ACCESS read-only
            STATUS current
            DESCRIPTION
                "If enabled, the device has cooling control functionality."
            ::= { commonTxFunctions 4 }

        
        commonFuncRackControl OBJECT-TYPE
            SYNTAX EnableOption
            MAX-ACCESS read-only
            STATUS current
            DESCRIPTION
                "If enabled, the device has rack control functionality."
            ::= { commonTxFunctions 5 }

        
        commonSystemControl OBJECT IDENTIFIER ::= { commonTransmitterConfiguration 6 }

        
        commonSystemType OBJECT-TYPE
            SYNTAX Xx9SystemType
            MAX-ACCESS read-only
            STATUS current
            DESCRIPTION
                "See textual convention for details."
            ::= { commonSystemControl 1 }

        
        commonSystemNumberOfTxA OBJECT-TYPE
            SYNTAX Unsigned32 (1..8)
            MAX-ACCESS read-only
            STATUS current
            DESCRIPTION
                "In the case of multi-transmitter systems, the number
                of transmitters which normally broadcast programs."
            ::= { commonSystemControl 2 }

        
        commonTxControlTable OBJECT-TYPE
            SYNTAX SEQUENCE OF CommonTxControlEntry
            MAX-ACCESS not-accessible
            STATUS current
            DESCRIPTION
                "Transmitter control properties for each transmitter."
            ::= { commonTransmitterConfiguration 7 }

        
        commonTxControlEntry OBJECT-TYPE
            SYNTAX CommonTxControlEntry
            MAX-ACCESS not-accessible
            STATUS current
            DESCRIPTION
                "An entry in the commonTxControlTable."
            INDEX { cmnTxCtrlTxIdx }
            ::= { commonTxControlTable 1 }

        
        CommonTxControlEntry ::=
            SEQUENCE { 
                cmnTxCtrlTxIdx
                    IndexTransmitter,
                cmnTxCtrlRedundancyMode
                    Xx9RedundancyMode,
                cmnTxCtrlModulationMode
                    Xx9ModulationMode,
                cmnTxCtrlAmplifierType
                    Xx9AmplifierType
             }

        cmnTxCtrlTxIdx OBJECT-TYPE
            SYNTAX IndexTransmitter
            MAX-ACCESS not-accessible
            STATUS current
            DESCRIPTION
                "transmitter index"
            ::= { commonTxControlEntry 1 }

        
        cmnTxCtrlRedundancyMode OBJECT-TYPE
            SYNTAX Xx9RedundancyMode
            MAX-ACCESS read-only
            STATUS current
            DESCRIPTION
                "Transmitter redundancy mode."
            ::= { commonTxControlEntry 2 }

        
        cmnTxCtrlModulationMode OBJECT-TYPE
            SYNTAX Xx9ModulationMode
            MAX-ACCESS read-only
            STATUS current
            DESCRIPTION
                "Transmitter modulation mode."
            ::= { commonTxControlEntry 3 }

        
        cmnTxCtrlAmplifierType OBJECT-TYPE
            SYNTAX Xx9AmplifierType
            MAX-ACCESS read-only
            STATUS current
            DESCRIPTION
                "Type of amplifiers for transmitter."
            ::= { commonTxControlEntry 4 }

        
        commonSnmpConfiguration OBJECT IDENTIFIER ::= { rsXx9CommonObjects 3 }

        
        sendTestNotification OBJECT-TYPE
            SYNTAX Trigger
            MAX-ACCESS read-write
            STATUS current
            DESCRIPTION
                "Agent generates the notification 'commonTest', which is useful when checking the
                connection between agent (transmitter control unit) and your notification sink(s)."
            ::= { commonSnmpConfiguration 1 }

        
        irtNotificationsAllOn OBJECT-TYPE
            SYNTAX Trigger
            MAX-ACCESS read-write
            STATUS current
            DESCRIPTION
                "This enables all IRT notifications.
                
                In detail, this means in the IRT-MIBs under branches *EventEnable all
                object instances are set to true(1).
                
                Caution!
                Setting this value influences remote controlling of devices.
                Too many alarms may flood your network. Use this only for testing - for 
                operation, we suggest switch on only a few important traps."
            ::= { commonSnmpConfiguration 2 }

        
        irtNotificationsAllOff OBJECT-TYPE
            SYNTAX Trigger
            MAX-ACCESS read-write
            STATUS current
            DESCRIPTION
                "This disables all IRT notifications.
                
                In detail, this means in the IRT-MIBs under branches *EventEnable all
                object instances are set to false(2).
                
                Note: This is typically set when using only R&S-MIBs 
                and you don't need IRT-MIBs."
            ::= { commonSnmpConfiguration 3 }

        
        rsNotificationsAllOn OBJECT-TYPE
            SYNTAX Trigger
            MAX-ACCESS read-write
            STATUS current
            DESCRIPTION
                "This enables all R&S notifications.
                
                In detail, this means in the R&S-MIBs *NotificationTable in
                column *NotificationMask all object instances are set to enable(1).
                
                Caution!
                Enabling all notifications is not recommended!
                
                Caution!
                Setting this value influences remote controlling of devices!
                Too many notifications may flood your network. Use this only for testing - for 
                operation, we suggest switch on only a few important notifications.
                
                Caution!
                This enables absolutely all R&S notifications!
                Make sure you can handle it (network speed, routers, firewalls, NOC database performance etc.)."
            ::= { commonSnmpConfiguration 4 }

        
        rsNotificationsAllOff OBJECT-TYPE
            SYNTAX Trigger
            MAX-ACCESS read-write
            STATUS current
            DESCRIPTION
                "This disables all R&S notifications.
                
                In detail, this means in the R&S-MIBs under *NotificationTable in
                column *NotificationMask all object instances are set to disable(2).
                
                Note: This is typically set when using only IRT-MIBs 
                and you don't need R&S-MIBs."
            ::= { commonSnmpConfiguration 5 }

        
        rsNotificationsAllFaultsOn OBJECT-TYPE
            SYNTAX Trigger
            MAX-ACCESS read-write
            STATUS current
            DESCRIPTION
                "This enables all R&S notifications of class fault(1).
                
                In detail, this means in the R&S-MIBs under *NotificationTable in column *NotificationMask
                all object instances with value fault(1) for binding 'commonNotificationAlarmClass'
                are set to enable(1).
                
                Note: This is the recommended setting when using R&S-MIBs. It gives you an 
                overview of the device state."
            ::= { commonSnmpConfiguration 6 }

        
        rsNotificationsAllFaultsOff OBJECT-TYPE
            SYNTAX Trigger
            MAX-ACCESS read-write
            STATUS current
            DESCRIPTION
                "This disables all R&S notifications of class fault(1).
                
                In detail, this means in the R&S-MIBs under *NotificationTable in column *NotificationMask
                all object instances with value fault(1) for binding 'commonNotificationAlarmClass'
                are set to disable(2)."
            ::= { commonSnmpConfiguration 7 }

        
        rsNotificationsAllWarningsOn OBJECT-TYPE
            SYNTAX Trigger
            MAX-ACCESS read-write
            STATUS current
            DESCRIPTION
                "This enables all R&S notifications of class warning(2).
                
                In detail, this means in the R&S-MIBs under *NotificationTable in column *NotificationMask
                all object instances with value warning(2) for binding 'commonNotificationAlarmClass'
                are set to enable(1).
                
                
                Note: This is the recommended setting when using R&S-MIBs and you want much more 
                informations from the device than only faults. 
                
                Caution!
                This enables lots of notifications.
                Make sure you can handle it (network speed, NOC database performance etc.)..."
            ::= { commonSnmpConfiguration 8 }

        
        rsNotificationsAllWarningsOff OBJECT-TYPE
            SYNTAX Trigger
            MAX-ACCESS read-write
            STATUS current
            DESCRIPTION
                "This disables all R&S notifications of class warning(2).
                
                In detail, this means in the R&S-MIBs under *NotificationTable in column *NotificationMask
                all object instances with value warning(2) for binding 'commonNotificationAlarmClass'
                are set to disable(2)."
            ::= { commonSnmpConfiguration 9 }

        
        customNotificationTable OBJECT-TYPE
            SYNTAX SEQUENCE OF CustomNotificationEntry
            MAX-ACCESS not-accessible
            STATUS current
            DESCRIPTION
                "A list of notification entries."
            ::= { commonSnmpConfiguration 10 }

        
        customNotificationEntry OBJECT-TYPE
            SYNTAX CustomNotificationEntry
            MAX-ACCESS not-accessible
            STATUS current
            DESCRIPTION
                "A conceptual row in the notificationTable."
            INDEX { customNotificationIndex }
            ::= { customNotificationTable 1 }

        
        CustomNotificationEntry ::=
            SEQUENCE { 
                customNotificationIndex
                    Unsigned32,
                customNotificationInterval
                    Unsigned32,
                customNotificationVariable
                    OBJECT IDENTIFIER,
                customNotificationSampleType
                    INTEGER,
                customNotificationValue
                    Integer32,
                customNotificationRisingThreshold
                    Integer32,
                customNotificationFallingThreshold
                    Integer32,
                customNotificationStatus
                    RowStatus,
                customNotificationPriority
                    NotificationPriority
             }

        customNotificationIndex OBJECT-TYPE
            SYNTAX Unsigned32 (1..65535)
            MAX-ACCESS not-accessible
            STATUS current
            DESCRIPTION
                "An index that uniquely identifies an entry in the
                notificationTable.  Each such entry defines a
                diagnostic sample for an object on the device."
            ::= { customNotificationEntry 1 }

        
        customNotificationInterval OBJECT-TYPE
            SYNTAX Unsigned32
            UNITS "second"
            MAX-ACCESS read-create
            STATUS current
            DESCRIPTION
                "The interval in seconds over which the data is sampled
                and compared according to customNotificationSampleType.
                
                This object may not be modified if the associated
                customNotificationStatus object is equal to active(1)."
            DEFVAL { 10 }
            ::= { customNotificationEntry 2 }

        
        customNotificationVariable OBJECT-TYPE
            SYNTAX OBJECT IDENTIFIER
            MAX-ACCESS read-create
            STATUS current
            DESCRIPTION
                "The object identifier of the particular variable to be
                sampled.  Only integer variables may be sampled.
                
                Because SNMP access control is articulated entirely
                in terms of the contents of MIB views, no access
                control mechanism exists that can restrict the value of
                this object to identify only those objects that exist
                in a particular MIB view.  Because there is thus no
                acceptable means of restricting the read access that
                could be obtained through the notification mechanism,
                the probe must only grant write access to this object in
                those views that have read access to all objects on
                the probe.
                
                During a set operation, if the supplied variable name is
                not available in the selected MIB view, a badValue error
                must be returned.  If at any time the variable name of
                an established notificationEntry is no longer available in the
                selected MIB view, the probe must change the status of
                this notificationEntry to invalid(4).
                
                This object may not be modified if the associated
                customNotificationStatus object is equal to active(1)."
            ::= { customNotificationEntry 3 }

        
        customNotificationSampleType OBJECT-TYPE
            SYNTAX INTEGER
                {
                absoluteValue(1),
                changingValue(2)
                }
            MAX-ACCESS read-create
            STATUS current
            DESCRIPTION
                "If the value of this object is absoluteValue(1),
                the value of the selected variable will be compared
                with the thresholds at the end of the sampling interval.
                If the value of this object is changingValue(2),
                the value of the selected variable at the last sample
                will be compared with the current value,
                and a difference will lead to a commonChanging notification.
                
                This object may not be modified if the associated
                customNotificationStatus object is equal to active(1)."
            DEFVAL { absoluteValue }
            ::= { customNotificationEntry 4 }

        
        customNotificationValue OBJECT-TYPE
            SYNTAX Integer32
            MAX-ACCESS read-only
            STATUS current
            DESCRIPTION
                "The value of the statistic during the last sampling period.
                This is the value that is compared with the rising and
                falling thresholds.
                
                The value during the current sampling period is not
                made available until the period is completed and will
                remain available until the next period completes."
            ::= { customNotificationEntry 5 }

        
        customNotificationRisingThreshold OBJECT-TYPE
            SYNTAX Integer32
            MAX-ACCESS read-create
            STATUS current
            DESCRIPTION
                "A threshold for the sampled statistic.  When the current
                sampled value is greater than or equal to this threshold,
                and the value at the last sampling interval was less than
                this threshold, a single event will be generated.
                
                After a rising event is generated, another such event
                will not be generated until the sampled value
                falls below this threshold and reaches the
                notificationFallingThreshold.
                
                This object may not be modified if the associated
                customNotificationStatus is equal to active(1)."
            ::= { customNotificationEntry 6 }

        
        customNotificationFallingThreshold OBJECT-TYPE
            SYNTAX Integer32
            MAX-ACCESS read-create
            STATUS current
            DESCRIPTION
                "A threshold for the sampled statistic.  When the current
                sampled value is less than or equal to this threshold,
                and the value at the last sampling interval was greater than
                this threshold, a single event will be generated.
                
                After a falling event is generated, another such event
                will not be generated until the sampled value
                rises above this threshold and reaches the
                notificationRisingThreshold.
                
                This object may not be modified if the associated
                customNotificationStatus object is equal to active(1)."
            ::= { customNotificationEntry 7 }

        
        customNotificationStatus OBJECT-TYPE
            SYNTAX RowStatus
            MAX-ACCESS read-create
            STATUS current
            DESCRIPTION
                "Control for creating and deleting entries.
                Entries may not be modified while active."
            ::= { customNotificationEntry 8 }

        
        customNotificationPriority OBJECT-TYPE
            SYNTAX NotificationPriority
            MAX-ACCESS read-create
            STATUS current
            DESCRIPTION
                "Priority of a generated notification.
                
                This object may not be modified if the associated
                customNotificationStatus object is equal to active(1)."
            DEFVAL { 1 }
            ::= { customNotificationEntry 9 }

        
        snmpUserConfiguration OBJECT IDENTIFIER ::= { commonSnmpConfiguration 11 }

        
        snmpEnable OBJECT-TYPE
            SYNTAX SwitchOnOff
            MAX-ACCESS read-write
            STATUS current
            DESCRIPTION
                "Switch SNMP off.
                Please note, that you can not turn SNMP on via this OID if SNMP is in the OFF state.
                "
            ::= { snmpUserConfiguration 1 }

        
        snmpSyncTrapSinks OBJECT-TYPE
            SYNTAX Trigger
            MAX-ACCESS read-write
            STATUS current
            DESCRIPTION
                "Synchronize SNMP trap sinks. All enabled traps (IRT and R&S) 
                are sent to all enabled trap sinks."
            ::= { snmpUserConfiguration 2 }

        
-- The following objects are ment only for internal use. 
-- They are used to store values for notification bindings.
        commonNotificationBindings OBJECT IDENTIFIER ::= { rsXx9CommonObjects 4 }

        
        commonNotificationAlarmClass OBJECT-TYPE
            SYNTAX NotificationClass
            MAX-ACCESS accessible-for-notify
            STATUS current
            DESCRIPTION
                "See TextualConvention for details."
            ::= { commonNotificationBindings 1 }

        
        commonTrapCounter OBJECT-TYPE
            SYNTAX Counter32
            MAX-ACCESS read-only
            STATUS current
            DESCRIPTION
                "The total number of SNMP Trap PDUs which have
                been generated by the SNMP protocol entity."
            ::= { commonNotificationBindings 2 }

        
        commonOptionManagement OBJECT IDENTIFIER ::= { rsXx9CommonObjects 5 }

        
        installOpkTable OBJECT-TYPE
            SYNTAX SEQUENCE OF InstallOpkEntry
            MAX-ACCESS not-accessible
            STATUS current
            DESCRIPTION
                "This Table gives the facility for activation/deactivation
                of an option key."
            ::= { commonOptionManagement 1 }

        
        installOpkEntry OBJECT-TYPE
            SYNTAX InstallOpkEntry
            MAX-ACCESS not-accessible
            STATUS current
            DESCRIPTION
                "An entry for a TCE900."
            INDEX { instOpkDeviceIdx }
            ::= { installOpkTable 1 }

        
        InstallOpkEntry ::=
            SEQUENCE { 
                instOpkDeviceIdx
                    IndexTceDevice,
                instOpkDeviceName
                    SnmpAdminString,
                instOpkNewKey
                    OCTET STRING,
                instOpkMessage
                    SnmpAdminString
             }

        instOpkDeviceIdx OBJECT-TYPE
            SYNTAX IndexTceDevice
            MAX-ACCESS not-accessible
            STATUS current
            DESCRIPTION
                "Index of a TCE90x or TLx."
            ::= { installOpkEntry 1 }

        
        instOpkDeviceName OBJECT-TYPE
            SYNTAX SnmpAdminString
            MAX-ACCESS read-only
            STATUS current
            DESCRIPTION
                "Name of the TCE90x or TLx."
            ::= { installOpkEntry 2 }

        
        instOpkNewKey OBJECT-TYPE
            SYNTAX OCTET STRING (SIZE (0..30))
            MAX-ACCESS read-write
            STATUS current
            DESCRIPTION
                "Setting this object you install an option key for the specified device. 
                Querying this object you get the last set optionkey or an empty string."
            ::= { installOpkEntry 3 }

        
        instOpkMessage OBJECT-TYPE
            SYNTAX SnmpAdminString
            MAX-ACCESS read-only
            STATUS current
            DESCRIPTION
                "When setting instOpkNewKey,
                there is a message showing the result of the action."
            ::= { installOpkEntry 4 }

        
        optionKeyTable OBJECT-TYPE
            SYNTAX SEQUENCE OF OptionKeyEntry
            MAX-ACCESS not-accessible
            STATUS current
            DESCRIPTION
                "This table includes information about installed option keys."
            ::= { commonOptionManagement 2 }

        
        optionKeyEntry OBJECT-TYPE
            SYNTAX OptionKeyEntry
            MAX-ACCESS not-accessible
            STATUS current
            DESCRIPTION
                "An entry for a certain option key."
            INDEX { instOpkDeviceIdx, optionKeyIdx }
            ::= { optionKeyTable 1 }

        
        OptionKeyEntry ::=
            SEQUENCE { 
                optionKeyIdx
                    Unsigned32,
                optionKeyNumber
                    DisplayString,
                optionKeyName
                    SnmpAdminString,
                optionKeyStatus
                    INTEGER,
                optionKeyValidity
                    DisplayString
             }

        optionKeyIdx OBJECT-TYPE
            SYNTAX Unsigned32 (1..50)
            MAX-ACCESS not-accessible
            STATUS current
            DESCRIPTION
                "This is the tables index column for a certain option key."
            ::= { optionKeyEntry 1 }

        
        optionKeyNumber OBJECT-TYPE
            SYNTAX DisplayString (SIZE (2..3))
            MAX-ACCESS read-only
            STATUS current
            DESCRIPTION
                "This is a part of the R&S material number of the option. 
                K0 is always a demo key, K2 and further are the options. 
                See column optionKeyName for the clear-text name."
            ::= { optionKeyEntry 2 }

        
        optionKeyName OBJECT-TYPE
            SYNTAX SnmpAdminString
            MAX-ACCESS read-only
            STATUS current
            DESCRIPTION
                "The option name as text (e.g. SNMP)."
            ::= { optionKeyEntry 3 }

        
        optionKeyStatus OBJECT-TYPE
            SYNTAX INTEGER
                {
                deactivated(1),
                installed(2),
                warning(3),
                fault(4),
                empty(5)
                }
            MAX-ACCESS read-only
            STATUS current
            DESCRIPTION
                "The status of this option key. 
                deactivated(1) means, the function is locked. Typically a demo key ran out.
                installed(2) means, the function is unlocked and operable.
                warning(3) means, the option is expired.
                fault(4) means, the option is required, but not installed.
                "
            ::= { optionKeyEntry 4 }

        
        optionKeyValidity OBJECT-TYPE
            SYNTAX DisplayString
            MAX-ACCESS read-only
            STATUS current
            DESCRIPTION
                "The validity range, e.g. '10 days left'."
            ::= { optionKeyEntry 5 }

        
        deactivationTable OBJECT-TYPE
            SYNTAX SEQUENCE OF DeactivationEntry
            MAX-ACCESS not-accessible
            STATUS current
            DESCRIPTION
                "This table includes information about temporary optionkeys and their
                status."
            ::= { commonOptionManagement 3 }

        
        deactivationEntry OBJECT-TYPE
            SYNTAX DeactivationEntry
            MAX-ACCESS not-accessible
            STATUS current
            DESCRIPTION
                "An entry for a certain option key."
            INDEX { instOpkDeviceIdx, deactivationIdx }
            ::= { deactivationTable 1 }

        
        DeactivationEntry ::=
            SEQUENCE { 
                deactivationIdx
                    Unsigned32,
                deactivationKeyNumber
                    DisplayString,
                deactivationKeyName
                    SnmpAdminString,
                deactivationResponse
                    SnmpAdminString
             }

        deactivationIdx OBJECT-TYPE
            SYNTAX Unsigned32 (1..60)
            MAX-ACCESS not-accessible
            STATUS current
            DESCRIPTION
                "The index for a certain deactivation key."
            ::= { deactivationEntry 1 }

        
        deactivationKeyNumber OBJECT-TYPE
            SYNTAX DisplayString
            MAX-ACCESS read-only
            STATUS current
            DESCRIPTION
                "This is a part of the R&S material number of the option. 
                K0 is always a demo key, K2 and further are the options. 
                See column deactivationKeyName for the clear-text name."
            ::= { deactivationEntry 2 }

        
        deactivationKeyName OBJECT-TYPE
            SYNTAX SnmpAdminString
            MAX-ACCESS read-only
            STATUS current
            DESCRIPTION
                "The option name as text (e.g. SNMP)."
            ::= { deactivationEntry 3 }

        
        deactivationResponse OBJECT-TYPE
            SYNTAX SnmpAdminString
            MAX-ACCESS read-only
            STATUS current
            DESCRIPTION
                "This is what customers send to R&S
                to ensure the option key is deactivated correctly."
            ::= { deactivationEntry 4 }

        
        commonOpkNotificationTable OBJECT-TYPE
            SYNTAX SEQUENCE OF CommonOpkNotificationEntry
            MAX-ACCESS not-accessible
            STATUS current
            DESCRIPTION
                "The context information/configuration for the notifications
                commonOptionKeyStatus"
            ::= { commonOptionManagement 4 }

        
        commonOpkNotificationEntry OBJECT-TYPE
            SYNTAX CommonOpkNotificationEntry
            MAX-ACCESS not-accessible
            STATUS current
            DESCRIPTION
                "An entry in the commonOpkNotificationTable."
            INDEX { instOpkDeviceIdx, commonOpkNotificationIdx }
            ::= { commonOpkNotificationTable 1 }

        
        CommonOpkNotificationEntry ::=
            SEQUENCE { 
                commonOpkNotificationIdx
                    Unsigned32,
                commonOpkNotificationName
                    INTEGER,
                commonOpkNotificationMask
                    NotificationMask,
                commonOpkNotificationPriority
                    NotificationPriority,
                commonOpkNotificationState
                    NotificationState
             }

        commonOpkNotificationIdx OBJECT-TYPE
            SYNTAX Unsigned32 (100)
            MAX-ACCESS not-accessible
            STATUS current
            DESCRIPTION
                "The notification number as below rsXx9CommonNotifications.
                This is a helper column and therefore not-accessible."
            ::= { commonOpkNotificationEntry 2 }

        
        commonOpkNotificationName OBJECT-TYPE
            SYNTAX INTEGER { commonOptionKeyStatus(100) }
            MAX-ACCESS read-only
            STATUS current
            DESCRIPTION
                "The notification number as an enumeration.
                The enumeration correlates with the notifications under rsXx9CommonNotifications."
            ::= { commonOpkNotificationEntry 3 }

        
        commonOpkNotificationMask OBJECT-TYPE
            SYNTAX NotificationMask
            MAX-ACCESS read-write
            STATUS current
            DESCRIPTION
                "See TextualConvention for details."
            ::= { commonOpkNotificationEntry 4 }

        
        commonOpkNotificationPriority OBJECT-TYPE
            SYNTAX NotificationPriority
            MAX-ACCESS read-write
            STATUS current
            DESCRIPTION
                "See TextualConvention for details."
            ::= { commonOpkNotificationEntry 5 }

        
        commonOpkNotificationState OBJECT-TYPE
            SYNTAX NotificationState
            MAX-ACCESS read-only
            STATUS current
            DESCRIPTION
                "See TextualConvention for details."
            ::= { commonOpkNotificationEntry 6 }

        
        commonDateTime OBJECT IDENTIFIER ::= { rsXx9CommonObjects 6 }

        
        commonDateTimeConfigurationTable OBJECT-TYPE
            SYNTAX SEQUENCE OF CommonDateTimeConfigurationEntry
            MAX-ACCESS not-accessible
            STATUS current
            DESCRIPTION
                "This Table gives the possibility for configuration
                of Date, Time and the NTP client."
            ::= { commonDateTime 1 }

        
        commonDateTimeConfigurationEntry OBJECT-TYPE
            SYNTAX CommonDateTimeConfigurationEntry
            MAX-ACCESS not-accessible
            STATUS current
            DESCRIPTION
                "A DateTime configuration entry for a TCE900."
            INDEX { commonDateTimeConfDeviceIdx }
            ::= { commonDateTimeConfigurationTable 1 }

        
        CommonDateTimeConfigurationEntry ::=
            SEQUENCE { 
                commonDateTimeConfDeviceIdx
                    IndexTceDevice,
                commonDateTimeConfDeviceName
                    SnmpAdminString,
                commonDateTimeConfLocalDateTime
                    DateAndTime,
                commonDateTimeConfLocalTimeOffset
                    INTEGER,
                commonDateTimeConfNtpEnable
                    SwitchOnOff,
                commonDateTimeConfNtpServer
                    OCTET STRING
             }

        commonDateTimeConfDeviceIdx OBJECT-TYPE
            SYNTAX IndexTceDevice
            MAX-ACCESS not-accessible
            STATUS current
            DESCRIPTION
                "Index of a TCE90x or TLx."
            ::= { commonDateTimeConfigurationEntry 1 }

        
        commonDateTimeConfDeviceName OBJECT-TYPE
            SYNTAX SnmpAdminString
            MAX-ACCESS read-only
            STATUS current
            DESCRIPTION
                "Name of the TCE90x or TLx."
            ::= { commonDateTimeConfigurationEntry 2 }

        
        commonDateTimeConfLocalDateTime OBJECT-TYPE
            SYNTAX DateAndTime
            MAX-ACCESS read-write
            STATUS current
            DESCRIPTION
                "Shows the local date and time. The time can be changed here. The time is 
                entered in coordinated universal time (UTC) format. It is therefore 
                recommended to correctly set the local time offset relative to 
                UTC before changing the time. The local time offset must be set by
                using commonDateTimeConfLocalTimeOffset
                
                Notes: The range of distance from UTC is -12h..+14h.
                       Omitting the optional UTC fields in a set-request results in keeping
                       the old UTC offset value."
            ::= { commonDateTimeConfigurationEntry 3 }

        
        commonDateTimeConfLocalTimeOffset OBJECT-TYPE
            SYNTAX INTEGER (-720..840)
            UNITS "minute"
            MAX-ACCESS read-write
            STATUS current
            DESCRIPTION
                "Shows the local time offset relative to UTC. The time offset is 
                calculated from the time zone + summer time. The time offset 
                can be changed here and has a direct effect on the displayed 
                local time. It is therefore recommended to check (and if 
                necessary to correct) the local time offset before setting 
                the local time.
                "
            ::= { commonDateTimeConfigurationEntry 4 }

        
        commonDateTimeConfNtpEnable OBJECT-TYPE
            SYNTAX SwitchOnOff
            MAX-ACCESS read-write
            STATUS current
            DESCRIPTION
                "Activates synchronization of the time of this TCE900 with an external 
                or internal NTP server.
                "
            ::= { commonDateTimeConfigurationEntry 5 }

        
        commonDateTimeConfNtpServer OBJECT-TYPE
            SYNTAX OCTET STRING (SIZE (0..255))
            MAX-ACCESS read-write
            STATUS current
            DESCRIPTION
                "Shows the IP address of the NTP server. If available, an external NTP 
                server should be entered for the TCE900 SysCtrl. This field can be left 
                empty for lower-level TCE units that are to be synchronized with the 
                TCE900 SysCtrl. In this case, synchronization takes place via NTP 
                broadcast. Alternatively, the IP address of the TCE900 SysCtrl can 
                also be entered for lower-level devices.
                "
            ::= { commonDateTimeConfigurationEntry 6 }

        
        commonDateTimeNotificationTable OBJECT-TYPE
            SYNTAX SEQUENCE OF CommonDateTimeNotificationEntry
            MAX-ACCESS not-accessible
            STATUS current
            DESCRIPTION
                "The context information/configuration for the notification commonDateTimeNtpState."
            ::= { commonDateTime 2 }

        
        commonDateTimeNotificationEntry OBJECT-TYPE
            SYNTAX CommonDateTimeNotificationEntry
            MAX-ACCESS not-accessible
            STATUS current
            DESCRIPTION
                "An entry in the commonDateTimeNotificationTable."
            INDEX { commonDateTimeNotificationDeviceIdx, commonDateTimeNotificationIdx }
            ::= { commonDateTimeNotificationTable 1 }

        
        CommonDateTimeNotificationEntry ::=
            SEQUENCE { 
                commonDateTimeNotificationDeviceIdx
                    IndexTceDevice,
                commonDateTimeNotificationIdx
                    Unsigned32,
                commonDateTimeNotificationName
                    INTEGER,
                commonDateTimeNotificationMask
                    NotificationMask,
                commonDateTimeNotificationPriority
                    NotificationPriority,
                commonDateTimeNotificationState
                    NotificationState
             }

        commonDateTimeNotificationDeviceIdx OBJECT-TYPE
            SYNTAX IndexTceDevice
            MAX-ACCESS not-accessible
            STATUS current
            DESCRIPTION
                "Index of a TCE90x or TLx."
            ::= { commonDateTimeNotificationEntry 1 }

        
        commonDateTimeNotificationIdx OBJECT-TYPE
            SYNTAX Unsigned32 (2000)
            MAX-ACCESS not-accessible
            STATUS current
            DESCRIPTION
                "The notification number as below rsXx9CommonNotifications.
                This is a helper column and therefore not-accessible."
            ::= { commonDateTimeNotificationEntry 2 }

        
        commonDateTimeNotificationName OBJECT-TYPE
            SYNTAX INTEGER { commonDateTimeNtpState(2000) }
            MAX-ACCESS read-only
            STATUS current
            DESCRIPTION
                "The notification number as an enumeration.
                The enumeration correlates with the notifications under rsXx9CommonNotifications."
            ::= { commonDateTimeNotificationEntry 3 }

        
        commonDateTimeNotificationMask OBJECT-TYPE
            SYNTAX NotificationMask
            MAX-ACCESS read-write
            STATUS current
            DESCRIPTION
                "See TextualConvention for details."
            ::= { commonDateTimeNotificationEntry 4 }

        
        commonDateTimeNotificationPriority OBJECT-TYPE
            SYNTAX NotificationPriority
            MAX-ACCESS read-write
            STATUS current
            DESCRIPTION
                "See TextualConvention for details."
            ::= { commonDateTimeNotificationEntry 5 }

        
        commonDateTimeNotificationState OBJECT-TYPE
            SYNTAX NotificationState
            MAX-ACCESS read-only
            STATUS current
            DESCRIPTION
                "See TextualConvention for details."
            ::= { commonDateTimeNotificationEntry 6 }

        
        commonUPS OBJECT IDENTIFIER ::= { rsXx9CommonObjects 7 }

        
        upsInformationTable OBJECT-TYPE
            SYNTAX SEQUENCE OF UpsInformationEntry
            MAX-ACCESS not-accessible
            STATUS current
            DESCRIPTION
                "Information about UPS for TCEs.
                Several TCEs may be connected to the same UPS.
                In this case the same information is listed
                for each of this TCEs."
            ::= { commonUPS 1 }

        
        upsInformationEntry OBJECT-TYPE
            SYNTAX UpsInformationEntry
            MAX-ACCESS not-accessible
            STATUS current
            DESCRIPTION
                "An entry in the upsInformationTable."
            INDEX { upsInfoDeviceIdx }
            ::= { upsInformationTable 1 }

        
        UpsInformationEntry ::=
            SEQUENCE { 
                upsInfoDeviceIdx
                    IndexTceDevice,
                upsInfoWithUPS
                    INTEGER,
                upsInfoLink
                    NotificationState,
                upsInfoManufacturer
                    SnmpAdminString,
                upsInfoModel
                    SnmpAdminString,
                upsInfoSoftwareVersion
                    SnmpAdminString,
                upsInfoName
                    SnmpAdminString,
                upsInfoAttachedDevices
                    SnmpAdminString,
                upsInfoBatteryStatus
                    INTEGER,
                upsInfoSecondsOnBattery
                    Unsigned32,
                upsInfoMinutesRemaining
                    Unsigned32,
                upsInfoChargeRemaining
                    Unsigned32,
                upsInfoOutputSource
                    INTEGER,
                upsInfoOutputPower
                    Unsigned32,
                upsInfoSelftestResult
                    INTEGER
             }

        upsInfoDeviceIdx OBJECT-TYPE
            SYNTAX IndexTceDevice
            MAX-ACCESS not-accessible
            STATUS current
            DESCRIPTION
                "Index of a TCE90x or TLx."
            ::= { upsInformationEntry 1 }

        
        upsInfoWithUPS OBJECT-TYPE
            SYNTAX INTEGER
                {
                unconfigured(1),
                disabled(2),
                enabled(3)
                }
            MAX-ACCESS read-only
            STATUS current
            DESCRIPTION
                "This TCE900 is connected to UPS.
                
                If the value isn't enabled(3),
                values for the other columns are not delivered for this TCE900."
            ::= { upsInformationEntry 2 }

        
        upsInfoLink OBJECT-TYPE
            SYNTAX NotificationState
            MAX-ACCESS read-only
            STATUS current
            DESCRIPTION
                "State of communication link to UPS."
            ::= { upsInformationEntry 3 }

        
        upsInfoManufacturer OBJECT-TYPE
            SYNTAX SnmpAdminString
            MAX-ACCESS read-only
            STATUS current
            DESCRIPTION
                "name of the UPS manufacturer"
            ::= { upsInformationEntry 4 }

        
        upsInfoModel OBJECT-TYPE
            SYNTAX SnmpAdminString
            MAX-ACCESS read-only
            STATUS current
            DESCRIPTION
                "UPS model designation"
            ::= { upsInformationEntry 5 }

        
        upsInfoSoftwareVersion OBJECT-TYPE
            SYNTAX SnmpAdminString
            MAX-ACCESS read-only
            STATUS current
            DESCRIPTION
                "UPS firmware/software version(s)"
            ::= { upsInformationEntry 6 }

        
        upsInfoName OBJECT-TYPE
            SYNTAX SnmpAdminString
            MAX-ACCESS read-only
            STATUS current
            DESCRIPTION
                "identifying the UPS"
            ::= { upsInformationEntry 7 }

        
        upsInfoAttachedDevices OBJECT-TYPE
            SYNTAX SnmpAdminString
            MAX-ACCESS read-only
            STATUS current
            DESCRIPTION
                "identifying the devices attached to the output(s) of the UPS"
            ::= { upsInformationEntry 8 }

        
        upsInfoBatteryStatus OBJECT-TYPE
            SYNTAX INTEGER
                {
                unknown(1),
                ok(2),
                low(3),
                deplated(4)
                }
            MAX-ACCESS read-only
            STATUS current
            DESCRIPTION
                "indication of the capacity remaining in the UPS system's batteries"
            ::= { upsInformationEntry 9 }

        
        upsInfoSecondsOnBattery OBJECT-TYPE
            SYNTAX Unsigned32
            UNITS "second"
            MAX-ACCESS read-only
            STATUS current
            DESCRIPTION
                "If the unit is on battery power,
                the elapsed time since the UPS last switched to battery power."
            ::= { upsInformationEntry 10 }

        
        upsInfoMinutesRemaining OBJECT-TYPE
            SYNTAX Unsigned32
            UNITS "minute"
            MAX-ACCESS read-only
            STATUS current
            DESCRIPTION
                "an estimate of the time to battery charge depletion"
            ::= { upsInformationEntry 11 }

        
        upsInfoChargeRemaining OBJECT-TYPE
            SYNTAX Unsigned32
            UNITS "percent"
            MAX-ACCESS read-only
            STATUS current
            DESCRIPTION
                "an estimate of the battery charge remaining"
            ::= { upsInformationEntry 12 }

        
        upsInfoOutputSource OBJECT-TYPE
            SYNTAX INTEGER
                {
                other(1),
                none(2),
                normal(3),
                bypass(4),
                battery(5),
                booster(6),
                reducer(7)
                }
            MAX-ACCESS read-only
            STATUS current
            DESCRIPTION
                "present source of output power"
            ::= { upsInformationEntry 13 }

        
        upsInfoOutputPower OBJECT-TYPE
            SYNTAX Unsigned32
            UNITS "W"
            MAX-ACCESS read-only
            STATUS current
            DESCRIPTION
                "power summed up over all output lines"
            ::= { upsInformationEntry 14 }

        
        upsInfoSelftestResult OBJECT-TYPE
            SYNTAX INTEGER
                {
                donePass(1),
                doneWarning(2),
                doneError(3),
                aborted(4),
                inProgress(5),
                noTestInitiated(6)
                }
            MAX-ACCESS read-only
            STATUS current
            DESCRIPTION
                "results of the current or last UPS diagnostics test performed"
            ::= { upsInformationEntry 15 }

        
        commonGPS OBJECT IDENTIFIER ::= { rsXx9CommonObjects 8 }

        
        commonGpsConfigurationTable OBJECT-TYPE
            SYNTAX SEQUENCE OF CommonGpsConfigurationEntry
            MAX-ACCESS not-accessible
            STATUS current
            DESCRIPTION
                "Table to configure GNSS (GPS, GLONASS)"
            ::= { commonGPS 1 }

        
        commonGpsConfigurationEntry OBJECT-TYPE
            SYNTAX CommonGpsConfigurationEntry
            MAX-ACCESS not-accessible
            STATUS current
            DESCRIPTION
                "An entry in the commonGpsConfigurationTable"
            INDEX { commonGpsConfDeviceIdx }
            ::= { commonGpsConfigurationTable 1 }

        
        CommonGpsConfigurationEntry ::=
            SEQUENCE { 
                commonGpsConfDeviceIdx
                    IndexTceDevice,
                commonGpsConfDeviceName
                    SnmpAdminString,
                commonGpsConfAntennaType
                    GpsPowerSource,
                commonGpsStateMonitoring
                    INTEGER,
                commonGpsConfGnssSelection
                    INTEGER
             }

        commonGpsConfDeviceIdx OBJECT-TYPE
            SYNTAX IndexTceDevice
            MAX-ACCESS not-accessible
            STATUS current
            DESCRIPTION
                "Index of a TCE90x or TLx."
            ::= { commonGpsConfigurationEntry 1 }

        
        commonGpsConfDeviceName OBJECT-TYPE
            SYNTAX SnmpAdminString
            MAX-ACCESS read-only
            STATUS current
            DESCRIPTION
                "Name of the TCE90x or TLx."
            ::= { commonGpsConfigurationEntry 2 }

        
        commonGpsConfAntennaType OBJECT-TYPE
            SYNTAX GpsPowerSource
            MAX-ACCESS read-write
            STATUS current
            DESCRIPTION
                "Indicates which antenna type is being used. 
                Passive: The R&S TCE90x exciter does not provide a supply voltage 
                for a GNSS antenna. 
                Active: The R&S TCE90x exciter provides a 5 V supply voltage for a 
                GNSS antenna. The setting can be changed here. If the antenna 
                supplied by Rohde & Schwarz is used, the 'Active' antenna type 
                must be selected.
                "
            ::= { commonGpsConfigurationEntry 3 }

        
        commonGpsStateMonitoring OBJECT-TYPE
            SYNTAX INTEGER
                {
                undefined(1),
                off(2),
                on(3)
                }
            MAX-ACCESS read-write
            STATUS current
            DESCRIPTION
                "turns the commonGpsState notification on and off. 
                This is useful in the case, that no GNSS module shall be used. 
                By default, the notification is on, if a GPS optionKey is installed, 
                otherwise it is off. 
                "
            ::= { commonGpsConfigurationEntry 4 }

        
        commonGpsConfGnssSelection OBJECT-TYPE
            SYNTAX INTEGER
                {
                undefined(1),
                unknown(2),
                none(3),
                gps(4),
                glonass(5),
                gpsAndGlonass(6)
                }
            MAX-ACCESS read-write
            STATUS current
            DESCRIPTION
                "Chooses the GNSS, which shall be used. 
                
                gps: only GPS and SBAS satellites are used. 
                glonass: only GLONASS and SBAS satellites are used.
                gpsAndGlonass: GPS, GLONASS and SBAS satellites are used. 
                "
            ::= { commonGpsConfigurationEntry 5 }

        
        commonGpsStateTable OBJECT-TYPE
            SYNTAX SEQUENCE OF CommonGpsStateEntry
            MAX-ACCESS not-accessible
            STATUS current
            DESCRIPTION
                "The GNSS (GPS, GLONASS) state table."
            ::= { commonGPS 2 }

        
        commonGpsStateEntry OBJECT-TYPE
            SYNTAX CommonGpsStateEntry
            MAX-ACCESS not-accessible
            STATUS current
            DESCRIPTION
                "an entry in the commonGpsStateTable"
            INDEX { commonGpsNotificationDeviceIdx }
            ::= { commonGpsStateTable 1 }

        
        CommonGpsStateEntry ::=
            SEQUENCE { 
                commonGpsStAntennaState
                    INTEGER,
                commonGpsStTdop
                    Unsigned32,
                commonGpsStSatellitesInView
                    Unsigned32,
                commonGpsStUsedSatellites
                    Unsigned32
             }

        commonGpsStAntennaState OBJECT-TYPE
            SYNTAX INTEGER
                {
                undefined(1),
                init(2),
                dontKnow(3),
                ok(4),
                short(5),
                open(6),
                notMonitored(7)
                }
            MAX-ACCESS read-only
            STATUS current
            DESCRIPTION
                "Indicates whether a connection to the GNSS antenna can be set up 
                or whether a fault is present. 
                
                Unknown: With the 'Passive' antenna type, detection of the antenna connection is not possible. 
                Short Circuit: There is a short circuit at the antenna input. 
                Not Connected: The connection to the antenna is interrupted. 
                Ok: The connection to the antenna or to the antenna splitter is set up.
                "
            ::= { commonGpsStateEntry 1 }

        
        commonGpsStTdop OBJECT-TYPE
            SYNTAX Unsigned32 (0..65535)
            MAX-ACCESS read-only
            STATUS current
            DESCRIPTION
                "Time dilution of precision (TDOP). This is a measure of the spread of the 
                measurement results for calculating the time. It depends on the 
                geographical position of the receivable satellites. If the receivable 
                satellites are positioned very closely together or are very low on the 
                horizon, the time calculation will be imprecise. A low value describes a 
                good geometrical arrangement of the satellites. A value less than 2 
                should be achieved. Large values are returned if the line of sight of the 
                receiving antenna is restricted.
                "
            ::= { commonGpsStateEntry 2 }

        
        commonGpsStSatellitesInView OBJECT-TYPE
            SYNTAX Unsigned32 (0..16)
            MAX-ACCESS read-only
            STATUS current
            DESCRIPTION
                "Indicates how many satellites are in the line of sight of the antenna. 
                Only satellites that differ in their relative position to one another 
                and that are not too low on the horizon are used for calculating the 
                time.
                "
            ::= { commonGpsStateEntry 3 }

        
        commonGpsStUsedSatellites OBJECT-TYPE
            SYNTAX Unsigned32 (0..16)
            MAX-ACCESS read-only
            STATUS current
            DESCRIPTION
                "Indicates how many satellites are used for calculating the current time. 
                Precise calculation is only possible if the signals from at least 4 
                satellites are available.
                "
            ::= { commonGpsStateEntry 4 }

        
        commonGpsNotificationTable OBJECT-TYPE
            SYNTAX SEQUENCE OF CommonGpsNotificationEntry
            MAX-ACCESS not-accessible
            STATUS current
            DESCRIPTION
                "The GNSS (GPS, GLONASS) notification table. "
            ::= { commonGPS 3 }

        
        commonGpsNotificationEntry OBJECT-TYPE
            SYNTAX CommonGpsNotificationEntry
            MAX-ACCESS not-accessible
            STATUS current
            DESCRIPTION
                "An entry in the commonGpsNotificationTable."
            INDEX { commonGpsNotificationDeviceIdx, commonGpsNotificationIdx }
            ::= { commonGpsNotificationTable 1 }

        
        CommonGpsNotificationEntry ::=
            SEQUENCE { 
                commonGpsNotificationDeviceIdx
                    IndexTceDevice,
                commonGpsNotificationIdx
                    Unsigned32,
                commonGpsNotificationName
                    INTEGER,
                commonGpsNotificationMask
                    NotificationMask,
                commonGpsNotificationPriority
                    NotificationPriority,
                commonGpsNotificationState
                    NotificationState
             }

        commonGpsNotificationDeviceIdx OBJECT-TYPE
            SYNTAX IndexTceDevice
            MAX-ACCESS not-accessible
            STATUS current
            DESCRIPTION
                "Index of a TCE90x."
            ::= { commonGpsNotificationEntry 1 }

        
        commonGpsNotificationIdx OBJECT-TYPE
            SYNTAX Unsigned32 (3000)
            MAX-ACCESS not-accessible
            STATUS current
            DESCRIPTION
                "The notification number as below rsXx9CommonNotifications.
                This is a helper column and therefore not-accessible."
            ::= { commonGpsNotificationEntry 2 }

        
        commonGpsNotificationName OBJECT-TYPE
            SYNTAX INTEGER { commonGpsState(3000) }
            MAX-ACCESS read-only
            STATUS current
            DESCRIPTION
                "The notification number as an enumeration.
                The enumeration correlates with the notifications under rsXx9CommonNotifications."
            ::= { commonGpsNotificationEntry 3 }

        
        commonGpsNotificationMask OBJECT-TYPE
            SYNTAX NotificationMask
            MAX-ACCESS read-write
            STATUS current
            DESCRIPTION
                "See TextualConvention for details."
            ::= { commonGpsNotificationEntry 4 }

        
        commonGpsNotificationPriority OBJECT-TYPE
            SYNTAX NotificationPriority
            MAX-ACCESS read-write
            STATUS current
            DESCRIPTION
                "See TextualConvention for details."
            ::= { commonGpsNotificationEntry 5 }

        
        commonGpsNotificationState OBJECT-TYPE
            SYNTAX NotificationState
            MAX-ACCESS read-only
            STATUS current
            DESCRIPTION
                "See TextualConvention for details."
            ::= { commonGpsNotificationEntry 6 }

        
        commonDeviceInformation OBJECT IDENTIFIER ::= { rsXx9CommonObjects 9 }

        
        commonDevInfoStateTable OBJECT-TYPE
            SYNTAX SEQUENCE OF CommonDevInfoStateEntry
            MAX-ACCESS not-accessible
            STATUS current
            DESCRIPTION
                "Table about device information state."
            ::= { commonDeviceInformation 1 }

        
        commonDevInfoStateEntry OBJECT-TYPE
            SYNTAX CommonDevInfoStateEntry
            MAX-ACCESS not-accessible
            STATUS current
            DESCRIPTION
                "An entry in the commonDevInfoStateTable."
            INDEX { devInfoStateDeviceIdx }
            ::= { commonDevInfoStateTable 1 }

        
        CommonDevInfoStateEntry ::=
            SEQUENCE { 
                devInfoStateDeviceIdx
                    IndexTceDevice,
                devInfoStateDeviceName
                    SnmpAdminString,
                devInfoStateCapacitorBatteryInstalled
                    TruthValue
             }

        devInfoStateDeviceIdx OBJECT-TYPE
            SYNTAX IndexTceDevice
            MAX-ACCESS not-accessible
            STATUS current
            DESCRIPTION
                "Index of a TCE90x or TLx."
            ::= { commonDevInfoStateEntry 1 }

        
        devInfoStateDeviceName OBJECT-TYPE
            SYNTAX SnmpAdminString
            MAX-ACCESS read-only
            STATUS current
            DESCRIPTION
                "Name of the TCE90x or TLx."
            ::= { commonDevInfoStateEntry 2 }

        
        devInfoStateCapacitorBatteryInstalled OBJECT-TYPE
            SYNTAX TruthValue
            MAX-ACCESS read-only
            STATUS current
            DESCRIPTION
                "Indicates if a capacitor battery is installed
                only valid for TLx devices"
            ::= { commonDevInfoStateEntry 3 }

        
        commonDevInfoNotificationTable OBJECT-TYPE
            SYNTAX SEQUENCE OF CommonDevInfoNotificationEntry
            MAX-ACCESS not-accessible
            STATUS current
            DESCRIPTION
                "The device information notification table."
            ::= { commonDeviceInformation 2 }

        
        commonDevInfoNotificationEntry OBJECT-TYPE
            SYNTAX CommonDevInfoNotificationEntry
            MAX-ACCESS not-accessible
            STATUS current
            DESCRIPTION
                "An entry in the commonDevInfoNotificationTable."
            INDEX { commonDevInfoNotificationDeviceIdx, commonDevInfoNotificationIdx }
            ::= { commonDevInfoNotificationTable 1 }

        
        CommonDevInfoNotificationEntry ::=
            SEQUENCE { 
                commonDevInfoNotificationDeviceIdx
                    IndexTceDevice,
                commonDevInfoNotificationIdx
                    Unsigned32,
                commonDevInfoNotificationName
                    INTEGER,
                commonDevInfoNotificationMask
                    NotificationMask,
                commonDevInfoNotificationPriority
                    NotificationPriority,
                commonDevInfoNotificationState
                    NotificationState
             }

        commonDevInfoNotificationDeviceIdx OBJECT-TYPE
            SYNTAX IndexTceDevice
            MAX-ACCESS not-accessible
            STATUS current
            DESCRIPTION
                "Index of a TCE90x or TLx."
            ::= { commonDevInfoNotificationEntry 1 }

        
        commonDevInfoNotificationIdx OBJECT-TYPE
            SYNTAX Unsigned32 (4000 | 4100 | 4200)
            MAX-ACCESS not-accessible
            STATUS current
            DESCRIPTION
                "The notification number as below rsXx9CommonNotifications.
                This is a helper column and therefore not-accessible."
            ::= { commonDevInfoNotificationEntry 2 }

        
        commonDevInfoNotificationName OBJECT-TYPE
            SYNTAX INTEGER
                {
                commonDevInfoAcFail(4000),
                commonDevInfoFanState(4100),
                commonDevInfoOvpState(4200)
                }
            MAX-ACCESS read-only
            STATUS current
            DESCRIPTION
                "The notification number as an enumeration.
                The enumeration correlates with the notifications under rsXx9CommonNotifications."
            ::= { commonDevInfoNotificationEntry 3 }

        
        commonDevInfoNotificationMask OBJECT-TYPE
            SYNTAX NotificationMask
            MAX-ACCESS read-write
            STATUS current
            DESCRIPTION
                "See TextualConvention for details."
            ::= { commonDevInfoNotificationEntry 4 }

        
        commonDevInfoNotificationPriority OBJECT-TYPE
            SYNTAX NotificationPriority
            MAX-ACCESS read-write
            STATUS current
            DESCRIPTION
                "See TextualConvention for details."
            ::= { commonDevInfoNotificationEntry 5 }

        
        commonDevInfoNotificationState OBJECT-TYPE
            SYNTAX NotificationState
            MAX-ACCESS read-only
            STATUS current
            DESCRIPTION
                "See TextualConvention for details."
            ::= { commonDevInfoNotificationEntry 6 }

        
        commonDevInfoConfigTable OBJECT-TYPE
            SYNTAX SEQUENCE OF CommonDevInfoConfigEntry
            MAX-ACCESS not-accessible
            STATUS current
            DESCRIPTION
                "Configure Device sepcific parameters."
            ::= { commonDeviceInformation 3 }

        
        commonDevInfoConfigEntry OBJECT-TYPE
            SYNTAX CommonDevInfoConfigEntry
            MAX-ACCESS not-accessible
            STATUS current
            DESCRIPTION
                "An entry in the commonDevInfoConfigTable. "
            INDEX { devInfoStateDeviceIdx }
            ::= { commonDevInfoConfigTable 1 }

        
        CommonDevInfoConfigEntry ::=
            SEQUENCE { 
                commonDevInfoConfAssignOvp
                    SwitchOnOff
             }

        commonDevInfoConfAssignOvp OBJECT-TYPE
            SYNTAX SwitchOnOff
            MAX-ACCESS read-write
            STATUS current
            DESCRIPTION
                "Description."
            ::= { commonDevInfoConfigEntry 1 }

        
        commonEnvironment OBJECT IDENTIFIER ::= { rsXx9CommonObjects 10 }

        
        commonEnvConfigurationTable OBJECT-TYPE
            SYNTAX SEQUENCE OF CommonEnvConfigurationEntry
            MAX-ACCESS not-accessible
            STATUS current
            DESCRIPTION
                "Description."
            ::= { commonEnvironment 1 }

        
        commonEnvConfigurationEntry OBJECT-TYPE
            SYNTAX CommonEnvConfigurationEntry
            MAX-ACCESS not-accessible
            STATUS current
            DESCRIPTION
                "Description."
            INDEX { commonEnvConfDeviceIdx }
            ::= { commonEnvConfigurationTable 1 }

        
        CommonEnvConfigurationEntry ::=
            SEQUENCE { 
                commonEnvConfDeviceIdx
                    IndexTceDevice,
                commonEnvConfDeviceName
                    SnmpAdminString,
                commonEnvConfTempWarnUpper
                    Integer32,
                commonEnvConfTempFaultUpper
                    Integer32,
                commonEnvConfTempWarnLower
                    Integer32,
                commonEnvConfTempFaultLower
                    Integer32
             }

        commonEnvConfDeviceIdx OBJECT-TYPE
            SYNTAX IndexTceDevice
            MAX-ACCESS not-accessible
            STATUS current
            DESCRIPTION
                "Index of a TCE90x or TLx."
            ::= { commonEnvConfigurationEntry 1 }

        
        commonEnvConfDeviceName OBJECT-TYPE
            SYNTAX SnmpAdminString
            MAX-ACCESS read-only
            STATUS current
            DESCRIPTION
                "Name of the TCE90x or TLx."
            ::= { commonEnvConfigurationEntry 2 }

        
        commonEnvConfTempWarnUpper OBJECT-TYPE
            SYNTAX Integer32 (10..450)
            UNITS "0.1 degree Celsius"
            MAX-ACCESS read-write
            STATUS current
            DESCRIPTION
                "Description."
            ::= { commonEnvConfigurationEntry 3 }

        
        commonEnvConfTempFaultUpper OBJECT-TYPE
            SYNTAX Integer32 (10..450)
            UNITS "0.1 degree Celsius"
            MAX-ACCESS read-only
            STATUS current
            DESCRIPTION
                "Description."
            ::= { commonEnvConfigurationEntry 4 }

        
        commonEnvConfTempWarnLower OBJECT-TYPE
            SYNTAX Integer32 (10..450)
            UNITS "0.1 degree Celsius"
            MAX-ACCESS read-write
            STATUS current
            DESCRIPTION
                "Description."
            ::= { commonEnvConfigurationEntry 5 }

        
        commonEnvConfTempFaultLower OBJECT-TYPE
            SYNTAX Integer32 (10..450)
            UNITS "0.1 degree Celsius"
            MAX-ACCESS read-only
            STATUS current
            DESCRIPTION
                "Description."
            ::= { commonEnvConfigurationEntry 6 }

        
        commonEnvStateTable OBJECT-TYPE
            SYNTAX SEQUENCE OF CommonEnvStateEntry
            MAX-ACCESS not-accessible
            STATUS current
            DESCRIPTION
                "Description."
            ::= { commonEnvironment 2 }

        
        commonEnvStateEntry OBJECT-TYPE
            SYNTAX CommonEnvStateEntry
            MAX-ACCESS not-accessible
            STATUS current
            DESCRIPTION
                "Description."
            INDEX { commonEnvConfDeviceIdx }
            ::= { commonEnvStateTable 1 }

        
        CommonEnvStateEntry ::=
            SEQUENCE { 
                commonEnvStTemperature
                    Integer32,
                commonEnvStHumidity
                    Integer32,
                commonEnvStDewPoint
                    Integer32
             }

        commonEnvStTemperature OBJECT-TYPE
            SYNTAX Integer32 (-40..500)
            UNITS "0.1 degree Celsius"
            MAX-ACCESS read-only
            STATUS current
            DESCRIPTION
                "Description."
            ::= { commonEnvStateEntry 1 }

        
        commonEnvStHumidity OBJECT-TYPE
            SYNTAX Integer32 (0..100)
            UNITS "percent"
            MAX-ACCESS read-only
            STATUS current
            DESCRIPTION
                "Description."
            ::= { commonEnvStateEntry 2 }

        
        commonEnvStDewPoint OBJECT-TYPE
            SYNTAX Integer32
            UNITS "0.1 degree Celsius"
            MAX-ACCESS read-only
            STATUS current
            DESCRIPTION
                "Description."
            ::= { commonEnvStateEntry 3 }

        
        commonEnvNotificationTable OBJECT-TYPE
            SYNTAX SEQUENCE OF CommonEnvNotificationEntry
            MAX-ACCESS not-accessible
            STATUS current
            DESCRIPTION
                "Description."
            ::= { commonEnvironment 3 }

        
        commonEnvNotificationEntry OBJECT-TYPE
            SYNTAX CommonEnvNotificationEntry
            MAX-ACCESS not-accessible
            STATUS current
            DESCRIPTION
                "Description."
            INDEX { commonEnvNotificationDeviceIdx, commonEnvNotificationIdx }
            ::= { commonEnvNotificationTable 1 }

        
        CommonEnvNotificationEntry ::=
            SEQUENCE { 
                commonEnvNotificationDeviceIdx
                    IndexTceDevice,
                commonEnvNotificationIdx
                    Unsigned32,
                commonEnvNotificationName
                    INTEGER,
                commonEnvNotificationMask
                    NotificationMask,
                commonEnvNotificationPriority
                    NotificationPriority,
                commonEnvNotificationState
                    NotificationState
             }

        commonEnvNotificationDeviceIdx OBJECT-TYPE
            SYNTAX IndexTceDevice
            MAX-ACCESS not-accessible
            STATUS current
            DESCRIPTION
                "Index of a TCE90x."
            ::= { commonEnvNotificationEntry 1 }

        
        commonEnvNotificationIdx OBJECT-TYPE
            SYNTAX Unsigned32 (5000..5002)
            MAX-ACCESS not-accessible
            STATUS current
            DESCRIPTION
                "The notification number as below rsXx9CommonNotifications.
                This is a helper column and therefore not-accessible."
            ::= { commonEnvNotificationEntry 2 }

        
        commonEnvNotificationName OBJECT-TYPE
            SYNTAX INTEGER
                {
                commonEnvSummary(5000),
                commonEnvTemperature(5001),
                commonEnvDewPoint(5002)
                }
            MAX-ACCESS read-only
            STATUS current
            DESCRIPTION
                "Description."
            ::= { commonEnvNotificationEntry 3 }

        
        commonEnvNotificationMask OBJECT-TYPE
            SYNTAX NotificationMask
            MAX-ACCESS read-write
            STATUS current
            DESCRIPTION
                "Description."
            ::= { commonEnvNotificationEntry 4 }

        
        commonEnvNotificationPriority OBJECT-TYPE
            SYNTAX NotificationPriority
            MAX-ACCESS read-write
            STATUS current
            DESCRIPTION
                "Description."
            ::= { commonEnvNotificationEntry 5 }

        
        commonEnvNotificationState OBJECT-TYPE
            SYNTAX NotificationState
            MAX-ACCESS read-only
            STATUS current
            DESCRIPTION
                "Description."
            ::= { commonEnvNotificationEntry 6 }

        
        rsXx9CommonConformance OBJECT IDENTIFIER ::= { rsXx9Common 2 }

        
        rsXx9CommonCompliances OBJECT IDENTIFIER ::= { rsXx9CommonConformance 1 }

        
        commonBasicCompliance MODULE-COMPLIANCE
            STATUS current
            DESCRIPTION 
                "The compliance statement for XX9000 entities
                which implement this MIB module."
            MODULE -- this module
                MANDATORY-GROUPS { commonObjBasic, commonObjNtp, commonObjSoftwareUpdate, commonObjCustomNotification, commonObjOptionManagement, 
                    commonNotifyBasic, commonNotifyNtp, commonNotifySoftwareUpdate, commonNotifyCustomNotification, commonNotifyOptionManagement, 
                    commonObjUPS }
            ::= { rsXx9CommonCompliances 1 }

        
        rsXx9CommonGroups OBJECT IDENTIFIER ::= { rsXx9CommonConformance 2 }

        
        commonObjBasic OBJECT-GROUP
            OBJECTS { commonDateAndTime, rsNotificationsAllWarningsOff, rsNotificationsAllWarningsOn, rsNotificationsAllFaultsOff, rsNotificationsAllFaultsOn, 
                rsNotificationsAllOff, rsNotificationsAllOn, irtNotificationsAllOff, irtNotificationsAllOn, commonEntPhysicalPowerUpCycles, 
                commonEntPhysicalOperationHours, commonEntPhysicalSwFwBiosNumber, commonNotificationAlarmClass, commonTrapCounter, commonSystemNumberOfTxA, 
                commonSystemType, commonFuncCoolingControl, commonFuncSignalProcessing, commonFuncTxControl, commonFuncSystemControl, 
                sendTestNotification, reboot, commonTxNotificationName, commonTxNotificationMask, commonTxNotificationPriority, 
                commonTxNotificationState, cmnTxCtrlRedundancyMode, commonFuncRackControl, snmpEnable, snmpSyncTrapSinks, 
                commonEntPhysicalConfigurationStatus, commonEntPhysicalHardwareStatus, cmnTxCtrlAmplifierType, cmnTxCtrlModulationMode, commonEntPhysicalType
                 }
            STATUS current
            DESCRIPTION 
                "Basic objects group."
            ::= { rsXx9CommonGroups 1 }

        
        commonObjNtp OBJECT-GROUP
            OBJECTS { commonDateTimeConfDeviceName, commonDateTimeConfLocalDateTime, commonDateTimeConfLocalTimeOffset, commonDateTimeConfNtpEnable, commonDateTimeConfNtpServer, 
                commonDateTimeNotificationName, commonDateTimeNotificationMask, commonDateTimeNotificationPriority, commonDateTimeNotificationState }
            STATUS current
            DESCRIPTION 
                "Objects for handling time and its synchronization via NTP."
            ::= { rsXx9CommonGroups 2 }

        
        commonObjSoftwareUpdate OBJECT-GROUP
            OBJECTS { swUpdateStart, swUpdateMode, swUpdateDeviceName, swUpdateDeviceGroup, swUpdateRebootPending
                 }
            STATUS current
            DESCRIPTION 
                "Objects for handling software update."
            ::= { rsXx9CommonGroups 3 }

        
        commonObjCustomNotification OBJECT-GROUP
            OBJECTS { customNotificationVariable, customNotificationSampleType, customNotificationValue, customNotificationRisingThreshold, customNotificationFallingThreshold, 
                customNotificationStatus, customNotificationPriority, customNotificationInterval }
            STATUS current
            DESCRIPTION 
                "Objects for defining custom notifications."
            ::= { rsXx9CommonGroups 4 }

        
        commonObjOptionManagement OBJECT-GROUP
            OBJECTS { optionKeyName, optionKeyStatus, optionKeyValidity, instOpkDeviceName, commonOpkNotificationState, 
                commonOpkNotificationPriority, commonOpkNotificationMask, commonOpkNotificationName, deactivationResponse, deactivationKeyName, 
                deactivationKeyNumber, instOpkMessage, instOpkNewKey, optionKeyNumber }
            STATUS current
            DESCRIPTION 
                "Objects for handling option management."
            ::= { rsXx9CommonGroups 5 }

        
        commonObjUPS OBJECT-GROUP
            OBJECTS { upsInfoWithUPS, upsInfoLink, upsInfoManufacturer, upsInfoModel, upsInfoSoftwareVersion, 
                upsInfoName, upsInfoAttachedDevices, upsInfoBatteryStatus, upsInfoSecondsOnBattery, upsInfoMinutesRemaining, 
                upsInfoChargeRemaining, upsInfoOutputSource, upsInfoOutputPower, upsInfoSelftestResult }
            STATUS current
            DESCRIPTION 
                "Objects for UPS information."
            ::= { rsXx9CommonGroups 6 }

        
        commonObjGps OBJECT-GROUP
            OBJECTS { commonGpsConfAntennaType, commonGpsStAntennaState, commonGpsStTdop, commonGpsStSatellitesInView, commonGpsStateMonitoring, 
                commonGpsConfGnssSelection, commonGpsStUsedSatellites, commonGpsConfDeviceName, commonGpsNotificationName, commonGpsNotificationMask, 
                commonGpsNotificationPriority, commonGpsNotificationState }
            STATUS current
            DESCRIPTION 
                "Objects for GNSS information."
            ::= { rsXx9CommonGroups 7 }

        
        commonObjDeviceInformation OBJECT-GROUP
            OBJECTS { devInfoStateDeviceName, devInfoStateCapacitorBatteryInstalled, commonDevInfoNotificationName, commonDevInfoNotificationMask, commonDevInfoNotificationPriority, 
                commonDevInfoNotificationState, commonDevInfoConfAssignOvp }
            STATUS current
            DESCRIPTION 
                "Description."
            ::= { rsXx9CommonGroups 8 }

        
        commonObjEnvironment OBJECT-GROUP
            OBJECTS { commonEnvConfTempWarnUpper, commonEnvConfTempFaultUpper, commonEnvConfTempWarnLower, commonEnvConfTempFaultLower, commonEnvStTemperature, 
                commonEnvStHumidity, commonEnvStDewPoint, commonEnvNotificationName, commonEnvNotificationMask, commonEnvNotificationPriority, 
                commonEnvNotificationState, commonEnvConfDeviceName }
            STATUS current
            DESCRIPTION 
                "Description."
            ::= { rsXx9CommonGroups 9 }

        
        commonObjNtpObsoleted OBJECT-GROUP
            OBJECTS { ntpMode, ntpSyncTimeInterval, ntpServerAddrIdx, ntpServerAddressType, ntpServerAddress, 
                ntpLastSync, ntpState }
            STATUS obsolete
            DESCRIPTION 
                "Obsoleted objects for handling time synchronization via NTP."
            ::= { rsXx9CommonGroups 50 }

        
        commonNotifyBasic NOTIFICATION-GROUP
            NOTIFICATIONS { commonTest }
            STATUS current
            DESCRIPTION 
                "Basic notifications group."
            ::= { rsXx9CommonGroups 100 }

        
        commonNotifyNtp NOTIFICATION-GROUP
            NOTIFICATIONS { commonDateTimeNtpState }
            STATUS current
            DESCRIPTION 
                "Notifications for time synchronization via NTP."
            ::= { rsXx9CommonGroups 101 }

        
        commonNotifySoftwareUpdate NOTIFICATION-GROUP
            NOTIFICATIONS { commonSwUpdateStatus, commonFwUpdateStatus }
            STATUS current
            DESCRIPTION 
                "Notifications for software update."
            ::= { rsXx9CommonGroups 102 }

        
        commonNotifyCustomNotification NOTIFICATION-GROUP
            NOTIFICATIONS { commonRising, commonFalling, commonChanging }
            STATUS current
            DESCRIPTION 
                "Customer defined notifications."
            ::= { rsXx9CommonGroups 103 }

        
        commonNotifyOptionManagement NOTIFICATION-GROUP
            NOTIFICATIONS { commonOptionKeyStatus }
            STATUS current
            DESCRIPTION 
                "Notifications for option management."
            ::= { rsXx9CommonGroups 104 }

        
        commonNotifyDeviceInformation NOTIFICATION-GROUP
            NOTIFICATIONS { commonDevInfoAcFail, commonDevInfoFanState, commonDevInfoOvpState }
            STATUS current
            DESCRIPTION 
                "Description."
            ::= { rsXx9CommonGroups 105 }

        
        commonNotifyEnvironment NOTIFICATION-GROUP
            NOTIFICATIONS { commonEnvSummary, commonEnvTemperature, commonEnvDewPoint }
            STATUS current
            DESCRIPTION 
                "Description."
            ::= { rsXx9CommonGroups 106 }

        
        commonNotifyNtpObsoleted NOTIFICATION-GROUP
            NOTIFICATIONS { commonNtpSync }
            STATUS obsolete
            DESCRIPTION 
                "Obsoleted notifications for time synchronization via NTP."
            ::= { rsXx9CommonGroups 150 }

        
        commonNotifyGps NOTIFICATION-GROUP
            NOTIFICATIONS { commonGpsState }
            STATUS current
            DESCRIPTION 
                "Notifications for GNSS."
            ::= { rsXx9CommonGroups 151 }

        
    
    END

--
-- RS-XX9-COMMON-MIB.mi2
--
