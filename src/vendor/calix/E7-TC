-- *****************************************************************
-- E7-TC.my: Calix Networks E7 Textual Conventions
--
-- Calix confidential and proprietary.
--
-- Copyright (c) 2007-2009 Calix Networks, Inc.
-- All rights reserved.
-- *****************************************************************

E7-TC DEFINITIONS ::= BEGIN

    IMPORTS
	TEXTUAL-CONVENTION
	    FROM SNMPv2-TC
	;

E7AlarmType ::= TEXTUAL-CONVENTION
    STATUS current
    DESCRIPTION "E7 supported alarms"
    SYNTAX INTEGER {
        none(0),
		logInit(1),
        moreToShow(2),
        unequipped(3),
        notOperational(4),
        mismatchEquipmentAttributes(5),
        backupFilesExist(6),
        restoreFileExists(7),
        multipleDatabases(8),
        improperRemoval(9),
        badInventory(10),
        unsupportedEquipment(11),
        lowSoftwareResources(12),
        ntpFreeRunning(13),
        ntpServer1Down(14),
        ntpServer2Down(15),
        ntpServer3Down(16),
        databaseFailure(17),
        cardTooCold(18),
        equipOverheat(19),
        lossOfSignal(20),
        aggLinkDown(21),
        erpsIsolatedNode(22),
        erpsRingPortDown(23),
        erpsRingDown(24),
        erpsSecondRingMaster(25),
        erpsActingRingMaster(26),
        fanFailure(27),
        rstpNoPrimary(28),
        rstpNoSecondary(29),
        rstpMultiplePrimaries(30),
        rstpMultipleSecondaries(31),
        airCompressorFail(32),
        airConditioningFail(33),
        airDryerFail(34),
        batteryDischarging(35),
        batteryFail(36),
        centralizedPwrFail(37),
        commericalPwrFail(38),
        coolingFanFail(39),
        engineFail(40),
        engineOperating(41),
        explosiveGas(42),
        fireDetectorFail(43),
        fire(44),
        flood(45),
        fuseFail(46),
        generatorFail(47),
        highAirflow(48),
        highHumidity(49),
        highTemp(50),
        highWater(51),
        intrusion(52),
        lowBatterVoltage(53),
        lowCablePressure(54),
        lowFuel(55),
        lowHumidity(56),
        lowTemp(57),
        lowWater(58),
        miscellaneous(59),
        openDoor(60),
        pumpFail(61),
        rectifierFail(62),
        rectifierHighVoltage(63),
        rectifierLowVoltate(64),
        smoke(65),
        toxicGas(66),
        ventilationFail(67),
        releaseNotCommitted(68),
        upgradeInProgress(69),
        newReleaseIsReady(70),
        moduleFault(71),
        contactOffNormal(72),
        powerAFail(73),
        powerBFail(74),
        bootDataCorrupt(75),
        power(76),
        thermal(77),
        security(78),
        lacpFault(79),
        rstpFault(80),
        unrecognizedSfp(81),
        shelfError(82),
        differentVersion(83),
        ponLaserEol(84),
        lossOfPon(85),
        ontMissing(86),
        ontMismatch(87),
        ontProvError(88),
        ontEquipFailed(89),
        ontOnBattery(90),
        ontBatteryMissing(91),
        ontBatteryFailed(92),
        ontBatteryLow(93),
        ontRfSignalLow(94),
        ontRfReturnLaserEol(95),
        ontEthDown(96),
        ontDs1LosLof(97),
        ontDs1Rai(98),
        ontDs1Ais(99),
        noStandbyController(100),
        noBpDataPath(101),
        svcWithNoFac(102),
        timingFreerun(103),
        timingHoldover(104),
        timingLockedA(105),
        timingLockedB(106),
        timingFailSrcA(107),
        timingFailSrcB(108),
        timingFailDevice(109),
        equipmentFailure(110),
        ontSoftwareMismatch(111),
        unused112(112),
        switchingPowerSupplyAFailed(113),
        switchingPowerSupplyBFailed(114),
        ontDs1LosMatrix(115),
        ontDs1LofMatrix(116),
        ponBwOverSubscribed(117),
        reserved118(118),
        reserved119(119),
        reserved120(120),
        duplicateOntRegId(121),
        gponReplicationResourceExhausted(122),
        cpldOutOfRev(123),
        bpduGuard(124),
        moduleNotForStacking(125),
        ethOamMepNearEndMaxLoss(126),
        ethOamMepNearEndAvgLoss(127),
        ethOamMepNearFarMaxLoss(128),
        ethOamMepNearFarAvgLoss(129),
        ethOamMepMaxDelayMeasurement(130),
        ethOamMepAvgDelayMeasurement(131),
        ethOamMepMaxDelayVariation(132),
        ethOamMepCcmLossOfContinuity(133),
        ethOamMepCcmRxInterfaceNotUp(134),
        ethOamMepCcmRxUnexpectedMeg(135),
        ethOamMepCcmRxUnexpectedMep(136),
        ethOamMepCcmRxUnexpectedPeriod(137),
        stackingRingPortDown(138),
        stackingRingSecondMaster(139),
        stackingRingActingMaster(140),
        ontPwe3FarEndLossOfPackets(141),
        ontPwe3FarEndLossOfSignal(142),
        ontPwe3MalformedPackets(143),
        ethOamMepCcmRxWithRdi(144),
        ethOamMepAvgDelayThresholdExceeded(145),
        rfc2544Loopback(146),
        e5TooOld(147),
        bpduUnknown(148),
        equipIdFail(149),
        noTimingCard(150),
        efmDown(151),
        rfiSignalLoss(152),
        rfiDyingGasp(153),
        rfiCriticalAlarm(154),
        noPower(155),
        ftaOutOfDate(156),
        cardNotFullyInserted(157),
        voipLowSoftwareResources(158),
        switchControlFault(159),
        voipDown(160),
        initialFlashWriteInProgress(161),
        voipRegFail(162),
        stackingRingHealthCompromised(163),
        erpsDomainHealthCompromised(164),
        controlVlanAuditFailure(165),
        ontRfSignalBad(166),
        interfaceQualityAuditFailure(167),
        xdslPortProvFailure(168),
        xdslGroupProvFailure(169),
        xdslGroupLowRateDownstream(170),
        xdslGroupLowRateUpstream(171),
        xdslGroupLossOfSignal(172),
        cardTypeDiffers(173),
        cardHwFailure(174),
        softwareInitializationInProgress(175),
        stackingRingVlanProvError(176),
        fastIgmpRingVlanProvError(177),
        dosAttack(178),
        ontUpgradeInProgress(179),
        differentOntPackage(180),
        deltInProgress(181),
        seltInProgress(182),
        ontConfigInProgress(183),
        differentOntConfig(184),
        ontUsSdber(185),
        ontDsSdber(186),
        ontRgConfigUnavailable(187),
        h248MgToMgcAssocDown(188),
        ontFileUpdateInProgress(189),
        ont3pFileUpgradeInProgress(190),
        differentOnt3pFile(191),
        voiceHwInitFailure(192),
        switchCriticalEvent(193),
        voipDhcpFail(194),
        potsCalibrationFailure(196),
        dcVbattFailure(197),
        improperConnectionOnStackingPort(195),
        ontDyingGasp(200),
        lowRxOptPowerNe(201),
        highRxOptPowerNe(202),
        lowTxOptPower(205),
        highTxOptPower(206),
        xdslVectoringProvFailure(213),
        ontSelfTestFailed(214),
        ontSipConfigUnavailable(216),
		msgQueueOverflow(228),
		voipMsgQueueOverflow(229),
		ontYellowTemp(230),
		ontRedTemp(231)
    }

E7EventType ::= TEXTUAL-CONVENTION
    STATUS current
    DESCRIPTION "E7 supported general events"
    SYNTAX INTEGER {
        none(0),
        logInit(1),
        upgradeHadErrors(2),
        upgradeFailedToXferFiles(3),
        upgradeFailedToRun(4),
        resetInProgress(5),
        resetSuccess(6),
        resetHadErrors(7),
        resetFailedToRun(8),
        commitInProgress(9),
        commitSuccess(10),
        commitHadErrors(11),
        commitFailedToCommit(12),
        revertInProgress(13),
        revertSuccess(14),
        revertHadErrors(15),
        revertFailedToRun(16),
        revertFailedToCommit(17),
        autoUpgrInProgress(18),
        autoUpgrSuccess(19),
        autoUpgrFailedToXferFiles(20),
        autoUpgrFailedToRun(21),
        autoUpgrFailedToCommit(22),
        deleteUpgrInProgress(23),
        deleteUpgrSuccess(24),
        deleteUpgrHadErrors(25),
        deleteUpgrFailed(26),
        databaseRestoreInProgress(27),
        databaseRestoreComplete(28),
        databaseRestoreCompleteWithFailures(29),
        vlanMacThresholdExceeded(30),
        stpMemoryAllocationFailure(31),
        stpBufferAllocationFailure(32),
        stpNewRoot(33),
        stpTopologyChange(34),
        stpProtocolMigration(35),
        stpInvalidBpdu(36),
        stpNewPortRole(37),
        erpsProtocolViolation(38),
        erpsInvalidProvisioning(39),
        timeSet(40),
        databaseReset(41),
        cancelUpgrInProgress(42),
        cancelUpgrSuccess(43),
        cancelUpgrHadErrors(44),
        cancelUpgrFailed(45),
        switchoverInProgress(46),
        switchoverSuccess(47),
        switchoverAborted(48),
        unused49(49),
        ontArrival(50),
        ontDeparture(51),
        ontDebugUpgrInProgress(52),
        ontDebugUpgrSuccess(53),
        ontDebugUpgrHadErrors(54),
        ontDebugUpgrFailed(55),
        ontPreArrival(56),
        autoUpgrTooManyFailures(57),
        cardArrival(58),
        cardDeparture(59),
        unused60(60),
        ontLink(61),
        ontUnlink(62),
        rebootInProgress(63),
        rebootSuccess(64),
        rebootHadErrors(65),
        rebootFailed(66),
        cancelResetInProgress(67),
        cancelResetSuccess(68),
        stackingRingProtocolViolation(69),
        stackingRingInvalidProvisioning(70),
        unused71(71),
        systemTimeSet(72),
        cardMigrationUpgrade(73),
        igmpGroupLimitReached(74),
        aeOntDiscovered(75),
        remoteLinkOamLoopbackStart(76),
        remoteLinkOamLoopbackEnd(77),
        localLinkOamLoopbackStart(78),
        localLinkOamLoopbackEnd(79),
        ontFileXferInProgress(80),
        ontFileXferSuccess(81),
        ontFileXferHadErrors(82),
        ontFileXferFailed(83),
        ontDownloadInProgress(84),
        ontDownloadSuccess(85),
        ontDownloadHadErrors(86),
        ontDownloadFailed(87),
        ontActivateInProgress(88),
        ontActivateSuccess(89),
        ontActivateHadErrors(90),
        ontActivateFailed(91),
        configFileXferInProgress(92),
        configFileXferSuccess(93),
        configFileXferHadErrors(94),
        configFileXferFailed(95),
        configFileApplyInProgress(96),
        configFileApplySuccess(97),
        configFileApplyHadErrors(98),
        configFileApplyFailed(99),
        ontFileCancelInProgress(100),
        ontFileCancelSuccess(101),
        ontFileCancelHadErrors(102),
        ontFileCancelFailed(103),
        ontFileRemoveInProgress(104),
        ontFileRemoveSuccess(105),
        ontFileRemoveHadErrors(106),
        ontFileRemoveFailed(107),
        ontUserReset(108),
        lldpDelete(109),
        lldpUpdate(110)
        ontAutoQuarantine(111)
    }

E7SecurityType ::= TEXTUAL-CONVENTION
    STATUS current
    DESCRIPTION "E7 supported security events"
    SYNTAX INTEGER {
        none(0),
        unused1(1),
        userLogin(2),
        userLogout(3),
        inactiveLogout(4),
        adminForcedLogout(5),
        loginFailed(6),
        alarmLogCleared(7),
        dbChangeLogCleared(8),
        eventLogCleared(9),
        securityLogCleared(10),
        tcaLogCleared(11),
        unused12(12),
        radiusLoginFailBadSecret(13),
        databaseReset(14)
    }

E7TcaType ::= TEXTUAL-CONVENTION
    STATUS current
    DESCRIPTION "E7 supported tcas"
    SYNTAX INTEGER {
        cvC(2),
        cvCFe(3),
        fecC(4),
        fecCFe(5),
        fecL(6),
        fecLFe(7),
        esL(8),
        esLFe(9),
        sesL(10),
        sesLFe(11),
        lossL(12),
        lossLFe(13),
        uasL(14),
        uasLFe(15),
        initL(16),
        lInitL(17),
        crcP(18),
        cvP(19),
        inErrors(43),
        inDiscards(44),
        fcsErr(61),
        exColl(62),
        lateColl(63),
        longFrame(64),
        rxBufOvfl(65),
        txBufOvfl(66),
        snglColl(67),
        multColl(68),
        sqe(69),
        deferredTx(70),
        macTxErr(71),
        carSenseErr(72),
        alignErr(73),
        macRxErr(74),
        errSec(75),
        sevErrSec(76),
        burstySec(77),
        unavailSec(78),
        rxCtrlSlipSec(79),
        missingPkts(88),
        misorderUsable(89),
        misorderDropped(90),
        bufferUnderOverrun(91),
        malformedPkts(92),
        strayPkts(93),
        mmtPktLoss(94),
        tdmLbitPktsSent(95)
    }

E7ObjectClass ::= TEXTUAL-CONVENTION
    STATUS current
    DESCRIPTION
        "Object class reported in the traps and AlarmTable"
    SYNTAX INTEGER {
        invalid(0),
        system(1),
        card(2),
        dhcpGlobal(3),
        ethPortAny(4),
        opt82Prof(5),
        vlan(6),
        sshKeyOld(7),
        chassis(8),
        shelf(9),
        db(10),
        snmpTrapDest(11),
        envPin(12),
        snmpCommunity(13),
        rstpConfig(14),
        craftUser(15),
        igmpGroup(16),
        craftSerial(17),
        craftFe(18),
        ponPort(19),
        ontEthMcastProf(20),
        ontEthStaticIp(21),
        fanTray(22),
        igmpMember(23),
        portMonitor(24),
        monitorSource(25),
        dscpMap(26),
        mgmtConfig(27),
        igmpConfig(28),
        ntp(29),
        macTableEntry(30),
        ontEthSvc(31),
        ontEthTagAction(32),
        ontEthBwProf(33),
        ontEthSecuProf(34),
        cos(35),
        ethStudy(36),
        erps(37),
        snmpUser(38),
        notfLogIndex(39),
        snmpConfig(40),
        potPortCos(41),
        l2CtrlProfile(42),
        l2Acl(43),
        l2AclRule(44),
        ethGePort(45),
        eth10GePort(46),
        vlanMember(47),
        tagAction(48),
        ponCosConfig(49),
        policyMap(50),
        policy(51),
        classMap(52),
        classRule(53),
        acl(54),
        aclRule(55),
        l3Acl(56),
        l3AclRule(57),
        ethPortGos(58),
        ontFEth(59),
        ethIntf(60),
        lagIntf(61),
        intfAny(62),
        ont(63),
        ontSlot(64),
        ontGigEth(65),
        ontHpnaEth(66),
        ontEthAny(67),
        ontRfVideo(68),
        ontHotRfVideo(69),
        ontVideoAny(70),
        ontPots(71),
        ontDs1(72),
        ontPortAny(73),
        ontProfile(74),   
        macTableCount(75),
        ontSipSvc(76),
        sipProfile(77),
        mcastAddrRange(78),
        mvrProfile(79),
        ontIpHost(80),
        discOnt(81),
        quarnatineOnt(82),
        ontEthSvcName(83),
        ontEthGos(84),
        ontDs1Gos(85),
        ontCsipSvc(86),
        csipProfile(87),
        ontPwe3Svc(88),
        ontPwe3Profile(89),
        ds1Pwe3Profile(90),
        bpVlanMap(91),
        ontMatchList(92),
        ontMatchRuleTagged(93),
        ontMatchRuleUntagged(94),
        timing(95),
        timingSrc(96),
        ontPwe3Gos(97),
        igmpIntfAny(98),
        sshKey(99),
        ontMgmt(100),
        ontRfAvo(101),
        radiusCfg(102),
        radiusAuthServer(103),
        radiusAcctServer(104),
        mcastFilter(105),
        syslog(106),
        mvrVlan(107),
        unused108(108),
        unused109(109),
        ethOamCfg(110),
        ethOamPmProfile(111),
        ethOamMeg(112),
        ethOamMep(113),
        ethOamMip(114),
        ethOamRemoteMep(115),
        igmpRouterPort(116),
        vlanIgmpProfile(117),
        h248MediaGwProfile(118),
        ontH248Svc(119),
        unused120(120),
        unused121(121),
        unused122(122),
        unused123(123),
        unused124(124),
        unused125(125),
        unused126(126),
        unused127(127),
        unused128(128),
        backplane10GePort(129),
        unused130(130),
        unused131(131),
        unused132(132),
        l2cpRange(133),
        l2cpFilter(134),
        powerInput(135),
        lcPots(136),
        lcIpHost(137),
        vdslPort(138),
        vdslBondedIntf(139),
        lcH248Svc(140),
        lcSipSvc(141),
        lcTdmGwSvc(142),
        unused143(143),
        vdslPortTemplate(144),
        vdslPortTemplateData(145),
        vdslPortTemplateMask(146),
        vdslPortGos(147),
        ethIntfEthSvc(148),
        ethIntfEthSvcStaticIp(149),
        bondedIntfEthSvc(150),
        bondedIntfEthSvcStaticIp(151),
        pppoeProf(152),
        dialPlan(153),
        dialPlanRule(154),
        unused155(155),
        unused156(156),
        unused157(157),
        sipGwProf(158),
        ontMgcpSvc(159),
        mgcpMediaGwProf(160),
        ipPrecMap(161),
        avoCfg(162),
        unused163(163),
        unused164(164),
        ontRg(165),
        ontFb(166),
        ontPonUsCos(167),
        macFilter(168),
        macFilterRule(169),
        unused170(170),
        unused171(171),
        ponUsCosProf(172),
        lcH248Gw(173),
        lcMgcpGw(174),
        ontRgMgmtProf(175),
        unused176(176),
        unused177(177),
        unused178(178),
        unused179(179),
        unused180(180),
        unused181(181),
        unused182(182),
        unused183(183),
        unused184(184),
        vdslVectorGrp(185),
        unused186(186)
    }

-- the following items are for the future E7-Calix MIB
E7AdminStatus ::= TEXTUAL-CONVENTION
    STATUS current
    DESCRIPTION "administrative status values"
    SYNTAX INTEGER {
        unknown(0),
        enabled(1),
		alarmsuppress(2),
        disabled(3)
    }

E7CardType ::= TEXTUAL-CONVENTION
    STATUS current
    DESCRIPTION "E7 card types"
    SYNTAX INTEGER {
        none(0),
        unknown(1),
		agg(1012),              -- E5400 card
		backplaneE5400(1013),
		backplaneE7x2SlotChassis1RU(1014),
		fantrayE5400(1015),
        fantrayE7x2SlotChassis1RU(1016),
        gpon4(1017),
        activeEthernet(1018),   -- E5312 card
        backplaneE5312(1019),
        tenge4(1020),           -- 10ge-4, leading digits not always accepted
        backplaneE7x2S0lotChassis(1021),
        fantrayE7x20SlotChassis(1022),
        ge12(1023),
        scp(1026),
        ge24(1027),
        gpon4x(1029),
        ge24x(1030),
        vdsl48c(1031),
        vdsl48(1032),
        gpon4r2(1036),
        gpon8(1037),
        gpon8x(1038),
        e348c(1040),
        backplaneE348C(1041),
        fantrayE7x2SlotChassis1RU2(1045),
        vdsl48c(1046),
        fantrayE5Fta2(2000),
        e548c(2001),
        e548(2003),
        backplaneE5(2005)
    }

E7PowerLevel ::= TEXTUAL-CONVENTION
    STATUS current
    DESCRIPTION "Power level for card"
    SYNTAX INTEGER {
        notSet(0),
        powerLevelLow(1),
        powerLevel2(2),
        powerLevel3(3),
        powerLevel4(4),
        powerLevelFull(5)
    }

E7SnmpVers ::= TEXTUAL-CONVENTION
    STATUS current
    DESCRIPTION "E7 snmp versions (for trap destinations)"
    SYNTAX INTEGER {
        unknown(0),
        v2c(2),
        v3(3)
    }

E7OperStatus ::= TEXTUAL-CONVENTION
    STATUS current
    DESCRIPTION "operational status values"
    SYNTAX INTEGER {
        unknown(0),
        up(1),
        down(2),
        testing(3)
    }

E7XdslGrpOperStatus ::= TEXTUAL-CONVENTION
    STATUS current
    DESCRIPTION "xDSL bonded group operational status values"
    SYNTAX INTEGER {
        unknown(0),
        up(1),
        down(2),
        bonding(3)
    }

END
