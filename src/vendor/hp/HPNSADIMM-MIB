-- ****************************************************************************
-- HP NSA DIMM Memory Subsystem Information MIB
-- February 26, 1996 
--
-- Copyright Hewlett-Packard Company 1994-1996
-- All rights reserved.
--
-- The information in this document is subject to change without notice.
--
-- The HP enterprise number is 11. The ASN.1 prefix to, and including,
-- the HP enterprise ID is 1.3.6.1.4.1.11.
--
-- ****************************************************************************
-- Summary of objects in the HP NSA DIMM Memory Subsystem Information MIB
-- ****************************************************************************
-- hp                                           (1.3.6.1.4.1.11)
--    nm                                        (hp.2)
--       hpnsa                                  (nm.23)
--          hpnsaDIMM Group                     <hpnsa.21>
--             hpnsaDIMMMibRev Group            <hpnsa.21.1>
--                hpnsaDIMMMibRevMajor          <hpnsa.21.1.1>
--                hpnsaDIMMMibRevMinor          <hpnsa.21.1.2>
--
--             hpnsaDIMMAgent Group             <hpnsa.21.2>
--                hpnsaDIMMAgentTable           <hpnsa.21.2.1>
--                   hpnsaDIMMAgentEntry        <hpnsa.21.2.1.1>
--                      hpnsaDIMMAgentIndex     <hpnsa.21.2.1.1.1>
--                      hpnsaDIMMAgentName      <hpnsa.21.2.1.1.2>
--                      hpnsaDIMMAgentVersion   <hpnsa.21.2.1.1.3>
--                      hpnsaDIMMAgentDate      <hpnsa.21.2.1.1.4>
--
--             hpnsaDIMMInfo Group                       <hpnsa.21.3>
--                hpnsaDIMMTable                         <hpnsa.21.3.1>
--                   hpnsaDIMMEntry                      <hpnsa.21.3.1.1>
--                      hpnsaDIMMSlotIndex               <hpnsa.21.3.1.1.1>
--                      hpnsaDIMMSize                    <hpnsa.21.3.1.1.2>
--                      hpnsaDIMMType                    <hpnsa.21.3.1.1.3>
--                      hpnsaDIMMSpeed                   <hpnsa.21.3.1.1.4>
--                      hpnsaDIMMManufacturer            <hpnsa.21.3.1.1.5>
--                      hpnsaDIMMManufacturerPartNumber  <hpnsa.21.3.1.1.6>
--                      hpnsaDIMMManufacturerDateCode    <hpnsa.21.3.1.1.7>
--                      hpnsaDIMMDramType                <hpnsa.21.3.1.1.8>
--                
--                   hpnsaDIMMHPLocalEntry               <hpnsa.21.3.1.2>
--                      hpnsaDIMMHPSlotIndex             <hpnsa.21.3.1.2.1>
--                      hpnsaDIMMHPProductNumber         <hpnsa.21.3.1.2.2>
--                      hpnsaDIMMHPSerialNumber          <hpnsa.21.3.1.2.3>

HPNSADIMM-MIB DEFINITIONS ::= BEGIN
   IMPORTS
      enterprises    FROM RFC1155-SMI
      DisplayString  FROM RFC1213-MIB
      OBJECT-TYPE    FROM RFC-1212;

   hp                  OBJECT IDENTIFIER ::= { enterprises 11 }
   nm                  OBJECT IDENTIFIER ::= { hp 2 }
   hpnsa               OBJECT IDENTIFIER ::= { nm 23 }
   hpnsaDIMM           OBJECT IDENTIFIER ::= { hpnsa 21 }
   hpnsaDIMMMibRev     OBJECT IDENTIFIER ::= { hpnsaDIMM 1 }
   hpnsaDIMMAgent      OBJECT IDENTIFIER ::= { hpnsaDIMM 2 }
   hpnsaDIMMInfo       OBJECT IDENTIFIER ::= { hpnsaDIMM 3 }


-- *************************************************************************
-- HP NSA DIMM Memory Sub-system MIB 
-- ===================================
--
-- hp                                           (1.3.6.1.4.1.11)
--    nm                                        (hp.2)
--       hpnsa                                  (nm.23)
--          hpnsaDIMM Group                     (hpnsa.21)
--             hpnsaDIMMMibRev Group            (hpnsa.21.1)
--                hpnsaDIMMMibRevMajor          (hpnsa.21.1.1)
--                hpnsaDIMMMibRevMinor          (hpnsa.21.1.2)
--
-- Implementation of the MibRev group is mandatory for all HPNSA Agents
-- supporting the HP DIMM Memory Sub-system MIB.
--
-- An HPNSA Agent conforming to this document will return a
-- hpnsaDIMMMibRevMajor of 1 and a hpnsaDIMMMibRevMinor of 0.
--
-- *************************************************************************

   hpnsaDIMMMibRevMajor OBJECT-TYPE
      SYNTAX INTEGER (1..65535)
      ACCESS read-only
      STATUS mandatory
      DESCRIPTION
	 "The major revision level of the MIB."
   ::= { hpnsaDIMMMibRev 1 }

   hpnsaDIMMMibRevMinor OBJECT-TYPE
      SYNTAX INTEGER (0..65535)
      ACCESS read-only
      STATUS mandatory
      DESCRIPTION
	 "The minor revision level of the MIB."
   ::= { hpnsaDIMMMibRev 2 }

-- *************************************************************************
-- HP NSA DIMM MIB Agent Information
-- =====================================
--
-- hp                                           (1.3.6.1.4.1.11)
--    nm                                        (hp.2)
--       hpnsa                                  (nm.23)
--          hpnsaDIMM Group                     (hpnsa.21)
--             hpnsaDIMMAgent Group             (hpnsa.21.2)
--                hpnsaDIMMAgentTable           (hpnsa.21.2.1)
--                   hpnsaDIMMAgentEntry        (hpnsa.21.2.1.1)
--                      hpnsaDIMMAgentIndex     (hpnsa.21.2.1.1.1)
--                      hpnsaDIMMAgentName      (hpnsa.21.2.1.1.2)
--                      hpnsaDIMMAgentVersion   (hpnsa.21.2.1.1.3)
--                      hpnsaDIMMAgentDate      (hpnsa.21.2.1.1.4)
--
-- Implementation of the Trap Config Info Agent group is mandatory for all 
-- HPNSA Agents supporting the HP DIMM Memory Sub-system MIB.
--
-- *************************************************************************

   hpnsaDIMMAgentTable OBJECT-TYPE
      SYNTAX SEQUENCE OF HPnsaDIMMAgentEntry
      ACCESS not-accessible
      STATUS mandatory
      DESCRIPTION
	 "A table of SNMP agents that satisfy requests for this MIB."
   ::= { hpnsaDIMMAgent 1 }

   hpnsaDIMMAgentEntry OBJECT-TYPE
      SYNTAX HPnsaDIMMAgentEntry
      ACCESS not-accessible
      STATUS mandatory
      DESCRIPTION
	 "A description of the agent/agents that access DIMM Memory."
      INDEX { hpnsaDIMMAgentIndex }
   ::= { hpnsaDIMMAgentTable 1 }

   HPnsaDIMMAgentEntry ::= SEQUENCE {
      hpnsaDIMMAgentIndex       INTEGER,
      hpnsaDIMMAgentName        DisplayString,
      hpnsaDIMMAgentVersion     DisplayString,
      hpnsaDIMMAgentDate        OCTET STRING
   }

   hpnsaDIMMAgentIndex OBJECT-TYPE
      SYNTAX INTEGER (0..255)
      ACCESS read-only
      STATUS mandatory
      DESCRIPTION
	 "A unique index for this agent."
   ::= { hpnsaDIMMAgentEntry 1 }

   hpnsaDIMMAgentName OBJECT-TYPE
      SYNTAX DisplayString (SIZE (0..255))
      ACCESS read-only
      STATUS mandatory
      DESCRIPTION
	 "Name of the agent/agents satisfying SNMP requests for this MIB."
   ::= { hpnsaDIMMAgentEntry 2 }

   hpnsaDIMMAgentVersion OBJECT-TYPE
      SYNTAX DisplayString (SIZE (0..10))
      ACCESS read-only
      STATUS mandatory
      DESCRIPTION
	 "Version number of the agent/agents satisfying SNMP requests for
	 this MIB."
   ::= { hpnsaDIMMAgentEntry 3 }

   hpnsaDIMMAgentDate OBJECT-TYPE
      SYNTAX OCTET STRING (SIZE (7))
      ACCESS read-only
      STATUS mandatory
      DESCRIPTION
	 "The date on which this agent was created.

	 field  octets  contents                  range
	 _________________________________________________
	    1       1    years since 1900          0..255
	    2       2    month                     1..12
	    3       3    day                       1..31
	    4       4    hour                      0..23
	    5       5    minute                    0..59
	    6       6    second                    0..59"
   ::= { hpnsaDIMMAgentEntry 4 }

-- *************************************************************************
-- HP NSA DIMM Table Standard Information
-- ======================================
--
-- hp                                           (1.3.6.1.4.1.11)
--    nm                                        (hp.2)
--       hpnsa                                  (nm.23)
--          hpnsaDIMM Group                     (hpnsa.21)
--             hpnsaDIMMInfo Group              (hpnsa.21.3)
--                hpnsaDIMMTable                         <hpnsa.21.3.1>
--                   hpnsaDIMMEntry                      <hpnsa.21.3.1.1>
--                      hpnsaDIMMSlotIndex               <hpnsa.21.3.1.1.1>
--                      hpnsaDIMMSize                    <hpnsa.21.3.1.1.2>
--                      hpnsaDIMMType                    <hpnsa.21.3.1.1.3>
--                      hpnsaDIMMSpeed                   <hpnsa.21.3.1.1.4>
--                      hpnsaDIMMManufacturer            <hpnsa.21.3.1.1.5>
--                      hpnsaDIMMManufacturerPartNumber  <hpnsa.21.3.1.1.6>
--                      hpnsaDIMMManufacturerDateCode    <hpnsa.21.3.1.1.7>
--                      hpnsaDIMMDramType                <hpnsa.21.3.1.1.8>
-- *************************************************************************

   hpnsaDIMMTable OBJECT-TYPE
      SYNTAX SEQUENCE OF HPnsaDIMMEntry
      ACCESS not-accessible
      STATUS mandatory
      DESCRIPTION
	 "DIMM industry standard data area"
   ::= { hpnsaDIMMInfo 1 }

   hpnsaDIMMEntry OBJECT-TYPE
      SYNTAX HPnsaDIMMEntry
      ACCESS not-accessible
      STATUS mandatory
      DESCRIPTION
	 "A description of DIMM industry standard data area."
      INDEX { hpnsaDIMMSlotIndex }
   ::= { hpnsaDIMMTable 1 }

   HPnsaDIMMEntry ::= SEQUENCE {
      hpnsaDIMMSlotIndex                 INTEGER,
      hpnsaDIMMSize                      INTEGER,
      hpnsaDIMMType                      INTEGER,
      hpnsaDIMMSpeed                     INTEGER,
      hpnsaDIMMManufacturer              DisplayString,
      hpnsaDIMMManufacturerPartNumber    DisplayString,
      hpnsaDIMMManufacturerDateCode      OCTET STRING,
      hpnsaDIMMDramType                  INTEGER
   }

   hpnsaDIMMSlotIndex OBJECT-TYPE
      SYNTAX INTEGER (0..255)
      ACCESS read-only
      STATUS mandatory
      DESCRIPTION
	 "A unique index for this DIMM table entry."
   ::= { hpnsaDIMMEntry 1 }

   hpnsaDIMMSize OBJECT-TYPE
      SYNTAX INTEGER 
      ACCESS read-only
      STATUS mandatory
      DESCRIPTION
	 "The size of DIMM in Kbytes"
   ::= { hpnsaDIMMEntry 2 }

   hpnsaDIMMType OBJECT-TYPE
      SYNTAX INTEGER {
             dimm-NONE(0),
	 dimm-Parity(1),
	 dimm-ECC(2)
      } 
      ACCESS read-only
      STATUS mandatory
      DESCRIPTION
	 "The DIMM memory type.
	    
	    0 -- No error detection/correction
	    1 -- Parity error detection/No error correction
	    2 -- Two bit detection/One bit correction."
   ::= { hpnsaDIMMEntry 3 }

   hpnsaDIMMSpeed OBJECT-TYPE
      SYNTAX INTEGER 
      ACCESS read-only
      STATUS mandatory
      DESCRIPTION
	 "The manufacturer specified CAS access time of the DIMM."
   ::= { hpnsaDIMMEntry 4 }

   hpnsaDIMMManufacturer OBJECT-TYPE
      SYNTAX DisplayString (SIZE (0..255))
      ACCESS read-only
      STATUS mandatory
      DESCRIPTION
	 "DIMM manufacturer's name."
   ::= { hpnsaDIMMEntry 5 }

   hpnsaDIMMManufacturerPartNumber OBJECT-TYPE
      SYNTAX DisplayString (SIZE (0..255))
      ACCESS read-only
      STATUS mandatory
      DESCRIPTION
	 "DIMM manufacturer's part number."
   ::= { hpnsaDIMMEntry 6 }

   hpnsaDIMMManufactureDateCode OBJECT-TYPE
      SYNTAX OCTET STRING (SIZE (2)) 
      ACCESS read-only
      STATUS mandatory
      DESCRIPTION
	 "The year and week of the DIMM manufactured.
	 
	 field   octets  contents           range
	   1        1    year since 1900    0..255
	   2        2    week of the year   1..52"
   ::= { hpnsaDIMMEntry 7 }

   hpnsaDIMMDramType OBJECT-TYPE
      SYNTAX INTEGER {
            dimm-FastPageMode(1),
	 dimm-ExtendedDataOut(2),
	 dimm-PipelinedNibble(3),
	 dimm-Synchronous(4)
      }
      ACCESS read-only
      STATUS mandatory
      DESCRIPTION
	 "The DIMM's DRAM memory type.
	 
	    1 -- Standard Fast Page Mode DRAM
	    2 -- Extended Data Out DRAM
	    3 -- Pipelined Nibble DRAM
	    4 -- Synchronous DRAM."
   ::= { hpnsaDIMMEntry 8 }
   
-- *************************************************************************
-- HP NSA DIMM Table HP Specific Data Areat
-- ========================================
--
-- hp                                           (1.3.6.1.4.1.11)
--    nm                                        (hp.2)
--       hpnsa                                  (nm.23)
--          hpnsaDIMM Group                     (hpnsa.21)
--             hpnsaDIMMInfo Group              (hpnsa.21.3)
--                hpnsaDIMMTable                         <hpnsa.21.3.1>
--                   hpnsaDIMMHPLocalEntry               <hpnsa.21.3.1.2>
--                      hpnsaDIMMHPSlotIndex             <hpnsa.21.3.1.2.1>
--                      hpnsaDIMMHPProductNumber         <hpnsa.21.3.1.2.2>
--                      hpnsaDIMMHPSerialNumber          <hpnsa.21.3.1.2.3>
-- *************************************************************************

   hpnsaDIMMHPLocalTable OBJECT-TYPE
      SYNTAX SEQUENCE OF HPnsaDIMMHPLocalEntry
      ACCESS not-accessible
      STATUS mandatory
      DESCRIPTION
	 "HP reserved DIMM data area."
   ::= { hpnsaDIMMTable 2 }

   hpnsaDIMMHPLocalEntry OBJECT-TYPE
      SYNTAX HPnsaDIMMHPLocalEntry
      ACCESS not-accessible
      STATUS mandatory
      DESCRIPTION
	 "A description of the HP reserved DIMM data area."
      INDEX { hpnsaDIMMHPSlotIndex }
   ::= { hpnsaDIMMHPLocalTable 1 }

   HPnsaDIMMHPLocalEntry ::= SEQUENCE {
      hpnsaDIMMHPSlotIndex        INTEGER,
      hpnsaDIMMHPProductNumber    DisplayString,
      hpnsaDIMMHPSerialNumber     INTEGER
   }

   hpnsaDIMMHPSlotIndex OBJECT-TYPE
      SYNTAX INTEGER (0..255)
      ACCESS read-only
      STATUS mandatory
      DESCRIPTION
	 "A unique index for this table."
   ::= { hpnsaDIMMHPLocalEntry 1 }

   hpnsaDIMMHPProductNumber OBJECT-TYPE
      SYNTAX DisplayString (SIZE (0..12))
      ACCESS read-only
      STATUS mandatory
      DESCRIPTION
	 "HP product number for the selected DIMM as an ASCII string."
   ::= { hpnsaDIMMHPLocalEntry 2 }

   hpnsaDIMMHPSerialNumber OBJECT-TYPE
      SYNTAX INTEGER 
      ACCESS read-only
      STATUS mandatory
      DESCRIPTION
	 "The combination of HP's part number and the serial number
	 uniquely identify a DIMM."
   ::= { hpnsaDIMMHPLocalEntry 3 }
END
