-- Copyright (c) 1999-2004, Juniper Networks, Inc.
-- All rights reserved.

NETSCREEN-TRAP-MIB DEFINITIONS ::= BEGIN

IMPORTS
    netscreenTrap, netscreenTrapInfo
        FROM NETSCREEN-SMI
    MODULE-IDENTITY, NOTIFICATION-TYPE, OBJECT-TYPE
        FROM SNMPv2-SMI
    DisplayString
        FROM SNMPv2-TC
    ;

netscreenTrapMibModule MODULE-IDENTITY
    LAST-UPDATED  "200503032022Z" -- March 03, 2005
    ORGANIZATION
        "Juniper Networks, Inc."
    CONTACT-INFO
        "Customer Support

         1194 North Mathilda Avenue 
         Sunnyvale, California 94089-1206
         USA

         Tel: 1-800-638-8296
         E-mail: customerservice@juniper.net
         HTTP://www.juniper.net"
    DESCRIPTION
        "Added trap types 15, it is still in use"
    REVISION      "200803170000Z" -- Mar 17, 2008
    DESCRIPTION
        "Added 5 new trap types - 800-804. Removed 1000."
    REVISION      "200510170000Z" -- Oct 17, 2005
    DESCRIPTION
        "Added 4 new trap types - ipv6 ip conflicts(101), dip util raise(102) and clear(103), 
        idsIcmpPingIdZero(441)."
    REVISION      "200503030000Z" -- March 03, 2005
    DESCRIPTION
        "Trap MIB"
    REVISION      "200409100000Z" -- Sep 10, 2004
    DESCRIPTION
        "Removed nsTrapType 3, 15,18,19 and 1000"
    REVISION      "200405030000Z" -- May 03, 2004
    DESCRIPTION
        "Modified copyright and contact information"
    REVISION      "200403030000Z" -- March 03, 2004
    DESCRIPTION
        "Converted to SMIv2 by Longview Software"
    REVISION      "200401230000Z" -- January 23, 2004
    DESCRIPTION
        "Add new traps (430~434)"
    REVISION      "200109280000Z" -- September 28, 2001
    DESCRIPTION
        "Add global-report manager specific trap"
    REVISION      "200008020000Z" -- August 02, 2000
    DESCRIPTION
        "Creation Date"
    ::= { netscreenTrapInfo 0 }

netscreenTrapHw NOTIFICATION-TYPE
    OBJECTS
        { netscreenTrapType, netscreenTrapDesc }
    STATUS        current
    DESCRIPTION
        "This trap indicates that some kind of hardware problem has
         occured."
    ::= { netscreenTrap 100 }

netscreenTrapFw NOTIFICATION-TYPE
    OBJECTS
        { netscreenTrapType, netscreenTrapDesc }
    STATUS        current
    DESCRIPTION
        "This trap indicates that some kind of firewall functions has
         been triggered."
    ::= { netscreenTrap 200 }

netscreenTrapSw NOTIFICATION-TYPE
    OBJECTS
        { netscreenTrapType, netscreenTrapDesc }
    STATUS        current
    DESCRIPTION
        "This trap indicates that some kind of software problem has
         occured."
    ::= { netscreenTrap 300 }

netscreenTrapTrf NOTIFICATION-TYPE
    OBJECTS
        { netscreenTrapType, netscreenTrapDesc }
    STATUS        current
    DESCRIPTION
        "This trap indicates that some kind of traffic conditions has
         been triggered."
    ::= { netscreenTrap 400 }

netscreenTrapVpn NOTIFICATION-TYPE
    OBJECTS
        { netscreenTrapType, netscreenTrapDesc }
    STATUS        current
    DESCRIPTION
        "This trap indicates that VPN tunnel status has occured."
    ::= { netscreenTrap 500 }

netscreenTrapNsrp NOTIFICATION-TYPE
    OBJECTS
        { netscreenTrapType, netscreenTrapDesc }
    STATUS        current
    DESCRIPTION
        "This trap indicates that NSRP status has occured."
    ::= { netscreenTrap 600 }

netscreenTrapGPRO NOTIFICATION-TYPE
    OBJECTS
        { netscreenTrapType, netscreenTrapDesc }
    STATUS        current
    DESCRIPTION
        "This trap indicates that some kind of Global PRO problems has
         occurred."
    ::= { netscreenTrap 700 }

netscreenTrapDrp NOTIFICATION-TYPE
    OBJECTS
        { netscreenTrapType, netscreenTrapDesc }
    STATUS        current
    DESCRIPTION
        "This trap indicates that Drp status has occured."
    ::= { netscreenTrap 800 }

netscreenTrapIFFailover NOTIFICATION-TYPE
    OBJECTS
        { netscreenTrapType, netscreenTrapDesc }
    STATUS        current
    DESCRIPTION
        "This trap indicates that interface fail over status has
         occured."
    ::= { netscreenTrap 900 }

netscreenTrapIDPAttack NOTIFICATION-TYPE
    OBJECTS
        { netscreenTrapType, netscreenTrapDesc }
    STATUS        current
    DESCRIPTION
        "This trap indicates that IDP attack status has occured."
    ::= { netscreenTrap 1000 }

netscreenTrapType OBJECT-TYPE
    SYNTAX        INTEGER {

	-- Traffic per-second threshold
        trafficSec(1),
	-- Traffic per-minute threshold
        trafficMin(2),
	-- Multiple user auth fail alarm type
        multiAuthFail(3),
        -- Winnuke pak
        winnuke(4),
        -- Syn attack
        synAttack(5),
        -- tear-drop attack
        tearDrop(6),
        -- Ping of Death attack
        pingDeath(7),
        -- IP spoofing attack
        ipSpoofing(8),
        -- IP source routing attack
        ipSrcRoute(9),
        -- land attack
        land(10),
        -- ICMP flooding attack
        icmpFlood(11),
        -- UDP flooding attack
        udpFlood(12),
        -- Illegal server IP to connect to CMS port
        illegalCmsSvr(13),
        -- URL blocking server connection alarm
        urlBlockSrv(14),
        -- high availability
        highAvailability(15),
        -- Port Scan attack
        portScan(16),
        -- address sweep attack
        addrSweep(17),
        -- deny by policy attack
        denyPolicy(18),
        -- device is dead
        deviceDead(19),
        -- memory low
        lowMemory(20),
        -- DNS server unreachable
        dnsSrvDown(21),
        -- Fan, Power Supply failure
        generic-HW-fail(22),
        -- Load balance server unreachable
        lbSrvDown(23),
        -- log buffer overflow
        logFull(24),
        -- X509 related
        x509(25),
        -- VPN and IKE related
        vpnIke(26),
        -- admin realted
        admin(27),
        -- Illegal src ip to connect to sme port
        sme(28),
        -- DHCP related
        dhcp(29),
        -- CPU usage is high
        cpuUsageHigh(30),
        -- Interface IP conflict
        ipConflict(31),
        -- Microsoft IIS server vulnerability
        attactMaliciousUrl(32),
        -- session threshold is exceeded
        sessionThreshold(33),
        -- SSH related alarms
        sshAlarm(34),
        -- Audit storage related alarms
        auditStorage(35),
        -- memory normal
        memoryNormal(36),
        -- cpu usage normal
        cpuUsageNormal(37),
        reserved38(38),
        -- driver's rx bd shortage
        rxbdLowAlarm(39),
        -- VPN tunnel from down to up
        vpnTunnelUp(40),
        -- VPN tunnel from up to down
        vpnTunnelDown(41),
        -- VPN replay detected
        vpnReplayAttack(42),
        -- VPN tunnel removed
        vpnL2tpTunnelRemove(43),    
        -- VPN tunnel removed and error detected 
        vpnL2tpTunnelRemoveErr(44), 
        -- VPN call removed
        vpnL2tpCallRemove(45), 
        -- VPN call removed and error detected
        vpnL2tpCallRemoveErr(46),   
        -- Number of IAS exceeds configured maximum
        vpnIasTooMany(47),
        -- Number of IAS crossed configured upper threshold
        vpnIasOverThreshold(48),	
        -- Number of IAS crossed configured lower threshold
        vpnIasUnderThreshold(49),	
        -- IKE error occured for the IAS session
        vpnIasIkeError(50),	
        -- allocated session exceed threshold
        allocatedSessionThreshold(51),
        -- av-csp related alarm
        avCspAlarm(52),
        -- av related alarm
        avAlarm(53),
        -- apppry related alarm
        apppryAlarm(54),
        -- NSRP rto self unit status change from up to down
        nsrpRtoUp(60),
        -- NSRP rto self unit status change from down to up
        nsrpRtoDown(61),
        -- NSRP track ip successed
        nsrpTrackipSuccess(62),
        -- NSRP track ip failed
        nsrpTrackipFailed(63),
        -- NSRP track ip fail over
        nsrpTrackipFailover(64),
        -- NSRP inconsistent configuration between master and backup
        nsrpInconsistentConfiguration(65),
        -- track ip status related alarm
        trackipStatus(66),
        -- NSRP vsd group status change to elect
        nsrpVsdInit(70),
        -- NSRP vsd group status change to master
        nsrpVsdMaster(71),
        -- NSRP vsd group status change to primary backup
        nsrpVsdPbackup(72),
        -- NSRP vsd group status change to backup
        nsrpVsdBackup(73),
        -- NSRP vsd group status change to ineligible
        nsrpVsdIneligible(74),
        -- NSRP VSD group status change to inoperable
        nsrpVsdInoperable(75),
        -- NSRP VSD request heartbeat from 2nd HA path
        nsrpVsdReqHearbeat2nd(76),
        -- NSRP VSD reply to 2nd path request
        nsrpVsdReply2nd(77),
        -- NSRP duplicated RTO group found
        nsrpRtoDuplicated(78),
        -- NSRP duplicated VSD group master
        ipDupMaster(79),
        -- MEM cannot find usable memory for current pool
        diHeapCreateFail(80),
        -- MEM cannot find usable in any pool
        memAllocFail(81),
        -- VRRP status related alarm
        vrrpStatusAlarm(82),
        -- SCCP related alarm
        sccpAlarm(83),
        -- MGCP related alarm
        mgcpReinit(84),
        -- MLFR related alarm
        mlfrAlarm(85),
        -- FR related alarm
        frAlarm(86),
        -- CISCO HDLC related alarm
        ciscoHdlcAlarm(87),
        -- PPPOW related alarm
        pppowAlarm(88),
        -- H323 related alarm
        h323Alarm(89),
        -- ISDN related alarm
        isdnAlarm(90),
  		-- interface backup 
        interfaceBackup(91), 
  		-- Card function is abnormal 
        wanCardFunction(92), 
  		-- A USB key is plug/unplug from USB port 
        usbDeviceOperation(93), 
  		-- interface failure 
        interfaceFailure(94), 
        -- No ppp IP pool configured 
        pppNoIpCfg(95),   
        -- IP pool exhausted. No ip to assign
        pppNoIpInPool(96), 
        -- Any change to interface IP address can use the type 
        ipAddrEvent(101),			
        -- DIP utilization reaches raised threshold limit
        dipUtilRaise(102),		
        -- DIP utilization reaches clear threshold limit
        dipUtilClear(103),	
        -- DOT1X related alarm
        dot1xAlarm(105),
        -- VPN IAS radius error
        vpnIasRadiusError(110),
        -- VPN IKEID enum attack
        vpnIkeidEnumAttack(111),
        -- VPN soft limit reached
        vpnSoftlimitReached(112),
        -- VPN IKE dos attack
        vpnIkedosAttack(113),
        -- VPN acvpn profile error
        vpnAcvpnProfileError(114),
	-- exceed maximum routing entry allowed for the system 
        routeSysEntryEx(200),
	-- exceed maximum routing entry allowed for a vr
        routeVrEntryEx(201),
	-- exceed the hello packet threshold per hello interval 
        routeOspfHelloFlood(202),
	-- exceed the lsa packet threshold per lsa threshold 
        routeOspfLsaFlood(203),
	-- exceed the update4 packet threshold per update time in rip
        routeRipUpdateFlood(204),
	-- Errors in route module (exceed limit, malloc failure, add-perfix failure etc) 
        routeAlarm(205),
	-- LSA/Hello packets flood in OSPF, route redistribution exceed limit, 
        ospfFlood(206),
	-- Update packet floods in RIP 
        ripFlood(207),
	-- Peer forms adjacency completely
        bgpEstablished(208),
	-- Peer's adjacency is torn down, goes to Idle state
        bgpBackwardtransition(209),
	-- change in virtual link's state (down, point-to-point etc)
        ospfVirtifstatechange(210),
	-- change in neighbor's state on regular interface (down, 2way, full etc)
        ospfNbrstatechange(211),
	-- change in neighbor's state on virtual link (down, full etc)
        ospfVirtnbrstatechange(212),
	-- authentication mismatch/area mismatch etc on regular interface
        ospfIfconfigerror(213),
	-- authentication mismatch/area mismatch etc on virtual link
        ospfVirtifconfigerror(214),
	-- Authentication eror on regular interface
        ospfIfauthfailure(215),
	-- Authentication eror on virtual link
        ospfVirtifauthfailure(216),
	-- lsa received with invalid lsa-type on regular interface
        ospfIfrxbadpacket(217),
	-- lsa received with invalid lsa-type on virtual link
        ospfVirtifrxbadpacket(218),
	-- retransmission to neighbor on regular interface
        ospfTxretransmit(219),
	-- retransmission to neighbor on virtual link
        ospfVirtiftxretransmit(220),
	-- new LSA generated by local router
        ospfOriginatelsa(221),
	-- LSA aged out
        ospfMaxagelsa(222),
	-- when total LSAs in database exceed predefined limit
        ospfLsdboverflow(223),
	-- when total LSAs in database approach predefined limit
        ospfLsdbapproachingoverflow(224),
	-- change in regular interface state (up/down, dr/bdr etc)
        ospfIfstatechange(225),
	-- BGP related alarm  
        bgpAlarm(226),
	-- packet floods in RIPng 
        ripngFlood(227),
	-- exceed the update4 packet threshold per update time in ripng
        routeRipngUpdateFlood(228),
	-- PBR related alarm  
        policyRouteAlarm(233),
	-- NHRP related alarm  
        nhrpAlarm(230),
	-- OSPFV3 related alarm  
        ospfv3Alarm(231),
        -- block java/active-x component
        idsComponent(400),
        -- icmp flood attack
        idsIcmpFlood(401),
        -- udp flood attack
        idsUdpFlood(402),
        -- winnuke attack
        idsWinnuke(403),
        -- port scan attack
        idsPortScan(404),
        -- address sweep attack
        idsAddrSweep(405),
        -- tear drop attack
        idsTearDrop(406),
        -- syn flood attack
        idsSyn(407),
        -- ip spoofing attack
        idsIpSpoofing(408),
        -- ping of death attack
        idsPingDeath(409),
        -- filter ip packet with source route option
        idsIpSourceRoute(410),
        -- land attack
        idsLand(411),
        -- screen syn fragment attack
        synFragAttack(412),
        -- screen tcp packet without flag attack
        tcpWithoutFlag(413),
        -- screen unknown ip packet
        unknowIpPacket(414),
        -- screen bad ip option
        badIpOption(415),
        -- screen ip option record
        ipOptionRecord(416),
        -- screen ip option timestamp 
        ipOptionTimestamp(417),
        -- screen ip option scht
        ipOptionScht(418),
        -- screen ip option lsr
        ipOptionLsr(419),
        -- screen ip option ssr
        ipOptionSsr(420),
        -- screen ip option stream
        ipOptionStream(421),
        -- screen icmp fragment packet
        icmpFragment(422),
        -- screen too large icmp packet
        tooLargeIcmp(423),
        -- screen tcp flag syn-fin set
        tcpSynFin(424),
        -- screen tcp fin without ack
        tcpFinNoAck(425),
        -- screen mal url
        tcpMalUrl(426),
        -- screen sess mal num
        tcpSessMalNum(427),
        -- avoid replying to syns after excessive 3 way TCP handshakes from
        -- same src ip but not proceeding with user auth. (not replying to
        -- username/password)..
        idsTcpSynAckAck(428),
        -- ip fragment
        idsIpBlockFrag(429),
        -- Dst IP-based session limiting
        dstIpSessionLimit(430),
        -- HTTP component blocking for .zip files
        idsBlockZip(431),
        -- HTTP component blocking for Java applets
        idsBlockJar(432),
        -- HTTP component blocking for .exe files
        idsBlockExe(433),
        -- HTTP component blocking for ActiveX controls
        idsBlockActivex(434),
        -- screenos tcp syn mac
        tcpSynMac(435),
        -- screenos nac attack
        idsNacAttack(436),
        -- icmp ping id 0
        idsIcmpPingIdZero(441),
        -- tcp sweep
        tcpSweep(442),
        -- udp sweep
        udpSweep(443),
		-- AV Scan Manager Alarm, sofeware trap 
        avScanMgr(554), 
        -- starting value for multicast alarm
        mcastBase(600),
        -- mcore related alarm
        mcoreAlarm(601),
        -- spim related alarm
        spimAlarm(602),
        -- starting value for Security Module alarm
        smBase(700),
        -- Security Module down detected
        smDown(701),
        -- Security Module packet droped detected
        smPacketDrop(702),
        -- Security Module memory, CPU and session detected
        smOverload(703),
        -- Security Module CPU unresponsive detected
        smCpuUnresponsive(704),
        -- Security Module Engine unresponisve
        smCpuUnresponsive(705),
        -- Secruity Module Policy Abnormal
        smPolicyAbnormal(706),
        -- switch alarm
        switch(751),
        -- sfp alarm
        sfp(752), 
        --Shared to fair transition forced
        cpuLimitS2fForced(800),   
        --Shared to fair transition auto
        cpuLimitS2fAuto(801),     
        --Fair to shared transition forced
        cpuLimitF2sForced(802),   
        --Fair to shared transition because of timeout
        cpuLimitF2sTimeout(803),  
        --Fair to shared transition auto 
        cpuLimitF2sAuto(804),      
        --Flow potential violation
        secPotentialVoilation(805),  
        --Flow session cache alarm 
        flowSessCache(806),      
        --vsys session limit alarm 
        vsysSessionLimit(850)      
    }
    MAX-ACCESS    accessible-for-notify
    STATUS        current
    DESCRIPTION
        "The integer value of the raised alarm type. Note that the type
         should be interpreted within a specific trap"
    ::= { netscreenTrapInfo 1 }

netscreenTrapDesc OBJECT-TYPE
    SYNTAX        DisplayString (SIZE(0..255))
    MAX-ACCESS    accessible-for-notify
    STATUS        current
    DESCRIPTION
        "The textual description of the alarm"
    ::= { netscreenTrapInfo 3 }

END
