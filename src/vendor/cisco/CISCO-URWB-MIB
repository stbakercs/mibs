-- *------------------------------------------------------------------
-- * CISCO-URWB-MIB.my:  Cisco URWB MIB.
-- *
-- * September 2022, ask-wireless@cisco.com
-- *
-- * Copyright (c) 2022 by cisco Systems, Inc.
-- * All rights reserved.
-- *
-- *------------------------------------------------------------------

CISCO-URWB-MIB DEFINITIONS ::= BEGIN

IMPORTS
	NOTIFICATION-TYPE, MODULE-IDENTITY, Integer32,
	Counter32, IpAddress, OBJECT-TYPE
	FROM SNMPv2-SMI

	ifNumber, ifTable
	FROM IF-MIB

	DisplayString
	FROM SNMPv2-TC
	
	ciscoMgmt
	FROM CISCO-SMI;

ciscoUrwb MODULE-IDENTITY
	LAST-UPDATED "202205100000Z"
	ORGANIZATION "Cisco Systems"
	CONTACT-INFO
                 "       Cisco Systems
                         Customer Service

                 Postal: 170 W Tasman Drive
                         San Jose, CA  95134
                         USA

                    Tel: +1-800-553-2447

                 E-mail: ask-wireless@cisco.com"

	DESCRIPTION "This MIB module defines objects to manage the
        		Cisco Ultra Reliable Wireless backhaul device"
	REVISION "202205260000Z"
	DESCRIPTION "Initial version of this module"
::= { ciscoMgmt 1056 }

ciscoUrwbInfo OBJECT IDENTIFIER ::= { ciscoUrwb 11 }
ciscoUrwbTraps OBJECT IDENTIFIER ::= { ciscoUrwb 12 }
ciscoUrwbExperimental OBJECT IDENTIFIER ::= { ciscoUrwb 13 }
ciscoUrwbMobilityInfo OBJECT IDENTIFIER ::= { ciscoUrwb 14 }
ciscoUrwbFailInfo OBJECT IDENTIFIER ::= { ciscoUrwb 15 }
ciscoUrwbFailSshLoginInfo OBJECT IDENTIFIER ::= { ciscoUrwb 16 }
ciscoUrwbFailWebLoginInfo OBJECT IDENTIFIER ::= { ciscoUrwb 17 }
ciscoUrwbHeadInfo OBJECT IDENTIFIER ::= { ciscoUrwb 18 }

ciscoUrwbNotif NOTIFICATION-TYPE
	OBJECTS {
		ciscoUrwbOperMode,
		ciscoUrwbModel,
		ciscoUrwbFwVersion,
		ciscoUrwbWs1,
		ciscoUrwbWs2,
		ciscoUrwbFreq1,
		ciscoUrwbChanWidth1,
		ciscoUrwbFreq2,
		ciscoUrwbChanWidth2,
		ciscoUrwbName,
		ciscoUrwbMid,
		ciscoUrwbUptime,
		ciscoUrwbSerial,
		ciscoUrwbDate,
		ciscoUrwbStaNum,
		ciscoUrwbStaIndex,
		ciscoUrwbLocalMacAddress,
		ciscoUrwbStaMacAddress,
		ciscoUrwbStaMid,
		ciscoUrwbStaSignal,
		ciscoUrwbStaRxBytes,
		ciscoUrwbStaRxPkts,
		ciscoUrwbStaRxRate,
		ciscoUrwbStaRxMcs,
		ciscoUrwbStaRxMcsFlag,
		ciscoUrwbStaTxBytes,
		ciscoUrwbStaTxPkts,
		ciscoUrwbStaTxFail,
		ciscoUrwbStaTxRetry,
		ciscoUrwbStaTxRate,
		ciscoUrwbStaTxMcs,
		ciscoUrwbStaTxMcsFlag,
		ciscoUrwbTputNum,
		ciscoUrwbTputIndex,
		ciscoUrwbTputIface,
		ciscoUrwbTputRx,
		ciscoUrwbTputTx,
		ciscoUrwbLoad1,
		ciscoUrwbLoad5,
		ciscoUrwbLoad15
	}
	STATUS current
	DESCRIPTION "CURWB periodic notification"
::= { ciscoUrwbTraps 1 }

ciscoUrwbHandoff NOTIFICATION-TYPE
	OBJECTS {
		ciscoUrwbMobileIp,
		ciscoUrwbStaticIp,
		ciscoUrwbMobileMid,
		ciscoUrwbStaticMid,
		ciscoUrwbHandoffSeq
	}
	STATUS current
	DESCRIPTION "CURWB Handoff event"
::= { ciscoUrwbTraps 2 }

ciscoUrwbFail NOTIFICATION-TYPE
	OBJECTS {
		ciscoUrwbMeshId,
		ciscoUrwbTimestamp,
		ciscoUrwbErrorCode,
		ciscoUrwbAdditionalInfo
	}
	STATUS current
	DESCRIPTION "CURWB fail event trap"
::= { ciscoUrwbTraps 3 }

ciscoUrwbFailSshLogin NOTIFICATION-TYPE
	OBJECTS {
		ciscoUrwbFailSshLoginFlag,
		ciscoUrwbFailSshLoginUser
	}
	STATUS current
	DESCRIPTION "CURWB SSH failed login event trap"
::= { ciscoUrwbTraps 4 }

ciscoUrwbWebSshLogin NOTIFICATION-TYPE
	OBJECTS {
		ciscoUrwbFailWebLoginUser
	}
	STATUS current
	DESCRIPTION "CURWB WEB failed login event trap"
::= { ciscoUrwbTraps 5 }

ciscoUrwbHeadDetect NOTIFICATION-TYPE
	OBJECTS {
		ciscoUrwbHeadMid,
		ciscoUrwbTailMid
	}
	STATUS current
	DESCRIPTION "CURWB Train head/tail car detection event"
::= { ciscoUrwbTraps 6 }

ciscoUrwbOperMode OBJECT-TYPE
	SYNTAX DisplayString (SIZE (0..255))
	MAX-ACCESS read-only
	STATUS current
	DESCRIPTION "The device operating mode"
::= { ciscoUrwbInfo 1 }

ciscoUrwbModel OBJECT-TYPE
	SYNTAX DisplayString (SIZE (0..255))
	MAX-ACCESS read-only
	STATUS current
	DESCRIPTION "The device model"
::= { ciscoUrwbInfo 2 }

ciscoUrwbFwVersion OBJECT-TYPE
	SYNTAX DisplayString (SIZE (0..255))
	MAX-ACCESS read-only
	STATUS current
	DESCRIPTION "The device firmware version"
::= { ciscoUrwbInfo 3 }

ciscoUrwbWs1 OBJECT-TYPE
	SYNTAX DisplayString (SIZE (0..255))
	MAX-ACCESS read-only
	STATUS current
	DESCRIPTION "The radio 1 working state"
::= { ciscoUrwbInfo 4 }

ciscoUrwbWs2 OBJECT-TYPE
	SYNTAX DisplayString (SIZE (0..255))
	MAX-ACCESS read-only
	STATUS current
	DESCRIPTION "The radio 2 working state"
::= { ciscoUrwbInfo 5 }

ciscoUrwbFreq1 OBJECT-TYPE
	SYNTAX Integer32
	MAX-ACCESS read-only
	STATUS current
	DESCRIPTION "Radio 1 frequency in MHz"
::= { ciscoUrwbInfo 6 }

ciscoUrwbChanWidth1 OBJECT-TYPE
	SYNTAX Integer32
	MAX-ACCESS read-only
	STATUS current
	DESCRIPTION "Radio 1 Channel width in MHz"
::= { ciscoUrwbInfo 7 }

ciscoUrwbFreq2 OBJECT-TYPE
	SYNTAX Integer32
	MAX-ACCESS read-only
	STATUS current
	DESCRIPTION "Radio 2 frequency in MHz"
::= { ciscoUrwbInfo 8 }

ciscoUrwbChanWidth2 OBJECT-TYPE
	SYNTAX Integer32
	MAX-ACCESS read-only
	STATUS current
	DESCRIPTION "Radio 2 Channel width in MHz"
::= { ciscoUrwbInfo 9 }

ciscoUrwbName OBJECT-TYPE
	SYNTAX DisplayString(SIZE (0..255))
	MAX-ACCESS read-only
	STATUS current
	DESCRIPTION "Name of the device"
::= { ciscoUrwbInfo 10 }

ciscoUrwbMid OBJECT-TYPE
	SYNTAX IpAddress
	MAX-ACCESS read-only
	STATUS current
	DESCRIPTION "Mesh-ID of the device"
::= { ciscoUrwbInfo 11 }

ciscoUrwbUptime OBJECT-TYPE
	SYNTAX DisplayString(SIZE (0..255))
	MAX-ACCESS read-only
	STATUS current
	DESCRIPTION "Device uptime"
::= { ciscoUrwbInfo 12 }

ciscoUrwbSerial OBJECT-TYPE
	SYNTAX DisplayString (SIZE (0..255))
	MAX-ACCESS read-only
	STATUS current
	DESCRIPTION "Device serial number"
::= { ciscoUrwbInfo 13 }

ciscoUrwbDate OBJECT-TYPE
	SYNTAX DisplayString (SIZE (0..255))
	MAX-ACCESS read-only
	STATUS current
	DESCRIPTION "System date"
::= { ciscoUrwbInfo 14 }

ciscoUrwbStaNum OBJECT-TYPE
	SYNTAX INTEGER
	MAX-ACCESS read-only
	STATUS current
	DESCRIPTION "The number of connected stations"
::= { ciscoUrwbInfo 20 }

ciscoUrwbStaTable OBJECT-TYPE
	SYNTAX SEQUENCE OF CiscoUrwbStaEntry
	MAX-ACCESS not-accessible
	STATUS current
	DESCRIPTION "The list of connected stations. The number of entries is
	given by the ciscoUrwbStaNum value"
::= { ciscoUrwbInfo 21 }

ciscoUrwbStaEntry OBJECT-TYPE
	SYNTAX CiscoUrwbStaEntry
	MAX-ACCESS not-accessible
	STATUS current
	DESCRIPTION "An entry containing one Station"
	INDEX { ciscoUrwbStaIndex }
::= { ciscoUrwbStaTable 1 }

CiscoUrwbStaEntry ::=
	SEQUENCE {
		ciscoUrwbStaIndex		INTEGER,
		ciscoUrwbLocalMacAddress		DisplayString,
		ciscoUrwbStaMacAddress		DisplayString,
		ciscoUrwbStaMid		IpAddress,
		ciscoUrwbStaSignal		INTEGER,
		ciscoUrwbStaRxBytes		Counter32,
		ciscoUrwbStaRxPkts		Counter32,
		ciscoUrwbStaRxRate		INTEGER,
		ciscoUrwbStaRxMcs		DisplayString,
		ciscoUrwbStaRxMcsFlag		DisplayString,
		ciscoUrwbStaTxBytes		Counter32,
		ciscoUrwbStaTxPkts		Counter32,
		ciscoUrwbStaTxFail		Counter32,
		ciscoUrwbStaTxRetry		Counter32,
		ciscoUrwbStaTxRate		INTEGER,
		ciscoUrwbStaTxMcs		DisplayString,
		ciscoUrwbStaTxMcsFlag		DisplayString
	}

ciscoUrwbStaIndex OBJECT-TYPE
	SYNTAX INTEGER (1..1024)
	MAX-ACCESS read-only
	STATUS current
	DESCRIPTION "The index of the Station"
::= { ciscoUrwbStaEntry 1 }

ciscoUrwbLocalMacAddress OBJECT-TYPE
	SYNTAX DisplayString (SIZE (0..255))
	MAX-ACCESS read-only
	STATUS current
	DESCRIPTION "MAC address of the local wireless interface relative to this Station info"
::= { ciscoUrwbStaEntry 2 }

ciscoUrwbStaMacAddress OBJECT-TYPE
	SYNTAX DisplayString (SIZE (0..255))
	MAX-ACCESS read-only
	STATUS current
	DESCRIPTION "The mac address of the station"
::= { ciscoUrwbStaEntry 3 }

ciscoUrwbStaMid OBJECT-TYPE
	SYNTAX IpAddress
	MAX-ACCESS read-only
	STATUS current
	DESCRIPTION "The mesh-id of the station"
::= { ciscoUrwbStaEntry 4 }

ciscoUrwbStaSignal OBJECT-TYPE
	SYNTAX Integer32
	MAX-ACCESS read-only
	STATUS current
	DESCRIPTION "The signal strength of the Station in dBm"
::= { ciscoUrwbStaEntry 5 }

ciscoUrwbStaRxBytes OBJECT-TYPE
	SYNTAX Counter32
	MAX-ACCESS read-only
	STATUS current
	DESCRIPTION "The bytes received from the Station"
::= { ciscoUrwbStaEntry 6 }

ciscoUrwbStaRxPkts OBJECT-TYPE
	SYNTAX Counter32
	MAX-ACCESS read-only
	STATUS current
	DESCRIPTION "The packets received from the Station"
::= { ciscoUrwbStaEntry 7 }

ciscoUrwbStaRxRate OBJECT-TYPE
	SYNTAX INTEGER
	MAX-ACCESS read-only
	STATUS current
	DESCRIPTION "IEEE802.11 RX rate in Mbit/s"
::= { ciscoUrwbStaEntry 8 }

ciscoUrwbStaRxMcs OBJECT-TYPE
	SYNTAX DisplayString (SIZE (0..255))
	MAX-ACCESS read-only
	STATUS current
	DESCRIPTION "Index of the current RX MCS (for VHT/HE channels it shows <MCS/NSS>)"
::= { ciscoUrwbStaEntry 9 }

ciscoUrwbStaRxMcsFlag OBJECT-TYPE
	SYNTAX DisplayString (SIZE (0..255))
	MAX-ACCESS read-only
	STATUS current
	DESCRIPTION "Channel RX flags: NO-HT or HT/VHT/HE mode plus BW and GI info."
::= { ciscoUrwbStaEntry 10 }

ciscoUrwbStaTxBytes OBJECT-TYPE
	SYNTAX Counter32
	MAX-ACCESS read-only
	STATUS current
	DESCRIPTION "The bytes transmitted to the Station"
::= { ciscoUrwbStaEntry 11 }

ciscoUrwbStaTxPkts OBJECT-TYPE
	SYNTAX Counter32
	MAX-ACCESS read-only
	STATUS current
	DESCRIPTION "The packets transmitted to the Station"
::= { ciscoUrwbStaEntry 12 }

ciscoUrwbStaTxFail OBJECT-TYPE
	SYNTAX Counter32
	MAX-ACCESS read-only
	STATUS current
	DESCRIPTION "The number of packet transmission failures to the Station"
::= { ciscoUrwbStaEntry 13 }

ciscoUrwbStaTxRetry OBJECT-TYPE
	SYNTAX Counter32
	MAX-ACCESS read-only
	STATUS current
	DESCRIPTION "The number of packet retransmissions to the Station"
::= { ciscoUrwbStaEntry 14 }

ciscoUrwbStaTxRate OBJECT-TYPE
	SYNTAX INTEGER
	MAX-ACCESS read-only
	STATUS current
	DESCRIPTION "IEEE802.11 TX rate in Mbit/s"
::= { ciscoUrwbStaEntry 15 }

ciscoUrwbStaTxMcs OBJECT-TYPE
	SYNTAX DisplayString (SIZE (0..255))
	MAX-ACCESS read-only
	STATUS current
	DESCRIPTION "Index of the current TX MCS (for VHT/HE channels it shows <MCS/NSS>)"
::= { ciscoUrwbStaEntry 16 }

ciscoUrwbStaTxMcsFlag OBJECT-TYPE
	SYNTAX DisplayString (SIZE (0..255))
	MAX-ACCESS read-only
	STATUS current
	DESCRIPTION "Channel TX flags: NO-HT or HT/VHT/HE mode plus BW and GI info"
::= { ciscoUrwbStaEntry 17 }

ciscoUrwbTputNum OBJECT-TYPE
	SYNTAX INTEGER
	MAX-ACCESS read-only
	STATUS current
	DESCRIPTION "The number of entries in the Throughput table"
::= { ciscoUrwbInfo 22 }

ciscoUrwbTputTable OBJECT-TYPE
	SYNTAX SEQUENCE OF CiscoUrwbTputEntry
	MAX-ACCESS not-accessible
	STATUS current
	DESCRIPTION "Throughput table"
::= { ciscoUrwbInfo 23 }

ciscoUrwbTputEntry OBJECT-TYPE
	SYNTAX CiscoUrwbTputEntry
	MAX-ACCESS not-accessible
	STATUS current
	DESCRIPTION "An Throughput entry"
	INDEX { ciscoUrwbTputIndex }
::= { ciscoUrwbTputTable 1 }

CiscoUrwbTputEntry ::=
	SEQUENCE {
		ciscoUrwbTputIndex		INTEGER,
		ciscoUrwbTputIface		INTEGER,
		ciscoUrwbTputRx		Counter32,
		ciscoUrwbTputTx		Counter32
	}

ciscoUrwbTputIndex OBJECT-TYPE
	SYNTAX INTEGER (0..16)
	MAX-ACCESS read-only
	STATUS current
	DESCRIPTION "The index of the entry in the table"
::= { ciscoUrwbTputEntry 1 }

ciscoUrwbTputIface OBJECT-TYPE
	SYNTAX INTEGER { wired(1), wireless1(2), wireless2(3) }
	MAX-ACCESS read-only
	STATUS current
	DESCRIPTION "The type of interface"
::= { ciscoUrwbTputEntry 2 }

ciscoUrwbTputTx OBJECT-TYPE
	SYNTAX Counter32
	MAX-ACCESS read-only
	STATUS current
	DESCRIPTION "The outgoing throughput in Kbit/s"
::= { ciscoUrwbTputEntry 3 }

ciscoUrwbTputRx OBJECT-TYPE
	SYNTAX Counter32
	MAX-ACCESS read-only
	STATUS current
	DESCRIPTION "The incoming throughput in Kbit/s"
::= { ciscoUrwbTputEntry 4 }

ciscoUrwbLoad1 OBJECT-TYPE
	SYNTAX DisplayString(SIZE (0..255))
	MAX-ACCESS read-only
	STATUS current
	DESCRIPTION "CPU average load in the last minute"
::= { ciscoUrwbInfo 25 }

ciscoUrwbLoad5 OBJECT-TYPE
	SYNTAX DisplayString(SIZE (0..255))
	MAX-ACCESS read-only
	STATUS current
	DESCRIPTION "CPU average load in the last 5 minutes"
::= { ciscoUrwbInfo 26 }

ciscoUrwbLoad15 OBJECT-TYPE
	SYNTAX DisplayString(SIZE (0..255))
	MAX-ACCESS read-only
	STATUS current
	DESCRIPTION "CPU average load in the last 15 minutes"
::= { ciscoUrwbInfo 27 }

ciscoUrwbTemperature OBJECT-TYPE
	SYNTAX INTEGER
	MAX-ACCESS read-only
	STATUS current
	DESCRIPTION "Device temperature"
::= { ciscoUrwbInfo 28 }

ciscoUrwbSoftwareStatus OBJECT-TYPE
	SYNTAX INTEGER { fault(0), normal(1) }
	MAX-ACCESS read-only
	STATUS current
	DESCRIPTION "Device software status"
::= { ciscoUrwbInfo 29 }

ciscoUrwbGenericHwFail OBJECT IDENTIFIER ::= { ciscoUrwbInfo 30 }

ciscoUrwbGenericHwFailTime OBJECT-TYPE
	SYNTAX DisplayString (SIZE (0..255))
	MAX-ACCESS read-only
	STATUS current
	DESCRIPTION "Error code for last generic hardware failure: Failure Error Timestamp"
::= { ciscoUrwbGenericHwFail 1 }

ciscoUrwbGenericHwFailCode OBJECT-TYPE
	SYNTAX INTEGER
	MAX-ACCESS read-only
	STATUS current
	DESCRIPTION "Error code for last generic hardware failure: Error Code Identifier"
::= { ciscoUrwbGenericHwFail 2 }

ciscoUrwbGenericHwFailInfo OBJECT-TYPE
	SYNTAX DisplayString (SIZE (0..255))
	MAX-ACCESS read-only
	STATUS current
	DESCRIPTION "Error code for last generic hardware failure: Error type additional info"
::= { ciscoUrwbGenericHwFail 3 }

ciscoUrwbDetectedRadars OBJECT-TYPE
	SYNTAX INTEGER
	MAX-ACCESS read-only
	STATUS current
	DESCRIPTION "Number of detected Radars"
::= { ciscoUrwbInfo 31 }

ciscoUrwbLastConfId OBJECT-TYPE
	SYNTAX INTEGER
	MAX-ACCESS read-only
	STATUS current
	DESCRIPTION "Last condifuration ID (Racer file)"
::= { ciscoUrwbInfo 32 }

ciscoUrwbGenericHwFailLogFile OBJECT-TYPE
	SYNTAX INTEGER
	MAX-ACCESS read-write
	STATUS current
	DESCRIPTION "Generic hardware failure log file stored"
::= { ciscoUrwbInfo 33 }

ciscoUrwbTracksideConn OBJECT IDENTIFIER ::= { ciscoUrwbInfo 40 }

ciscoUrwbTracksideConnStatic OBJECT-TYPE
	SYNTAX IpAddress
	MAX-ACCESS read-only
	STATUS current
	DESCRIPTION "Mesh-ID of trackside device connected to mobile device"
::= { ciscoUrwbTracksideConn 1 }

ciscoUrwbTracksideConnMobile OBJECT-TYPE
	SYNTAX IpAddress
	MAX-ACCESS read-only
	STATUS current
	DESCRIPTION "Mesh-ID of mobile device connected to trackside device"
::= { ciscoUrwbTracksideConn 2 }

ciscoUrwbTracksideConnMobilePrimary OBJECT-TYPE
	SYNTAX IpAddress
	MAX-ACCESS read-only
	STATUS current
	DESCRIPTION "Mesh-ID of mobile primary device"
::= { ciscoUrwbTracksideConn 3 }

ciscoUrwbTracksideConnRssi OBJECT-TYPE
	SYNTAX INTEGER
	MAX-ACCESS read-only
	STATUS current
	DESCRIPTION "Mobile device vs trackside device RSSI value"
::= { ciscoUrwbTracksideConn 4 }

ciscoUrwbVehicleInfo OBJECT IDENTIFIER ::= { ciscoUrwbInfo 41 }

ciscoUrwbTrainHead OBJECT-TYPE
	SYNTAX IpAddress
	MAX-ACCESS read-only
	STATUS current
	DESCRIPTION "Mesh-ID of the mobile device located in the head car"
::= { ciscoUrwbVehicleInfo 1 }

ciscoUrwbTrainTail OBJECT-TYPE
	SYNTAX IpAddress
	MAX-ACCESS read-only
	STATUS current
	DESCRIPTION "Mesh-ID of the mobile device located in the tail car"
::= { ciscoUrwbVehicleInfo 2 }

ciscoUrwbOnboardMobiles OBJECT-TYPE
	SYNTAX INTEGER
	MAX-ACCESS read-only
	STATUS current
	DESCRIPTION "Number of on-board mobile devices "
::= { ciscoUrwbVehicleInfo 3 }


ciscoUrwbMobileIp OBJECT-TYPE
	SYNTAX IpAddress
	MAX-ACCESS read-only
	STATUS current
	DESCRIPTION "Mobile Ip address"
::= { ciscoUrwbMobilityInfo 1 }

ciscoUrwbStaticIp OBJECT-TYPE
	SYNTAX IpAddress
	MAX-ACCESS read-only
	STATUS current
	DESCRIPTION "Static Ip address"
::= { ciscoUrwbMobilityInfo 2 }

ciscoUrwbMobileMid OBJECT-TYPE
	SYNTAX IpAddress
	MAX-ACCESS read-only
	STATUS current
	DESCRIPTION "Mobile Mesh-ID"
::= { ciscoUrwbMobilityInfo 3 }

ciscoUrwbStaticMid OBJECT-TYPE
	SYNTAX IpAddress
	MAX-ACCESS read-only
	STATUS current
	DESCRIPTION "Static Mesh-ID"
::= { ciscoUrwbMobilityInfo 4 }

ciscoUrwbHandoffSeq OBJECT-TYPE
	SYNTAX Counter32
	MAX-ACCESS read-only
	STATUS current
	DESCRIPTION "Handoff sequence number"
::= { ciscoUrwbMobilityInfo 7 }

ciscoUrwbMeshId OBJECT-TYPE
	SYNTAX IpAddress
	MAX-ACCESS read-only
	STATUS current
	DESCRIPTION "Device Mesh-ID"
::= { ciscoUrwbFailInfo 1 }

ciscoUrwbTimestamp OBJECT-TYPE
	SYNTAX DisplayString (SIZE (0..255))
	MAX-ACCESS read-only
	STATUS current
	DESCRIPTION "Failure Error Timestamp"
::= { ciscoUrwbFailInfo 2 }

ciscoUrwbErrorCode OBJECT-TYPE
	SYNTAX INTEGER
	MAX-ACCESS read-only
	STATUS current
	DESCRIPTION "Error Code Identifier"
::= { ciscoUrwbFailInfo 3 }

ciscoUrwbAdditionalInfo OBJECT-TYPE
	SYNTAX DisplayString (SIZE (0..255))
	MAX-ACCESS read-only
	STATUS current
	DESCRIPTION "Error type additional info"
::= { ciscoUrwbFailInfo 4 }

ciscoUrwbFailSshLoginFlag OBJECT-TYPE
	SYNTAX INTEGER { invalid-username(1), invalid-passwd(2) }
	MAX-ACCESS read-only
	STATUS current
	DESCRIPTION "Flag identifying type of failed SSH login attempt"
::= { ciscoUrwbFailSshLoginInfo 1 }

ciscoUrwbFailSshLoginUser OBJECT-TYPE
	SYNTAX DisplayString (SIZE (0..255))
	MAX-ACCESS read-only
	STATUS current
	DESCRIPTION "Username used for failed SSH login attempt"
::= { ciscoUrwbFailSshLoginInfo 2 }

ciscoUrwbFailWebLoginUser OBJECT-TYPE
	SYNTAX DisplayString (SIZE (0..255))
	MAX-ACCESS read-only
	STATUS current
	DESCRIPTION "Username used for failed WEB login attempt"
::= { ciscoUrwbFailWebLoginInfo 1 }

ciscoUrwbHeadMid OBJECT-TYPE
	SYNTAX IpAddress
	MAX-ACCESS read-only
	STATUS current
	DESCRIPTION "Train Head car Mesh-ID"
::= { ciscoUrwbHeadInfo 1 }

ciscoUrwbTailMid OBJECT-TYPE
	SYNTAX IpAddress
	MAX-ACCESS read-only
	STATUS current
	DESCRIPTION "Train Tail car Mesh-ID"
::= { ciscoUrwbHeadInfo 2 }

END
