------------------------------------------------------------------------------
------------------------------------------------------------------------------
--
--  File         : gbnRadius.mib
--  Description  : Sample admin Radius configuration MIB 
--  Version      : 1.0  
--  Date         : July 2, 2002     
--
--  Copyright (c) 1999-2000 admin Systems, Inc.  All Rights Reserved.
--
------------------------------------------------------------------------------

    GBNServiceRADIUS-MIB DEFINITIONS ::= BEGIN

    IMPORTS
        MODULE-IDENTITY, OBJECT-TYPE,
        Integer32, IpAddress, 
        NOTIFICATION-TYPE                       FROM SNMPv2-SMI
        
        DisplayString, MacAddress,
        RowStatus, TruthValue                   FROM SNMPv2-TC
        
        MODULE-COMPLIANCE, OBJECT-GROUP         FROM SNMPv2-CONF
        
        gbnServiceAAA                           FROM ADMIN-MASTER-MIB;
        

    gbnRadiusMib MODULE-IDENTITY
        LAST-UPDATED    "0008290000Z"
        ORGANIZATION    "admin Systems, Inc."
        CONTACT-INFO    "admin Systems, Inc.
                         E-mail: support@admin.com.cn"
        DESCRIPTION     "admin Radius Enterprise MIB definition."
        REVISION        "0008290000Z"
        DESCRIPTION     "admin Radius Enterprise MIB definition."
        ::= { gbnServiceAAA 2 }

------------------------------------------------------------------------------
--  define groups in admin-RADIUS-MIB
------------------------------------------------------------------------------

        -------------------------------------------------------------------
        --Add gbnRadiusConfTable MIB      2002/07/02     ouyangchunbo
        -------------------------------------------------------------------
        gbnRadiusConfTable OBJECT-TYPE
        SYNTAX SEQUENCE OF GbnRadiusConfEntry
        MAX-ACCESS not-accessible
        STATUS current
        DESCRIPTION
            "A Table of Radius configuration table"
        ::= { gbnRadiusMib 1 }

        gbnRadiusConfEntry OBJECT-TYPE
        SYNTAX GbnRadiusConfEntry
        MAX-ACCESS not-accessible
        STATUS current
        DESCRIPTION
            "A list of radius parameters."
        INDEX { serverIndex }
        ::= { gbnRadiusConfTable 1 }

        GbnRadiusConfEntry ::= SEQUENCE {
            serverIndex     Integer32,
            serverName      DisplayString,
            primServerIP    DisplayString,
            primAuthPort    Integer32,
            primAcctPort     Integer32,
            secServerIP     DisplayString,
            secAuthPort      Integer32,
            secAcctPort     Integer32,
            radiusKey             DisplayString,
            bRadiusUsed     TruthValue,
            userNameFormat   TruthValue,
            realAcctTime     Integer32,
            bRealAcct     TruthValue,
            gbnRadiusClientIp DisplayString,
            primAcctServerIP    DisplayString,
            secAcctServerIP     DisplayString,
            acctKey             DisplayString            
          }

        serverIndex OBJECT-TYPE
        SYNTAX INTEGER (1..1024)
        MAX-ACCESS not-accessible
        STATUS current
        DESCRIPTION
            "A simple index into 'gbnRadiusConfTable'."
        ::= { gbnRadiusConfEntry 1 }

        serverName OBJECT-TYPE
        SYNTAX DisplayString
        MAX-ACCESS read-write
        STATUS current
        DESCRIPTION
            " A simple serverName of gbnRadiusConfEntry."
        ::= { gbnRadiusConfEntry 2 }

        primServerIP OBJECT-TYPE
        SYNTAX DisplayString
        MAX-ACCESS read-write
        STATUS current
        DESCRIPTION
            " A simple primServerIP of gbnRadiusConfEntry."
        ::= { gbnRadiusConfEntry 3 }

        primAuthPort OBJECT-TYPE
        SYNTAX INTEGER
        MAX-ACCESS read-write
        STATUS current
        DESCRIPTION
            "DURABLE: 1812:all. The authenticate port of prime radius server"
        ::= { gbnRadiusConfEntry 4 }

        primAcctPort OBJECT-TYPE
        SYNTAX INTEGER
        MAX-ACCESS read-write
        STATUS current
        DESCRIPTION
            "DURABLE: 1813:all. The account port of prime radius server"
        ::= { gbnRadiusConfEntry 5 }


        secServerIP OBJECT-TYPE
        SYNTAX DisplayString
        MAX-ACCESS read-write
        STATUS current
        DESCRIPTION
            " A simple secServerIP of gbnRadiusConfEntry."
        ::= { gbnRadiusConfEntry 6 }

        secAuthPort OBJECT-TYPE
        SYNTAX INTEGER
        MAX-ACCESS read-write
        STATUS current
        DESCRIPTION
            "DURABLE: 1812:all. The authenticate port of second radius server"
        ::= { gbnRadiusConfEntry 7 }

        secAcctPort OBJECT-TYPE
        SYNTAX INTEGER
        MAX-ACCESS read-write
        STATUS current
        DESCRIPTION
            "DURABLE: 1813:all. The account port of second radius server"
        ::= { gbnRadiusConfEntry 8 }

        radiusKey OBJECT-TYPE
        SYNTAX DisplayString
        MAX-ACCESS read-write
        STATUS current
        DESCRIPTION
            "DURABLE: empty. A simple radiusKey of gbnRadiusConfEntry."
        ::= { gbnRadiusConfEntry 9 }

        bRadiusUsed OBJECT-TYPE
        SYNTAX TruthValue
        MAX-ACCESS read-write
        STATUS current
        DESCRIPTION
             "Status of the current radius server 1-used  2 - unused."
        ::= { gbnRadiusConfEntry 10 }

        userNameFormat OBJECT-TYPE
        SYNTAX TruthValue
        MAX-ACCESS read-write
        STATUS current
        DESCRIPTION
             "Status of user name format configuration 1-with domain  2-without domain."
        ::= { gbnRadiusConfEntry 11 }

        realAcctTime OBJECT-TYPE
        SYNTAX INTEGER
        MAX-ACCESS read-write
        STATUS current
        DESCRIPTION
            "The realtime account time of radius server,the value of default is 12 minutes"
        ::= { gbnRadiusConfEntry 12 }

        bRealAcct OBJECT-TYPE
        SYNTAX TruthValue
        MAX-ACCESS read-write
        STATUS current
        DESCRIPTION
             "Status of the realtime account switch 1-used  2 - unused."
        ::= { gbnRadiusConfEntry 13 }

    gbnRadiusClientIp OBJECT-TYPE
        SYNTAX DisplayString
        MAX-ACCESS read-write
        STATUS current
        DESCRIPTION
            " A system IP address for RADIUS client to report who it is to the server."
        ::= { gbnRadiusConfEntry 14 }

        primAcctServerIP OBJECT-TYPE
        SYNTAX DisplayString
        MAX-ACCESS read-write
        STATUS current
        DESCRIPTION
            " A simple primAcctServerIP of gbnRadiusConfEntry."
        ::= { gbnRadiusConfEntry 15 }    

        secAcctServerIP OBJECT-TYPE
        SYNTAX DisplayString
        MAX-ACCESS read-write
        STATUS current
        DESCRIPTION
            " A simple secAcctServerIP of gbnRadiusConfEntry."
        ::= { gbnRadiusConfEntry 16 }        

       acctKey OBJECT-TYPE
        SYNTAX DisplayString
        MAX-ACCESS read-write
        STATUS current
        DESCRIPTION
            "DURABLE: empty. A simple acctKey of gbnRadiusConfEntry."
        ::= { gbnRadiusConfEntry 17 }
--
-- END of admin-RADIUS-MIB                
--

END
