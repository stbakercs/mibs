-- **************************************************************
-- **************************************************************
-- +++
-- Copyright 2001-2008 Symmetricom Austin
-- 
-- FILENAME:    SSU2000.MIB 
-- PRODUCT: SSU2000 COMM Module
-- DESCRIPTION:
--   This file contains the Symmetricom-Austin SSU2000 private MIB.
-- 
-- NOTES:
--  In this private MIB, when we define the syntax in Octet String,
--  we use the subset of the Type-Length-Value (TLV) format (except 
--  we specified otherwise).
--
--  The TLV
--      TYPE (1 byte): indicates the ASN.1 type, as well as 
--          the class of the type. 
--      LENGTH (1 byte): indicates the length of the actual 
--          value represention
--      VALUE: represents the value of the ASN.1 type as 
--          a string octets.
--
--  The (1 byte) type is defined as
--  Class [bit 6-7], P/C [bit 5], Tag Number [bit 0-4]
--    Class:
--      00 = Universal
--      01 = Application
--      10 = Context Specific
--      11 = Private
--
--    P/C:
--      0 = Primitive Encoding
--      1 = Constructed encoding
--
--    Tag Number:
--      1 = Boolean type
--      2 = Integer
--      4 = Octetstring type
--      5 = Null type
--      10 = Enumerated type
--      
--  In our application, the type is Application Class with 
--      Primitive Encoding (0x40).
--   
--
--
-- COMMENTS/CHANGES:
--      JJW 01/11/2001  - Jay Wang: Created
--      JJW 06/06/2001  - Fixed StaDiMtie1A/B and StaDiMtie2A/B missing mtie100000 definition
--      JJW 06/22/2001  - Change setMiFreqAErrLmt/setMiFreqBErrLmt setMiFreqAErrLmt/setMiFreqBErrLmt range to [0..10000000]
--      JJW 06/22/2001  - added extra definition NA for setDiCSFlt.
--      JJW 06/22/2001  - changed setMiMtie10xxxEL1/2 and setMiMtie10xxxCL1/2 limits to [0..60000] since defined as 16bits.
--      JJW 09/26/2001  - Changed the Opaque to OCTET STRING
--      JJW 10/22/2001  - Removed value "warm(1)" in setCkPLLMode
--      JJW 10/22/2001  - Put stronger check to make sure mtHisInpLoc and tdHisInpLoc specified with port number
--      JJW 10/22/2001  - Removed value "ignored" in tpNtfCode which is not used.
--      JJW 01/25/2002  - Added the Composite Clock Input Module, statusCcInp and setupCcInp
--      JJW 01/25/2002  - Added  sysOpmode field in sys to set subtending or non-subtending mode
--      JJW 02/19/2002  - Allowed additional pql value 1 and 9 be settable in setGpsProvPql, setDiProvPql, and setCiProvPql fields.
--      JJW 07/09/2002  - Changed setGpsPdop range from 1-10 to 3-10.
--      JJW 07/09/2002  - Changed setCcComp comments for 275ft per step intead of 500ft per step.
--      JJW 07/16/2002  - Added inAdapterPart field in InEntry.
--      JJW 10/02/2002  - Added staOtPortSta range from 1-5 to 1-6 where 6 is defined as port is squelched.
--      JJW 10/02/2002  - Added setCoSquelch field in SetCoEntry.
--      JJW 04/01/2003  - Added RS422 Output Module MIB in setup422Out
--      JJW 05/01/2003  - Changed the MODULE-IDENTITY to Symmetricom
--      JJW 06/18/2003  - Added E12048 Output Module MIB in setupE12048Out
--      JJW 09/23/2003  - Restricted snmpmanIp to Read Only for SNMPv3 (It belongs to Level4 function)
--      JJW 09/23/2003  - Restricted snmpmanInit to v2 and not apply to v3.
--      JJW 11/20/2003  - Changed setCkMinTau and setCkMaxTau ranges from (300..10000) to (150..10000)
--      JJW 01/08/2004  - Added DS1 LRM Module MIB in statusLrm and setupLrm
--      JJW 02/06/2004  - Added pllflt(6) in staLrmMRefSrc field
--      JJW 02/06/2004  - Added unknown(4) in staLrmMCtaId field
--      JJW 03/05/2004  - Added etl1c(10) and etl1d(11) in comLogoff fields.
--      JJW 03/05/2004  - Added etl1c(10) and etl1d(11) in whoPort fields.
--      JJW 03/08/2004  - Allowed pql value 1 thru 9 be settable in setGpsProvPql, setDiProvPql, and setCiProvPql fields.
--      JJW 03/08/2004  - Added sysTl1Format(sys 5)object in sys object.
--      JJW 03/29/2004  - Added Sine Output Module MIB in setupSineOut
--      JJW 03/29/2004  - Added Sine Input Module MIB in setupSineInp and statusSineInp
--      JJW 03/29/2004  - Added Japanese Composite Clock Output Module MIB in setupJccOut
--      JJW 03/29/2004  - Added Japanese Composite Clock Input Module MIB in setupJccInp and statusJccInp
--      JJW 07/23/2004  - Added japanese(3)in sysOpmode fields (i.e. Japanese subtending mode).
--      JJW 10/11/2004  - Changed the stGpsTkChnl from 1..8 to 1..12
--      JJW 01/12/2005  - added xxxMStatus (module status) fields for all input modules.
--      JJW 01/14/2005  - Tracker #20460, limited pql value 1 and 9 be settable in setGpsProvPql, setDiProvPql, setCiProvPql, setSineiProvPql, setJcciProvPql fields.
--      JJW 02/01/2005  - RES #3321, Added/changed snmpman objects and fields for new v3 implementation
--                        renamed snmpmanTable to snmpv2manTable 
--                        added initv2 and initv3 fields in snmpmanInit object 
--                        added snmpNotification, snmpEnable, snmpv3manTable, snmpv2userTable, snmpv3userTable objects
--      JJW 02/01/2005  - Added sInterfaces(ssu2000 60) object to specify if various interfaces present or not.
--      JJW 02/01/2005  - RES #3464, Added E1 LRM Module MIB in statusLrme1 and setupLrme1.
--      JJW 02/01/2005  - removed statusCdma (mstatus 6) and setupCdma (msetup 6) in the msetup object.
--      JJW 02/01/2005  - Tracker #20519, added setGpsZeroPhase field in SetGpsEntry.
--      JJW 02/22/2005  - Tracker #20553, applied "ssu2000 MODULE-IDENTITY" OID with {austron 1 1} instead of {products 1} (note: both are the same OID)
--                          to avoid conflicts within HP Openview with some MIBs from other vendors.
--      JJW 02/22/2005  - Tracker #20545, removed unnecessary fields in the CC inp module of StaCiEntry, SetCiEntry, and SetCimEntry.
--      JJW 05/20/2005  - Tracker #20580, added fields setE12048oFrame, setE12048oCrc, setE12048oSsm, setE12048oCrc and setE12048oSsmBit in SetE12048oEntry.
--      JJW 08/26/2005  - Tracker #21166, added sysAco 'alarm cut off' (sys 7) in sys object.
--      JJW 02/22/2006  - Version realignment.
--      JJW 03/28/2006  - Added more description in TModuleCode hex number module definition.
--      JJW 03/29/2006  - Tracker #21301, Added ntpPrefer (ntp 12) in the ntp object.
--      JJW 03/30/2006  - Tracker #20656, Added tmLocalOffset (time 2) in the time object and TLocalTimeOffset definition.
--      JJW 04/25/2006  - Tracker #20639, Added GPS Performance Monitor (MTIE and FREQ)
--                        added staGpsMtie1A, staGpsMtie2A, staGpsMtie1B, staGpsMtie2B, staGpsFreqA, staGpsFreqB to StaGpsEntry object.
--                        added setAlmThGpsInpTable object in (setupGps 2) for MTIE and FREQ setting.
--      JJW 06/20/2006  - Tracker #21475, Changed the limitis from 1-100k, to 1-10k in setMiOOFErrCnt,setMiOOFClrCnt,setMiBPVErrCnt,
--                          setMiBPVClrCnt, setMiCRCErrCnt,and setMiCRCClrCnt in the DS1/E1 input module. 
--                          setCimBPVErrCnt and setCimBPVClrCnt in the CC Input Module
--      JJW 10/18/2006  - Tracker #22077, Added alarm threshold setting in the Sine Input Module:
--                        added fields in staSineiPql, staSineiMtie1A, staSineiMtie2A, staSineiMtie1B, staSineiMtie2B,
--                        staSineiFreqA, staSineiFreqB in the staSineiEntry. 
--                        added a new object table setAlmThSineInpTable in setupSineInp object.
--      JJW 10/18/2006  - Tracker #21780, Added staGpsPpsSigma and staGps3Sigma in the StaGpsEntry object.
--      JJW 01/25/2008  - PRD 5.1, Added PackeTime NTP Module Support: 
--                          Added statusPtNtp object in  mstatus (15), 
--                          Added setupPtNtp object in msetup (22),
--                          Added ntpq object in ssu2000 (19),
--                          Added route object in ssu2000 (20),
--                          Added setCkTodTimeout field in the setCkEntry(7)
--                          Added staCkUtc field in the staCkEntry(7)
--                          Added refClkTodsrc field in the ref(7)
--                          Added setGpsTodsrcPriority(14) and setGpsTodsrcCompensation(15) field in the setGpsEntry.
--      JJW 02/02/2012  - PRD 6.4, Added following support:
--                          Added statusPtPtp object in  mstatus (16), 
--                          Added setupPtPtp object in msetup (23),
--                          Added ptpclient object in ssu2000 (36),
--                          Added almStatus field in almEntry (9),
--                          Added statusSynce object in  mstatus (17), 
--                          Added setupSynce object in  msetup (24),
--							Added setPtPtpRmvClient field in setPtPtpEntry (34) 
--                          Added setCkFreqTimeout field in the setCkEntry(8)
--      GGUO 07/08/2012 - PRD GLONASS, Added following support:
--                          Added setGnssCmode field in the setGpsEntry (16), 
--                          Added new option for setGpsEngine field in the setGpsEntry(3)
--                          modified stGpsTkChnl from 12 TO 32, 
--                          modified stGpsAvChnl from 12 TO 32, 
--                          modified setGpsAvg from 10..3600 to 20..3600, and also the method will
--								make GSP to be 20..3600, and GNSS to be 20..1440
--                          modified setGpsPosel from (0..60)to (0..90)
--                          modified setGpsTimel from (0..60)to (0..90)
--
-- CURRENT VERSION:
--      Part No - 12613127-002-2
--      04/16/2001  - A.00
--      07/06/2001  - A.01
--      01/21/2002  - A.02
--      07/17/2002  - B.00 (ECN#: 2167)
--      10/22/2002  - C.00 (ECN#: 2241)
--      05/15/2003  - D.00 (ECO#: 7735)
--      09/09/2003  - E.00 (ECO#: 7825)
--      01/14/2004  - F.00 (ECO#: 7946)
--      02/06/2004  - F.01 (ECO#: 7969)
--      03/05/2004  - F.02 (ECO#: 8021)
--      09/03/2004  - G.00 (ECO#: 8139)
--      02/01/2005  - G.01 (ECO#: 8302)
--      03/25/2005  - H.00 (ECO#: 8369)
--      09/29/2005  - J.00 (ECO#: 8483)
--      02/22/2006  - K.00 (ECO#: 8600)
--      07/06/2006  - L.00 (ECO#: 8762)
--      11/03/2006  - L.01 (ECO#: 8936)
--      06/10/2008  - M.00 (EC0#: 0190)
--      03/08/2012  - N.00 (EC07565)
--      08/17/2012  - P.00
-- 
-- +++
-- **************************************************************
-- **************************************************************


    SSU2000-MIB DEFINITIONS ::= BEGIN


    IMPORTS
            MODULE-IDENTITY, OBJECT-TYPE, NOTIFICATION-TYPE, 
            OBJECT-IDENTITY,Counter32, 
            IpAddress
        FROM SNMPv2-SMI

            DisplayString,TEXTUAL-CONVENTION
        FROM SNMPv2-TC

            austron
        FROM DATUM-MIB;


    ssu2000 MODULE-IDENTITY
        -- YYMMDD0000Z the LAST-UPDATED format
        LAST-UPDATED "0801140000Z"
        ORGANIZATION "Symmetricom"
        CONTACT-INFO
            "        
            Symmetricom Technical Support
            1-888-367-7966 toll free USA
            1-408-428-7907 worldwide
            Support@symmetricom.com
           "
    DESCRIPTION
          "Private MIB module for management of SSU2000.
          This SSU2000 private MIB supports all existing 
          functions of the SSU2000 thus achieving full system
          control via this software interface. All reports, 
          queries, autonomous messages, control, provisioning
          and administration (except for Set User ID/password/level, 
          Set IP assignments, Reset Connection and SNMP Community 
          Settings) will be addressable via SNMP.
          " 
    ::= { austron 1 1 }



    -- **************************************************************
    -- SSU2000 PRIVATE MIB, TOP-LEVEL TREE STRUCTURE
    -- **************************************************************

    inventory   OBJECT IDENTIFIER ::= { ssu2000 1 }
    mstatus     OBJECT IDENTIFIER ::= { ssu2000 2 }
    msetup      OBJECT IDENTIFIER ::= { ssu2000 3 }
    general     OBJECT IDENTIFIER ::= { ssu2000 4 }
    event       OBJECT IDENTIFIER ::= { ssu2000 5 }
    alarm       OBJECT IDENTIFIER ::= { ssu2000 6 }
    ref         OBJECT IDENTIFIER ::= { ssu2000 7 }
    phase       OBJECT IDENTIFIER ::= { ssu2000 8 }
    freq        OBJECT IDENTIFIER ::= { ssu2000 9 }
    ntp         OBJECT IDENTIFIER ::= { ssu2000 10 }
    time        OBJECT IDENTIFIER ::= { ssu2000 11 }
    pqlTable    OBJECT IDENTIFIER ::= { ssu2000 12 }
    ioname      OBJECT IDENTIFIER ::= { ssu2000 13 }
    comm        OBJECT IDENTIFIER ::= { ssu2000 14 }
    snmpman     OBJECT IDENTIFIER ::= { ssu2000 15 }
    sys         OBJECT IDENTIFIER ::= { ssu2000 16 }
    users       OBJECT IDENTIFIER ::= { ssu2000 17 }
    who         OBJECT IDENTIFIER ::= { ssu2000 18 }
    ntpq        OBJECT IDENTIFIER ::= { ssu2000 19 }
    route       OBJECT IDENTIFIER ::= { ssu2000 20 }

    mtie        OBJECT IDENTIFIER ::= { ssu2000 30 }
    tdev        OBJECT IDENTIFIER ::= { ssu2000 31 }

--    s1port      OBJECT IDENTIFIER ::= { ssu2000 32 }
--    phaseT1     OBJECT IDENTIFIER ::= { ssu2000 33 }
--    tie100      OBJECT IDENTIFIER ::= { ssu2000 34 }
--    mtie100     OBJECT IDENTIFIER ::= { ssu2000 35 }
    ptpclient   OBJECT IDENTIFIER ::= { ssu2000 36 }

    mTrapReq    OBJECT IDENTIFIER ::= { ssu2000 50 }
    mTrapObjs   OBJECT IDENTIFIER ::= { ssu2000 51 }
    mTraps      OBJECT IDENTIFIER ::= { ssu2000 52 }

    sInterfaces OBJECT IDENTIFIER ::= { ssu2000 60 }


    --
    -- status 
    --
    statusCom       OBJECT IDENTIFIER ::= { mstatus 1 }
    statusClk       OBJECT IDENTIFIER ::= { mstatus 2 }
    statusGps       OBJECT IDENTIFIER ::= { mstatus 5 }
    statusDs1E1Inp  OBJECT IDENTIFIER ::= { mstatus 7 }
    statusCcInp     OBJECT IDENTIFIER ::= { mstatus 8 }
    statusOut       OBJECT IDENTIFIER ::= { mstatus 10 }
    statusLrm       OBJECT IDENTIFIER ::= { mstatus 11 }
    statusSineInp   OBJECT IDENTIFIER ::= { mstatus 12 }
    statusJccInp    OBJECT IDENTIFIER ::= { mstatus 13 }
    statusLrmE1     OBJECT IDENTIFIER ::= { mstatus 14 }
    statusPtNtp     OBJECT IDENTIFIER ::= { mstatus 15 }
    statusPtPtp     OBJECT IDENTIFIER ::= { mstatus 16 }
    statusSynce     OBJECT IDENTIFIER ::= { mstatus 17 }


    --
    -- setup 
    --
    setupCom        OBJECT IDENTIFIER ::= { msetup 1 }
    setupClk        OBJECT IDENTIFIER ::= { msetup 2 }
    setupGps        OBJECT IDENTIFIER ::= { msetup 5 }
    setupDs1E1Inp   OBJECT IDENTIFIER ::= { msetup 7 }
    setupCcInp      OBJECT IDENTIFIER ::= { msetup 8 }
    setupDs1Out     OBJECT IDENTIFIER ::= { msetup 10 }
    setupE1Out      OBJECT IDENTIFIER ::= { msetup 11 }
    setup2048Out    OBJECT IDENTIFIER ::= { msetup 12 }
    setupCCOut      OBJECT IDENTIFIER ::= { msetup 13 }
    setup422Out     OBJECT IDENTIFIER ::= { msetup 14 }
    setupE12048Out  OBJECT IDENTIFIER ::= { msetup 15 }
    setupLrm        OBJECT IDENTIFIER ::= { msetup 16 }
    setupSineOut    OBJECT IDENTIFIER ::= { msetup 17 }
    setupSineInp    OBJECT IDENTIFIER ::= { msetup 18 }
    setupJccOut     OBJECT IDENTIFIER ::= { msetup 19 }
    setupJccInp     OBJECT IDENTIFIER ::= { msetup 20 }
    setupLrmE1      OBJECT IDENTIFIER ::= { msetup 21 }
    setupPtNtp      OBJECT IDENTIFIER ::= { msetup 22 }
    setupPtPtp      OBJECT IDENTIFIER ::= { msetup 23 }
    setupSynce      OBJECT IDENTIFIER ::= { msetup 24 }


    -- **************************************************************
    -- SSU2000 TEXTUAL-CONVENTION DEFINITION
    -- **************************************************************

    OkValue ::= INTEGER { ok (1), fault (2) }
    OnValue ::= INTEGER { on (1), off (2) }
    YesValue ::= INTEGER { yes (1), no (2) }
    EnaValue ::= INTEGER { ena (1), dis (2) }
    ActiveValue ::= INTEGER { active (1), inactive (2) }
    ValidValue ::= INTEGER { valid (1), invalid (2) }
    TrueValue ::= INTEGER { true (1), false (2) }


    -- ******************************************
    -- DEFINED IN RFC2579
    -- ******************************************

    DateAndTime ::= TEXTUAL-CONVENTION
        DISPLAY-HINT "2d-1d-1d,1d:1d:1d.1d,1a1d:1d"
        STATUS       current
        DESCRIPTION
            "A date-time specification.

            field  octets  contents                  range
            -----  ------  --------                  -----
              1      1-2   year*                     0..65536
              2       3    month                     1..12
              3       4    day                       1..31
              4       5    hour                      0..23
              5       6    minutes                   0..59
              6       7    seconds                   0..60
                           (use 60 for leap-second)
              7       8    deci-seconds              0..9
              8       9    direction from UTC        '+' / '-'
              9      10    hours from UTC*           0..13
             10      11    minutes from UTC          0..59

            * Notes:
            - the value of year is in network-byte order
            - daylight saving time in New Zealand is +13

            For example, Tuesday May 26, 1992 at 1:30:15 PM EDT would be
            displayed as:

                             1992-5-26,13:30:15.0,-4:0


            Note that if only local time is known, then timezone
            information (fields 8-10) is not present."
        SYNTAX       OCTET STRING (SIZE (8 | 11))


    -- ******************************************
    -- LOCAL TIME OFFSET DEFINITION
    -- ******************************************

    TLocalTimeOffset ::= TEXTUAL-CONVENTION
        DISPLAY-HINT "1a1d:1d"
        STATUS       current
        DESCRIPTION
            "A local time offset specification.

            field  octets  contents                  range
            -----  ------  --------                  -----
              1       1    direction from UTC        '+' / '-'
              2       2    hours from UTC*           0..13
              3       3    minutes from UTC          0..59

            * Notes:
            - the value of year is in network-byte order
            - The hours range is 0..13

            For example, the -6 local time offset would be
            displayed as:  -6:0
            "
        SYNTAX       OCTET STRING (SIZE (3))


    -- ******************************************
    -- MODULE HEX CODE DEFINITION
    -- ******************************************

    TModuleCode ::= TEXTUAL-CONVENTION
        DISPLAY-HINT "x"
        STATUS       current
        DESCRIPTION
            "The module hex code
            1001    Input - 3 Port
            1002    Input - 1 Port
            1003    Input - DS1 3 Port
            1004    Input - DS1 1 Port 
            1005    Input - E1 3 Port 
            1006    Input - E1 1 Port 
            1008    Input - GPS
            1010    Input - Composite Clock (1 Port)
            1012    Input - Japanese CC (1 Port)
            1013    Input - Japanese Sine (3 Port)
            2001    Clock - Stratum 2E Rubidium
            2002    Clock - Stratum 3E
            2003    Clock - Type I
            3001    Communication Module
            4001    Output - DS1
            4002    Output - E1
            4003    Output - Composite Clock
            4004    Output - 2048 kHz
            4007    Output - EIA 422
            4008    Output - E1/2048 kHz
            4009    DS1 Line Retiming Module 4 Ports
            400A    DS1 Line Retiming Module 2 Ports
            400B    Output  - Japanese CC
            400C    Output  - Japanese Sine
            400D    E1 Line Retiming Module 4 Ports
            4021    NTP Blade
            4022    PTP Blade
            5001    Buffer Card
            "         
        SYNTAX       INTEGER (0..'FFFF'h)


    -- ******************************************
    -- SYNC STATUS MESSAGE (SSM) DEFINITION
    -- ******************************************

    TSsm ::= TEXTUAL-CONVENTION
        DISPLAY-HINT "x"
        STATUS       current
        DESCRIPTION
            "The ssm hex code"
        SYNTAX       INTEGER (0..255)



    -- ******************************************
    -- ANTENNA LATITUDE AND LONGITUDE DEFINITION
    -- ******************************************

    TLatAndLon ::= TEXTUAL-CONVENTION
        DISPLAY-HINT "1a1d:1d:1d.1d"
        STATUS       current
        DESCRIPTION
            "antenna latitude and longitude specification.

            field  octets  contents                  range
            -----  ------  --------                  -----
              1       1    +/-180 deg                '+' / '-'
              2       2    degree                    0..180
              3       3    minute                    0..59
              4       4    second                    0..59
              5       5    second fraction           0..99

            +/- dd:mm:ss.ss
            "
        SYNTAX       OCTET STRING (SIZE (5))


    -- ******************************************
    -- ANTENNA HIGHT DEFINITION
    -- ******************************************

    TAntHeight ::= TEXTUAL-CONVENTION
        DISPLAY-HINT "1a2d.1d"
        STATUS       current
        DESCRIPTION
            "antenna height specification.

            field  octets  contents                  range
            -----  ------  --------                  -----
              1       1    +/-                       '+' / '-'
              2      2-3   meter                     0..10000
              3       4    meter fraction            0..99

            +/- hh.hh

            "
        SYNTAX       OCTET STRING (SIZE (4))



    -- **************************************************************
    -- **************************************************************
    -- SSU2000 INVENTORY GROUP
    -- **************************************************************
    -- **************************************************************

    inventoryTable OBJECT-TYPE
    SYNTAX  SEQUENCE OF InEntry
    MAX-ACCESS  not-accessible
    STATUS  current
    DESCRIPTION
    "A list containing the system inventory of installed hardware and software components contained in the SSU-2000. 
    The number of entries is given by the values of inChassis and inSlot.
    "
    ::= { inventory 1 }


    inEntry OBJECT-TYPE
    SYNTAX  InEntry
    MAX-ACCESS  not-accessible
    STATUS  current
    DESCRIPTION
    "The Inventory table contains inventory information for all modules installed in the SSU2000 unit.
    System Inventory attributes.
    "
    INDEX   { inChassis, inSlot }
    ::= { inventoryTable 1 }

 
    InEntry ::=
        SEQUENCE {
            inChassis
                INTEGER,    
            inSlot
                INTEGER,    
            inModCode
                TModuleCode,
            inName
                DisplayString,
            inSerial
                DisplayString,
            inService
                DateAndTime,
            inHwPart
                DisplayString,
            inHwRev
                DisplayString,
            inHwDate
                DateAndTime,
            inSwPart
                DisplayString,
            inSwRev
                DisplayString,
            inRevision
                DisplayString,
            inShelfDesc
                DisplayString,
            inShelfPart
                DisplayString,
            inInstalled
                YesValue,
            inAction
                INTEGER,
            inAdapterPart
                DisplayString
        }

    inChassis OBJECT-TYPE
        SYNTAX  INTEGER (1..5)
        MAX-ACCESS  not-accessible
        STATUS  current
        DESCRIPTION
        "Identifies which chassis is being addressed. 
        This chassis number and slot number uniquely identify each inventory entry.
        "
    ::= { inEntry 1 }

    inSlot OBJECT-TYPE
        SYNTAX  INTEGER (1..20)
        MAX-ACCESS  not-accessible
        STATUS  current
        DESCRIPTION
        "Identifies which slot is being addressed. 
        This chassis number and slot number uniquely identify each inventory entry.
        "
    ::= { inEntry 2 }

    inModCode OBJECT-TYPE
        SYNTAX  TModuleCode
        MAX-ACCESS  read-only
        STATUS  current
        DESCRIPTION
        "Reports module type is identified with a Hex value.
        "
    ::= { inEntry 3 }


    inName OBJECT-TYPE
        SYNTAX  DisplayString (SIZE (0..20))
        MAX-ACCESS  read-only
        STATUS  current
        DESCRIPTION
        "Reports module type is identified with a Name.
        "
    ::= { inEntry 4 }

    inSerial OBJECT-TYPE
        SYNTAX  DisplayString (SIZE (0..20))
        MAX-ACCESS  read-only
        STATUS  current
        DESCRIPTION
        "Reports module's serial number.
        "
    ::= { inEntry 5 }

    inService OBJECT-TYPE
        SYNTAX  DateAndTime
        MAX-ACCESS  read-only
        STATUS  current
        DESCRIPTION
        "Reports module's in-service time.
        "
    ::= { inEntry 6 }

    inHwPart OBJECT-TYPE
        SYNTAX  DisplayString (SIZE (0..14))
        MAX-ACCESS  read-only
        STATUS  current
        DESCRIPTION
        "Reports module's hardware part number.
        "
    ::= { inEntry 7 }

    inHwRev OBJECT-TYPE
        SYNTAX  DisplayString (SIZE (0..10))
        MAX-ACCESS  read-only
        STATUS  current
        DESCRIPTION
        "Reports module's hardware revision.
        "
    ::= { inEntry 8 }

    inHwDate OBJECT-TYPE
        SYNTAX  DateAndTime
        MAX-ACCESS  read-only
        STATUS  current
        DESCRIPTION
        "Reports module's date of manufacture.
        "
    ::= { inEntry 9 }

    inSwPart OBJECT-TYPE
        SYNTAX  DisplayString (SIZE (0..14))
        MAX-ACCESS  read-only
        STATUS  current
        DESCRIPTION
        "Reports module's software part number.
        "
    ::= { inEntry 10 }

    inSwRev OBJECT-TYPE
        SYNTAX  DisplayString (SIZE (0..10))
        MAX-ACCESS  read-only
        STATUS  current
        DESCRIPTION
        "Reports module's main software revision.
        "
    ::= { inEntry 11 }

    inRevision OBJECT-TYPE
        SYNTAX  DisplayString (SIZE (0..60))
        MAX-ACCESS  read-only
        STATUS  current
        DESCRIPTION
        "Reports module's software and PLD revisions.
        "
    ::= { inEntry 12 }

    inShelfDesc OBJECT-TYPE
        SYNTAX  DisplayString (SIZE (0..20))
        MAX-ACCESS  read-only
        STATUS  current
        DESCRIPTION
        "Reports shelf type description.
        "
    ::= { inEntry 13 }

    inShelfPart OBJECT-TYPE
        SYNTAX  DisplayString (SIZE (0..14))
        MAX-ACCESS  read-only
        STATUS  current
        DESCRIPTION
        "Reports shelf part number.
        "
    ::= { inEntry 14 }

    inInstalled OBJECT-TYPE
        SYNTAX  YesValue
        MAX-ACCESS  read-only
        STATUS  current
        DESCRIPTION
        "Reports if this module is physically installed in the system or not.
        1 = module is installed.
        2 = module is physically absent, but the configuration data is still there.
        "
    ::= { inEntry 15 }

    inAction OBJECT-TYPE
        SYNTAX  INTEGER
                {
                    enable(1),
                    disable(2),
                    remove(3)
                }
        MAX-ACCESS  read-write
        STATUS  current
        DESCRIPTION
        "User Action: 
        ENABLE (1), enables the module.
        DISABLE (2), marks a module as inactive to be removed from the system.
        REMOVE (3), if physically absent, the module is removed from the registry.

        Note: This field only is meaningful during the write operation.	
          When read, it always displayed as 1.
        "
    ::= { inEntry 16 }


    inAdapterPart OBJECT-TYPE
        SYNTAX  DisplayString (SIZE (0..14))
        MAX-ACCESS  read-only
        STATUS  current
        DESCRIPTION
            "Reports the Symmetricom input adapter part number.
            Note: If this field is an empty string, it means the input adapter identification is not applicable for this module.
            "
    ::= { inEntry 17 }

    -- **************************************************************
    -- SSU2000 FEATURE PRESENCE TABLE
    -- **************************************************************

    inFeatureTable OBJECT-TYPE
    SYNTAX  SEQUENCE OF InFeatureEntry
    MAX-ACCESS  not-accessible
    STATUS  current
    DESCRIPTION
    "The SSU-2000 has two optional features, NTP and SNMP.
    The Feature Presence table provides presence of these features.
    "
    ::= { inventory 2 }

    inFeatureEntry OBJECT-TYPE
    SYNTAX  InFeatureEntry
    MAX-ACCESS  not-accessible
    STATUS  current
    DESCRIPTION
    "inFeatureIndex
    The index to identify the feature
    inFeature
    The setting of the feature 
      "
    INDEX   { inFeatureIndex }
    ::= { inFeatureTable 1 }


    InFeatureEntry ::=
        SEQUENCE {
            inFeatureIndex
                INTEGER,    
            inFeature
                EnaValue
        }

    inFeatureIndex OBJECT-TYPE
        SYNTAX  INTEGER (1..2)
        MAX-ACCESS  not-accessible
        STATUS  current
        DESCRIPTION
        "A unique value for each feature table. 
        1 = NTP
        2 = SNMP
        "
    ::= { inFeatureEntry 1 }


    inFeature OBJECT-TYPE
        SYNTAX  EnaValue
        MAX-ACCESS  read-only
        STATUS  current
        DESCRIPTION
        "Reports SSU-2000 feature set:
        1 = Enabled  
        2 = Disabled
        "
    ::= { inFeatureEntry 2 }

    -- **************************************************************
    -- **************************************************************
    -- SSU2000 MODULE STATUS GROUP
    -- **************************************************************
    -- **************************************************************
    -- FUNCTIONAL DESCRIPTION
    -- The module status group provides information on each module
    -- installed in the system. There are status attributes that are
    -- common for all modules in the system and there are module
    -- specific attributes. All of the status attributes are 
    -- read-only objects. Descriptions of the specific module 
    -- attributes are listed in each Module Status Group for each type
    -- of module.


    -- **************************************************************
    -- SSU2000 COMMUNICATION MODULE STATUS GROUP
    -- **************************************************************
    -- FUNCTIONAL DESCRIPTION
    -- The module status group provides information on each module
    -- installed in the system. There are status attributes that are
    -- common for all modules in the system and there are module
    -- specific attributes. All of the status attributes are 
    -- read-only objects. Descriptions of the specific module 
    -- attributes are listed in each Module Status Group for each type
    -- of module.
    -- Though the Status Information will show alarm status (if a module
    -- is in an alarmed state or not), the detail of all alarm states 
    -- is available through the module's alarm object.
 

    -- **************************************************************
    -- SSU2000 CLOCK MODULE STATUS GROUP
    -- **************************************************************

    staClkTable OBJECT-TYPE
    SYNTAX  SEQUENCE OF StaCkEntry
    MAX-ACCESS  not-accessible
    STATUS  current
    DESCRIPTION
    "Reports Clock Module Status, loop mode, tau, and system-level priority quality level (pql).
    "
    ::= { statusClk 1 }


    staCkEntry OBJECT-TYPE
    SYNTAX  StaCkEntry
    MAX-ACCESS  not-accessible
    STATUS  current
    DESCRIPTION
    "Clock Status Attributes:
    "
    INDEX   { staCkChassis, staCkSlot}
    ::= { staClkTable 1 }

    StaCkEntry ::=
        SEQUENCE {
            staCkChassis
                INTEGER,    
            staCkSlot
                INTEGER,    
            staCkStatus
                INTEGER,    
            staCkPLLMode
                INTEGER,    
            staCkTau
                Counter32,  
            staCkPql
                INTEGER,    
            staCkUtc
                YesValue    
        }

    staCkChassis OBJECT-TYPE
        SYNTAX  INTEGER (1..1)
        MAX-ACCESS  not-accessible
        STATUS  current
        DESCRIPTION
        "Identifies which chassis is being addressed. 
        This chassis number and slot number uniquely identify each inventory entry.

        Note: In the SSU2000, this number is always one. (i.e. in the main chassis)
        "
    ::= { staCkEntry 1 }

    staCkSlot OBJECT-TYPE
        SYNTAX  INTEGER (1..20)
        MAX-ACCESS  not-accessible
        STATUS  current
        DESCRIPTION
        "Identifies which slot is being addressed. 
        This slot number and chassis number uniquely identify each inventory entry.

        Note: In the SSU2000, valid slots for Clocks are slot 1 and slot 12.
        "
    ::= { staCkEntry 2 }


    staCkStatus OBJECT-TYPE
        SYNTAX  INTEGER
                {
                    ok(1),
                    selected(2),
                    disable(3),
                    fault(4)
                }
        MAX-ACCESS  read-only
        STATUS  current
        DESCRIPTION
        "Reports the clock module status.
        ok(1), -- module is enabled and operating without faults
        selected(2), -- module is enabled and selected as primary local oscillator
        disable(3), -- module is disabled
        fault(4) -- module is enabled and operating with fault(s)
        "
    ::= { staCkEntry 3 }

    staCkPLLMode OBJECT-TYPE
        SYNTAX  INTEGER
                {
                    failed(1),
                    warmup(2),
                    acquire(3),
                    holdover(4),
                    lock(5)
                }
        MAX-ACCESS  read-only
        STATUS  current
        DESCRIPTION
        "Reports the clock software Phase Locked Loop (PLL) Mode.
        failed(1), -- pll hardware failure, pll unlocked
        warmup(2), -- local oscillator is initialized and warming up
        acquire(3), -- LO is operating in acquire or fast locked mode
        holdover(4), -- LO is operating in holdover due to lose or reference input
        lock(5) -- LO is operating in normal mode
        "
    ::= { staCkEntry 4 }

    staCkTau OBJECT-TYPE
        SYNTAX  Counter32
        MAX-ACCESS  read-only
        STATUS  current
        DESCRIPTION
        "Reports the clock tau value.
        The tau is the time constant (in seconds) used by the clock's servo control loop.
        "
    ::= { staCkEntry 5 }

    staCkPql OBJECT-TYPE
        SYNTAX  INTEGER (0 | 1..16)
        MAX-ACCESS  read-only
        STATUS  current
        DESCRIPTION
        "Reports the system Priority Quality Level (PQL). 
        The PQL indicates the Stratum Level of the clock.
        Zero indicates an invalid SSM was read.
        "
    ::= { staCkEntry 6 }

    staCkUtc OBJECT-TYPE
        SYNTAX  YesValue
        MAX-ACCESS  read-only
        STATUS  current
        DESCRIPTION
        "Reports the clock has been TOD synced with GPS or PackeTime..
        "
    ::= { staCkEntry 7 }

    -- **************************************************************
    -- SSU2000 GPS MODULE STATUS GROUP
    -- **************************************************************

    -- ******************************************
    -- GPS STATUS TABLE
    -- ******************************************

    staGpsTable OBJECT-TYPE
    SYNTAX  SEQUENCE OF StaGpsEntry
    MAX-ACCESS  not-accessible
    STATUS  current
    DESCRIPTION
    "The GPS Input Module Status reports the module's current status, input port phase data, 
    time status, MTIE threshold status, frequency threshold status, and TIE measurement statistics status.
    "
    ::= { statusGps 1 }

    staGpsEntry OBJECT-TYPE
    SYNTAX  StaGpsEntry
    MAX-ACCESS  not-accessible
    STATUS  current
    DESCRIPTION
    "GPS Status Attributes:
    staGpsChassis
        Identifies which chassis is being addressed
    stGpskSlot 
        Identifies which slot is being addressed
    staGpsMStatus
        Reports module status
    staGpsStatus 
        Reports gps input port status 
    staGpsPhaseA
        Reports phase value versus clock A in nano-seconds.
    staGpsPhaseB
        Reports phase value versus clock B in nano-seconds.
    staGpsUtc
        Reports number tells us whether the GPS module has UTC time or not.
    staGpsMtie1A
        Reports which MTIE limit 1 threshold was exceeded on clock A.
    staGpsMtie2A
        Reports which MTIE limit 2 threshold was exceeded on clock A.
    staGpsMtie1B
        Reports which MTIE limit 1 threshold was exceeded on clock B.
    staGpsMtie2B
        Reports which MTIE limit 2 threshold was exceeded on clock B.
    staGpsFreqA
        Reports input port frequency threshold exceeded on clock A.
    staGpsFreqB
        Reports input port frequency threshold exceeded on clock B.
    staGpsPpsSigma
        Reports sigma (statistical) calculation representing noise variation on the GPS 1PPS
    staGps3Sigma
        Reports 3sigma (statistical) calculation representing noise variation on the GPS 1PPS
    "
    INDEX   { staGpsChassis, staGpsSlot}
    ::= { staGpsTable 1 }


    StaGpsEntry ::=
        SEQUENCE {
            staGpsChassis
                INTEGER,    
            staGpsSlot
                INTEGER,    
            staGpsStatus
                INTEGER,
            staGpsPhaseA
                INTEGER,    
            staGpsPhaseB
                INTEGER,    
            staGpsUtc
                YesValue,
            staGpsMStatus
                INTEGER,

            -- MTIE THRESHOLD STATUS
            staGpsMtie1A
                INTEGER,
            staGpsMtie2A
                INTEGER,    
            staGpsMtie1B
                INTEGER,    
            staGpsMtie2B
                INTEGER,
                
            -- FREQUENCY THRESHOLD STATUS   
            staGpsFreqA
                OkValue,    
            staGpsFreqB
                OkValue,

            -- SIGMA Values 
            staGpsPpsSigma
                DisplayString,

            staGps3Sigma
                DisplayString
        }

    staGpsChassis OBJECT-TYPE
        SYNTAX  INTEGER (1..1)
        MAX-ACCESS  not-accessible
        STATUS  current
        DESCRIPTION
        "Identifies which chassis is being addressed. 
        This chassis number and slot number uniquely identify each inventory entry.

        Note: In the SSU2000, this number is always one. (i.e. in the main chassis)
        "
    ::= { staGpsEntry 1 }

    staGpsSlot OBJECT-TYPE
        SYNTAX  INTEGER (1..20)
        MAX-ACCESS  not-accessible
        STATUS  current
        DESCRIPTION
        "Identifies which slot position is being addressed. 
        This chassis number and slot number uniquely identify each inventory entry.

        Note: In the SSU2000, valid slots for GPS are slot 3 and slot 5.
        "
    ::= { staGpsEntry 2 }


    staGpsStatus OBJECT-TYPE
        SYNTAX  INTEGER
                {
                    ok(1),
                    selected(2),
                    disable(3),
                    fault(4),
                    reject(5)
                }
        MAX-ACCESS  read-only
        STATUS  current
        DESCRIPTION
        "The GPS port status.
        ok(1), -- module is enabled and operating without faults
        selected(2), -- module is enabled and selected as input reference
        disable(3), -- module is disabled
        fault(4), -- module is enabled and operating with faults
        reject(5) -- module is rejected due to antenna failure
        "
    ::= { staGpsEntry 3 }

    staGpsPhaseA OBJECT-TYPE
        SYNTAX  INTEGER (-1999999998..1999999998 | 1999999999)
        MAX-ACCESS  read-only
        STATUS  current
        DESCRIPTION
        "The phase value versus clock A.
        The phaseA is the current 1 second phase value in nanoseconds on clock A.
        The 1,999,999,999 is designated for invalid phase value.
        "
    ::= { staGpsEntry 4 }

    staGpsPhaseB OBJECT-TYPE
        SYNTAX  INTEGER (-1999999998..1999999998 | 1999999999)
        MAX-ACCESS  read-only
        STATUS  current
        DESCRIPTION
        "Reports phase value versus clock B.
        The phaseB is the current 1 second phase value in nanoseconds on clock B.
        The 1,999,999,999 is designated for invalid phase value.            
        "
    ::= { staGpsEntry 5 }

    staGpsUtc OBJECT-TYPE
        SYNTAX  YesValue
        MAX-ACCESS  read-only
        STATUS  current
        DESCRIPTION
        "Reports the GPS module has been set to UTC time (or not).
        1 = time is available
        2 = time is not available
        "
    ::= { staGpsEntry 6 }

    staGpsMStatus OBJECT-TYPE
        SYNTAX  INTEGER
                {
                    ok(1),
                    disable(2),
                    fault(3)
                }
        MAX-ACCESS  read-only
        STATUS  current
        DESCRIPTION
        "Reports the GPS module status.
        ok(1), -- module is enabled and operating normally
        disable(2), -- module is disabled
        fault(3) -- module is enabled, but not operational due to faults
        "
    ::= { staGpsEntry 7 }

    staGpsMtie1A OBJECT-TYPE
        SYNTAX  INTEGER 
                {
                    ok(1),
                    mtie10(10),
                    mtie100(100),
                    mtie1000(1000),
                    mtie10000(10000),
                    mtie100000(100000)
                }
        MAX-ACCESS  read-only
        STATUS  current
        DESCRIPTION
        "Reports which MTIE limit 1 threshold was exceeded on clock A.
        If ok, it means no error for MTIE limit 1 on clock A.
        If not, one of the 10/ 100/ 1000/ 10000/ 100000 seconds
        MTIE limit 1 threshold was exceeded on clock A.
        "
    ::= { staGpsEntry 8 }

    staGpsMtie2A OBJECT-TYPE
        SYNTAX  INTEGER 
                {
                    ok(1),
                    mtie10(10),
                    mtie100(100),
                    mtie1000(1000),
                    mtie10000(10000),
                    mtie100000(100000)
                }
        MAX-ACCESS  read-only
        STATUS  current
        DESCRIPTION
        "Reports which MTIE limit 2 threshold was exceeded on clock A.
        If ok, it means no error for MTIE limit 2 on clock A.
        If not, one of the 10/ 100/ 1000/ 10000/ 100000 seconds
        MTIE limit 2 threshold was exceeded on clock A.
        "
    ::= { staGpsEntry 9 }


    staGpsMtie1B OBJECT-TYPE
        SYNTAX  INTEGER 
                {
                    ok(1),
                    mtie10(10),
                    mtie100(100),
                    mtie1000(1000),
                    mtie10000(10000),
                    mtie100000(100000)
                }
        MAX-ACCESS  read-only
        STATUS  current
        DESCRIPTION
        "Reports which MTIE limit 1 threshold was exceeded on clock B.
        If ok, it means no error for MTIE limit 1 on clock B.
        If not, one of the 10/ 100/ 1000/ 10000/ 100000 seconds
        MTIE limit 1 threshold was exceeded on clock B.
        "
    ::= { staGpsEntry 10 }


    staGpsMtie2B OBJECT-TYPE
        SYNTAX  INTEGER 
                {
                    ok(1),
                    mtie10(10),
                    mtie100(100),
                    mtie1000(1000),
                    mtie10000(10000),
                    mtie100000(100000)
                }
        MAX-ACCESS  read-only
        STATUS  current
        DESCRIPTION
        "Reports which MTIE limit 2 threshold was exceeded on clock B.
        If ok, it means no error for MTIE limit 2 on clock B.
        If not, one of the 10/ 100/ 1000/ 10000/ 100000 seconds
        MTIE limit 2 threshold was exceeded on clock B.
        "
    ::= { staGpsEntry 11 }


    staGpsFreqA OBJECT-TYPE
        SYNTAX  OkValue
        MAX-ACCESS  read-only
        STATUS  current
        DESCRIPTION
        "Reports the input port frequency threshold exceeded on clock A.
        "
    ::= { staGpsEntry 12 }


    staGpsFreqB OBJECT-TYPE
        SYNTAX  OkValue
        MAX-ACCESS  read-only
        STATUS  current
        DESCRIPTION
        "Reports the input port frequency threshold exceeded on clock B.
        "
    ::= { staGpsEntry 13 }


    staGpsPpsSigma OBJECT-TYPE
        SYNTAX  DisplayString (SIZE (0..32))
        MAX-ACCESS  read-only 
        STATUS  current
        DESCRIPTION
        "Reports current 1 PPS Sigma.
        "
    ::= { staGpsEntry 14 }

    staGps3Sigma OBJECT-TYPE
        SYNTAX  DisplayString (SIZE (0..32))
        MAX-ACCESS  read-only 
        STATUS  current
        DESCRIPTION
        "Reports current 3 Sigma Threshold.
        "
    ::= { staGpsEntry 15 }

    -- ******************************************
    -- GPS ENGINE POSITION TABLE
    -- ******************************************

    stGpsPosTable OBJECT-TYPE
    SYNTAX  SEQUENCE OF StGpsPosEntry
    MAX-ACCESS  not-accessible
    STATUS  current
    DESCRIPTION
    "The GPS attributes that report the status of the GPS engine's position and status
    "
    ::= { statusGps 2 }


    stGpsPosEntry OBJECT-TYPE
    SYNTAX  StGpsPosEntry
    MAX-ACCESS  not-accessible
    STATUS  current
    DESCRIPTION
    "The GPS position attributes:
    stGpsPosChassis 
        Identifies which chassis is being addressed
    stGpsPosSlot 
        Identifies which slot is being addressed
    stGpsPosValid
        Reports if the GPS position is valid or not.
    stGpsPosLat
        Reports antenna latitude position of the GPS module.
    stGpsPosLon
        Reports antenna longitude position of the GPS module.
    stGpsPosHgt
        Reports antenna height (meter) position of the GPS module.
    stGpsPosAccurate
        Reports antenna position accuracy
    stGpsPosPdop
        Reports PDOP assigns a value of accuracy to the calculated position.
    stGpsPosAvg
        Reports position averaging value indicates how many position values are used to determine position. 
    "
    INDEX   { stGpsPosChassis, stGpsPosSlot}
    ::= { stGpsPosTable 1 }


    StGpsPosEntry ::=
        SEQUENCE {
            stGpsPosChassis
                INTEGER,    
            stGpsPosSlot
                INTEGER,    
            stGpsPosValid
                ValidValue, 
            stGpsPosLat
                TLatAndLon,
            stGpsPosLon
                TLatAndLon,
            stGpsPosHgt
                TAntHeight,
            stGpsPosAccurate
                INTEGER,
            stGpsPosPdop
                INTEGER,
            stGpsPosAvg
                INTEGER
        }

    stGpsPosChassis OBJECT-TYPE
        SYNTAX  INTEGER (1..1)
        MAX-ACCESS  not-accessible
        STATUS  current
        DESCRIPTION
        "Identifies which shelf is being addressed. 
        This chassis number and slot number uniquely identify each inventory entry.

        Note: In the SSU2000, this number is always one. (i.e. in the main chassis)
        "
    ::= { stGpsPosEntry 1 }

    stGpsPosSlot OBJECT-TYPE
        SYNTAX  INTEGER (1..20)
        MAX-ACCESS  not-accessible
        STATUS  current
        DESCRIPTION
        "Identifies which slot position is being addressed. 
        This chassis number and slot number uniquely identify each inventory entry.

        Note: In the SSU2000, valid slots for GPS are slot 3 and slot 5.
        "
    ::= { stGpsPosEntry 2 }

    stGpsPosValid OBJECT-TYPE
        SYNTAX  ValidValue
        MAX-ACCESS  read-only
        STATUS  current
        DESCRIPTION
        "Reports if the GPS position is valid or not.

        1 = valid
        2 = invalid
        "
    ::= { stGpsPosEntry 3 }

    stGpsPosLat OBJECT-TYPE
        SYNTAX  TLatAndLon
        MAX-ACCESS  read-only
        STATUS  current
        DESCRIPTION
        "Reports antenna latitude position of the GPS module.

        The format is +dd:mm:ss.ss or -dd:mm:ss.ss
        The latitude is +/- 90 deg.
        "
    ::= { stGpsPosEntry 4 }

    stGpsPosLon OBJECT-TYPE
        SYNTAX  TLatAndLon
        MAX-ACCESS  read-only
        STATUS  current
        DESCRIPTION
        "Reports antenna longitude position of the GPS module.

        The format is +dd:mm:ss.ss or -dd:mm:ss.ss
        The longitude is +/- 180 deg.
        "
    ::= { stGpsPosEntry 5 }

    stGpsPosHgt OBJECT-TYPE
        SYNTAX  TAntHeight
        MAX-ACCESS  read-only
        STATUS  current
        DESCRIPTION
        "Reports antenna height (meter) position of the GPS module.

        The format is +hh.hh or -hh.hh
        The height is +/- 10000.0 meters.
        "
    ::= { stGpsPosEntry 6 }

    stGpsPosAccurate OBJECT-TYPE
        SYNTAX  INTEGER
                {
                    approx (1),
                    d2 (2),
                    d3 (3)
                }
        MAX-ACCESS  read-only
        STATUS  current
        DESCRIPTION
        "Reports antenna position accuracy
        APPROX - position is not accurate
        D2 - position is accurate, 2D, height is not valid
        D3 - position is accurate, 3D, height is valid
        "
    ::= { stGpsPosEntry 7 }

    stGpsPosPdop OBJECT-TYPE
        SYNTAX  INTEGER (0..100)
        MAX-ACCESS  read-only
        STATUS  current
        DESCRIPTION
        "Reports PDOP indicates position precision as an integer representation of value in tenths.
        For example, the value 19 means 1.9 pdop.
        if zero, it means invalid.
        "
    ::= { stGpsPosEntry 8 }

    stGpsPosAvg OBJECT-TYPE
        SYNTAX  INTEGER (0..3600)
        MAX-ACCESS  read-only
        STATUS  current
        DESCRIPTION
        "Reports satellite position averaging value. 
        If zero, the satellite position is user entered.
        "
    ::= { stGpsPosEntry 9 }


    -- ******************************************
    -- GPS AVAILABILITY TABLE
    -- ******************************************

    stGpsAvailTable OBJECT-TYPE
    SYNTAX  SEQUENCE OF StGpsAvEntry
    MAX-ACCESS  not-accessible
    STATUS  current
    DESCRIPTION
        "A list of GPS satellite availability, reports the location of visible satellites.
        "
    ::= { statusGps 3 }


    stGpsAvEntry OBJECT-TYPE
    SYNTAX  StGpsAvEntry
    MAX-ACCESS  not-accessible
    STATUS  current
    DESCRIPTION
    "GPS Availability attributes:
    "
    INDEX   { stGpsAvChassis, stGpsAvSlot, stGpsAvChnl}
    ::= { stGpsAvailTable 1 }


    StGpsAvEntry ::=
        SEQUENCE {
            stGpsAvChassis
                INTEGER,    
            stGpsAvSlot
                INTEGER,    
            stGpsAvChnl
                INTEGER,    
            stGpsAvPNCode
                INTEGER,
            stGpsAvElevation
                INTEGER,
            stGpsAvAzimuth
                INTEGER,
            stGpsAvHealthy
                YesValue
        }


    stGpsAvChassis OBJECT-TYPE
        SYNTAX  INTEGER (1..1)
        MAX-ACCESS  not-accessible
        STATUS  current
        DESCRIPTION
        "Identifies which chassis is being addressed. 
        This chassis number and slot number uniquely identify each inventory entry.

        Note: In the SSU2000, this number is always one. (i.e. in the main chassis)
        "
    ::= { stGpsAvEntry 1 }

    stGpsAvSlot OBJECT-TYPE
        SYNTAX  INTEGER (1..20)
        MAX-ACCESS  not-accessible
        STATUS  current
        DESCRIPTION
        "Identifies which slot position is being addressed. 
        This chassis number and slot number uniquely identify each inventory entry.

        Note: In the SSU2000, valid slots for GPS are slot 3 and slot 5.
        "
    ::= { stGpsAvEntry 2 }

    stGpsAvChnl OBJECT-TYPE
        SYNTAX  INTEGER (1..32)
        MAX-ACCESS  not-accessible
        STATUS  current
        DESCRIPTION
        "Reports satellite channel number.
        "
    ::= { stGpsAvEntry 3 }

    stGpsAvPNCode OBJECT-TYPE
        SYNTAX  INTEGER (0..99)
        MAX-ACCESS  read-only
        STATUS  current
        DESCRIPTION
        "Reports satellite PN code.
        "
    ::= { stGpsAvEntry 4 }

    stGpsAvElevation OBJECT-TYPE
        SYNTAX  INTEGER (0..90)
        MAX-ACCESS  read-only
        STATUS  current
        DESCRIPTION
        "Reports calculated elevation (in degrees) of the satellite.
        "
    ::= { stGpsAvEntry 5 }

    stGpsAvAzimuth OBJECT-TYPE
        SYNTAX  INTEGER (0..360)
        MAX-ACCESS  read-only
        STATUS  current
        DESCRIPTION
        "Reports calculated Azimuth (in degrees) of the satellite.
        "
    ::= { stGpsAvEntry 6 }

    stGpsAvHealthy OBJECT-TYPE
        SYNTAX  YesValue
        MAX-ACCESS  read-only
        STATUS  current
        DESCRIPTION
        "Reports current health of the satellite.

        1 = healthy
        2 = unhealthy
        "
    ::= { stGpsAvEntry 7 }


    -- ******************************************
    -- GPS TRACKING TABLE
    -- ******************************************

    stGpsTrackTable OBJECT-TYPE
    SYNTAX  SEQUENCE OF StGpsTkEntry
    MAX-ACCESS  not-accessible
    STATUS  current
    DESCRIPTION
    "A list of GPS satellites being tracked show with visibility, signal strength, & health information. 
    "
    ::= { statusGps 5 }


    stGpsTkEntry OBJECT-TYPE
    SYNTAX  StGpsTkEntry
    MAX-ACCESS  not-accessible
    STATUS  current
    DESCRIPTION
    "A entry GPS attributes. 
    "
    INDEX   { stGpsTkChassis, stGpsTkSlot, stGpsTkChnl}
    ::= { stGpsTrackTable 1 }


    StGpsTkEntry ::=
        SEQUENCE {
            stGpsTkChassis
                INTEGER,    
            stGpsTkSlot
                INTEGER,    
            stGpsTkChnl
                INTEGER,    
            stGpsTkSv
                INTEGER,    
            stGpsTkSnr
                INTEGER,    
            stGpsTkStatus
                INTEGER 
        }

    stGpsTkChassis OBJECT-TYPE
        SYNTAX  INTEGER (1..1)
        MAX-ACCESS  not-accessible
        STATUS  current
        DESCRIPTION
        "Identifies which chassis is being addressed. 
        This chassis number and slot number uniquely identify each inventory entry.

        Note: In the SSU2000, this number is always one. (i.e. in the main chassis)
        "
    ::= { stGpsTkEntry 1 }

    stGpsTkSlot OBJECT-TYPE
        SYNTAX  INTEGER (1..20)
        MAX-ACCESS  not-accessible
        STATUS  current
        DESCRIPTION
        "Identifies which slot position is being addressed. 
        This chassis number and slot number uniquely identify each inventory entry.

        Note: In the SSU2000, valid slots for GPS are slot 3 and slot 5.
        "
    ::= { stGpsTkEntry 2 }

    stGpsTkChnl OBJECT-TYPE
        SYNTAX  INTEGER (1..32)
        MAX-ACCESS  not-accessible
        STATUS  current
        DESCRIPTION
        "Reports satellite channel number.
        "
    ::= { stGpsTkEntry 3 }

    stGpsTkSv OBJECT-TYPE
        SYNTAX  INTEGER (0 | 1..32)
        MAX-ACCESS  read-only
        STATUS  current
        DESCRIPTION
        "Reports satellite vehicle number being tracked.
        if zero, it is invalid
        "
    ::= { stGpsTkEntry 4 }

    stGpsTkSnr OBJECT-TYPE
        SYNTAX  INTEGER (0 | 1..255)
        MAX-ACCESS  read-only
        STATUS  current
        DESCRIPTION
        "Reports signal-to-noise ration number being reported
        if zero, it is invalid
        "
    ::= { stGpsTkEntry 5 }

    stGpsTkStatus OBJECT-TYPE
        SYNTAX  INTEGER
                {
                    src (1),    -- search
                    acq (2),    -- acquire
                    agc (3),    -- automatic gain control
                    frq (4),    -- frequency locking
                    cod (5),    -- code locking
                    msg (6),    -- messaging
                    tim (7),    -- setting time
                    eph (8),    -- retriving ephemeris data
                    ok  (9)     -- satellite being used in the timing solution

                }
        MAX-ACCESS  read-only
        STATUS  current
        DESCRIPTION
        "Reports tracking status.
        src (1), -- search
        acq (2), -- acquire
        agc (3), -- automatic gain control
        frq (4), -- frequency locking
        cod (5), -- code locking
        msg (6), -- messaging
        tim (7), -- setting time
        eph (8), -- retriving ephemeris data
        ok  (9)  -- satellite being used in the timing solution
        "
    ::= { stGpsTkEntry 6 }

    -- **************************************************************
    -- SSU2000 DS1/E1 INPUT MODULE STATUS GROUP
    -- **************************************************************

    staDs1E1InpTable OBJECT-TYPE
    SYNTAX  SEQUENCE OF StaDiEntry
    MAX-ACCESS  not-accessible
    STATUS  current
    DESCRIPTION
        "A list of DS1/E1 Input status entries. 
        "
    ::= { statusDs1E1Inp 2 }


    staDiEntry OBJECT-TYPE
    SYNTAX  StaDiEntry
    MAX-ACCESS  not-accessible
    STATUS  current
    DESCRIPTION
    "Input port status attributes.
    "
    INDEX   { staDiChassis, staDiSlot, staDiPort }
    ::= { staDs1E1InpTable 1 }

    StaDiEntry ::=
        SEQUENCE {
            staDiChassis
                INTEGER,    
            staDiSlot
                INTEGER,    
            staDiPort
                INTEGER,
                    
            staDiStatus
                INTEGER,    
            staDiPhaseA
                INTEGER,    
            staDiPhaseB
                INTEGER,    
            staDiPql
                INTEGER,    
            staDiPqlRcv
                YesValue,
                
            -- INPUT HARDWARE SIGNAL STATUS 
            staDiLOS
                OkValue,    
            staDiAIS
                OkValue,    
            staDiOOF
                OkValue,    
            staDiBPV
                OkValue,    
            staDiCRC
                OkValue,

            -- MTIE THRESHOLD STATUS
            staDiMtie1A
                INTEGER,
            staDiMtie2A
                INTEGER,    
            staDiMtie1B
                INTEGER,    
            staDiMtie2B
                INTEGER,
                
            -- FREQUENCY THRESHOLD STATUS   
            staDiFreqA
                OkValue,    
            staDiFreqB
                OkValue,
                
            -- INPUT SIGNAL ERROR/CLEAR COUNT   
            staLOSErCnt
                Counter32,  
            staLOSClCnt
                Counter32,  
            staAISErCnt
                Counter32,  
            staAISClCnt
                Counter32,  
            staOOFErCnt
                Counter32,  
            staOOFClCnt
                Counter32,  
            staBPVErCnt
                Counter32,  
            staBPVClCnt
                Counter32,  
            staCRCErCnt
                Counter32,  
            staCRCClCnt
                Counter32,
                    
            -- Module Status
            staDiMStatus
                INTEGER 
        }

    staDiChassis OBJECT-TYPE
        SYNTAX  INTEGER (1..1)
        MAX-ACCESS  not-accessible
        STATUS  current
        DESCRIPTION
        "Identifies which chassis is being addressed. 
        This chassis number, slot number, and port number uniquely identify each inventory entry.

        Note: In the SSU2000, this number is always one.
        (i.e. in the main chassis)
        "
    ::= { staDiEntry 1 }

    staDiSlot OBJECT-TYPE
        SYNTAX  INTEGER (1..20)
        MAX-ACCESS  not-accessible
        STATUS  current
        DESCRIPTION
        "Identifies which slot position is being addressed. 
        This chassis number, slot number, and port number uniquely identify each inventory entry.
        "
    ::= { staDiEntry 2 }


    staDiPort OBJECT-TYPE
        SYNTAX  INTEGER (1..3)
        MAX-ACCESS  not-accessible
        STATUS  current
        DESCRIPTION
        "Identifies which port is being addressed. 
        This chassis number, slot number, and port number uniquely identify each inventory entry.
        "
    ::= { staDiEntry 3 }


    staDiStatus OBJECT-TYPE
        SYNTAX  INTEGER
                {
                    ok(1),
                    selected(2),
                    disable(3),
                    fault(4)
                }
        MAX-ACCESS  read-only
        STATUS  current
        DESCRIPTION
        "Reports input port status.
        ok(1), -- port is enabled & operating without faults
        selected(2), -- port is selected as system reference
        disable(3), -- port is diabled
        fault(4) -- port is enabled & operating with fault(s)
        "
    ::= { staDiEntry 4 }

    staDiPhaseA OBJECT-TYPE
        SYNTAX  INTEGER (-1999999998..1999999998 | 1999999999)
        MAX-ACCESS  read-only
        STATUS  current
        DESCRIPTION
        "Reports input phase value versus clock A. 
        The phaseA is the current 1 second phase value in nanoseconds on clock A.

        The 1,999,999,999 is designated for invalid phase value.
        "
    ::= { staDiEntry 5 }

    staDiPhaseB OBJECT-TYPE
        SYNTAX  INTEGER (-1999999998..1999999998 | 1999999999)
        MAX-ACCESS  read-only
        STATUS  current
        DESCRIPTION
        "Reports input phase value versus clock B. 
        The phaseB is the current 1 second phase value in nanoseconds on clock B.

        The 1,999,999,999 is designated for invalid phase value.
        "
    ::= { staDiEntry 6 }

    staDiPql OBJECT-TYPE
        SYNTAX  INTEGER (0 | 1..16)
        MAX-ACCESS  read-only
        STATUS  current
        DESCRIPTION
        "Reports input port Priority Quality Level (PQL). 
        The PQL is the current stratum level (read or provisioned) being reported by the port.
        If zero, it is invalid.
        "
    ::= { staDiEntry 7 }

    staDiPqlRcv OBJECT-TYPE
        SYNTAX  YesValue
        MAX-ACCESS  read-only
        STATUS  current
        DESCRIPTION
        "Reports receiving Sync Status Message (SSM) for the input port state.

        1 = enabled
        2 = disabled
        "
    ::= { staDiEntry 8 }


    staDiLOS OBJECT-TYPE
        SYNTAX  OkValue
        MAX-ACCESS  read-only
        STATUS  current
        DESCRIPTION
        "Reports input port has LOS fault.
        "
    ::= { staDiEntry 9 }

    staDiAIS OBJECT-TYPE
        SYNTAX  OkValue
        MAX-ACCESS  read-only
        STATUS  current
        DESCRIPTION
        "Reports input port has AIS fault.
        "
    ::= { staDiEntry 10 }

    staDiOOF OBJECT-TYPE
        SYNTAX  OkValue
        MAX-ACCESS  read-only
        STATUS  current
        DESCRIPTION
        "Reports input port has OOF fault.
        "
    ::= { staDiEntry 11 }


    staDiBPV OBJECT-TYPE
        SYNTAX  OkValue
        MAX-ACCESS  read-only
        STATUS  current
        DESCRIPTION
        "Reports input port has BPV fault.
        "
    ::= { staDiEntry 12 }


    staDiCRC OBJECT-TYPE
        SYNTAX  OkValue
        MAX-ACCESS  read-only
        STATUS  current
        DESCRIPTION
        "Reports input port CRC fault.
        "
    ::= { staDiEntry 13 }


    staDiMtie1A OBJECT-TYPE
        SYNTAX  INTEGER 
                {
                    ok(1),
                    mtie10(10),
                    mtie100(100),
                    mtie1000(1000),
                    mtie10000(10000),
                    mtie100000(100000)
                }
        MAX-ACCESS  read-only
        STATUS  current
        DESCRIPTION
        "Reports which MTIE limit 1 threshold was exceeded versus clock A.

        If ok, it means no error for MTIE limit 1 on clock A.
        If not, one of the 10/ 100/ 1000/ 10000/ 100000 seconds
        MTIE limit 1 threshold was exceeded versus clock A.
        "
    ::= { staDiEntry 14 }

    staDiMtie2A OBJECT-TYPE
        SYNTAX  INTEGER 
                {
                    ok(1),
                    mtie10(10),
                    mtie100(100),
                    mtie1000(1000),
                    mtie10000(10000),
                    mtie100000(100000)
                }
        MAX-ACCESS  read-only
        STATUS  current
        DESCRIPTION
        "Reports which MTIE limit 2 threshold was exceeded versus clock A.

        If ok, it means no error for MTIE limit 2 versus clock A.
        If not, one of the 10/ 100/ 1000/ 10000/ 100000 seconds
        MTIE limit 2 threshold was exceeded versus clock A.
        "
    ::= { staDiEntry 15 }


    staDiMtie1B OBJECT-TYPE
        SYNTAX  INTEGER 
                {
                    ok(1),
                    mtie10(10),
                    mtie100(100),
                    mtie1000(1000),
                    mtie10000(10000),
                    mtie100000(100000)
                }
        MAX-ACCESS  read-only
        STATUS  current
        DESCRIPTION
        "Reports which MTIE limit 1 threshold was exceeded verus clock B.

        If ok, it means no error for MTIE limit 1 versus clock B.
        If not, one of the 10/ 100/ 1000/ 10000/ 100000 seconds
        MTIE limit 1 threshold was exceeded versus clock B.
        "
    ::= { staDiEntry 16 }


    staDiMtie2B OBJECT-TYPE
        SYNTAX  INTEGER 
                {
                    ok(1),
                    mtie10(10),
                    mtie100(100),
                    mtie1000(1000),
                    mtie10000(10000),
                    mtie100000(100000)
                }
        MAX-ACCESS  read-only
        STATUS  current
        DESCRIPTION
        "Reports which MTIE limit 2 threshold was exceeded versus clock B.

        If ok, it means no error for MTIE limit 2 versus clock B.
        If not, one of the 10/ 100/ 1000/ 10000/ 100000 seconds
        MTIE limit 2 threshold was exceeded versus clock B.
        "
    ::= { staDiEntry 17 }


    staDiFreqA OBJECT-TYPE
        SYNTAX  OkValue
        MAX-ACCESS  read-only
        STATUS  current
        DESCRIPTION
        "Reports input port frequency threshold exceeded versus clock A.
        "
    ::= { staDiEntry 18 }


    staDiFreqB OBJECT-TYPE
        SYNTAX  OkValue
        MAX-ACCESS  read-only
        STATUS  current
        DESCRIPTION
        "Reports input port frequency threshold exceeded versus clock B.
        "
    ::= { staDiEntry 19 }


    staLOSErCnt OBJECT-TYPE
        SYNTAX  Counter32
        MAX-ACCESS  read-only
        STATUS  current
        DESCRIPTION
        "Reports input port LOS error count.
        "
    ::= { staDiEntry 20 }


    staLOSClCnt OBJECT-TYPE
        SYNTAX  Counter32
        MAX-ACCESS  read-only
        STATUS  current
        DESCRIPTION
        "Reports input port LOS clear count.
        "
    ::= { staDiEntry 21 }


    staAISErCnt OBJECT-TYPE
        SYNTAX  Counter32
        MAX-ACCESS  read-only
        STATUS  current
        DESCRIPTION
        "Reports input port AIS error count.
        "
    ::= { staDiEntry 22 }


    staAISClCnt OBJECT-TYPE
        SYNTAX  Counter32
        MAX-ACCESS  read-only
        STATUS  current
        DESCRIPTION
        "Reports input port AIS clear count.
        "
    ::= { staDiEntry 23 }


    staOOFErCnt OBJECT-TYPE
        SYNTAX  Counter32
        MAX-ACCESS  read-only
        STATUS  current
        DESCRIPTION
        "Reports input port OOF error count.
        "
    ::= { staDiEntry 24 }


    staOOFClCnt OBJECT-TYPE
        SYNTAX  Counter32
        MAX-ACCESS  read-only
        STATUS  current
        DESCRIPTION
        "Reports input port OOF clear count.
        "
    ::= { staDiEntry 25 }


    staBPVErCnt OBJECT-TYPE
        SYNTAX  Counter32
        MAX-ACCESS  read-only
        STATUS  current
        DESCRIPTION
        "Reports input port BPV error count.
        "
    ::= { staDiEntry 26 }


    staBPVClCnt OBJECT-TYPE
        SYNTAX  Counter32
        MAX-ACCESS  read-only
        STATUS  current
        DESCRIPTION
        "Reports input port BPV clear count.
        "
    ::= { staDiEntry 27 }


    staCRCErCnt OBJECT-TYPE
        SYNTAX  Counter32
        MAX-ACCESS  read-only
        STATUS  current
        DESCRIPTION
        "Reports input port CRC error count.
        "
    ::= { staDiEntry 28 }


    staCRCClCnt OBJECT-TYPE
        SYNTAX  Counter32
        MAX-ACCESS  read-only
        STATUS  current
        DESCRIPTION
        "Reports input port CRC clear count.
        "
    ::= { staDiEntry 29 }


    staDiMStatus OBJECT-TYPE
        SYNTAX  INTEGER
                {
                    ok(1),
                    disable(2),
                    fault(3)
                }
        MAX-ACCESS  read-only
        STATUS  current
        DESCRIPTION
        "The input module status.
        ok(1), -- module is enabled and operating without faults
        disable(2), -- module is disabled
        fault(3) -- module is enabled and operating with fault(s)
        "
    ::= { staDiEntry 30 }

    -- **************************************************************
    -- SSU2000 COMPOSITE CLOCK INPUT MODULE STATUS GROUP
    -- **************************************************************

    staCcInpTable OBJECT-TYPE
    SYNTAX  SEQUENCE OF StaCiEntry
    MAX-ACCESS  not-accessible
    STATUS  current
    DESCRIPTION
        "A list of Composite Clock Input status information. 
        "
    ::= { statusCcInp 2 }


    staCiEntry OBJECT-TYPE
    SYNTAX  StaCiEntry
    MAX-ACCESS  not-accessible
    STATUS  current
    DESCRIPTION
    "Input port status attributes.
    "
    INDEX   { staCiChassis, staCiSlot, staCiPort }
    ::= { staCcInpTable 1 }

    StaCiEntry ::=
        SEQUENCE {
            staCiChassis
                INTEGER,    
            staCiSlot
                INTEGER,    
            staCiPort
                INTEGER,
                    
            staCiStatus
                INTEGER,    
            staCiPhaseA
                INTEGER,    
            staCiPhaseB
                INTEGER,    
                
            -- INPUT HARDWARE SIGNAL STATUS 
            staCiLOS
                OkValue,    
            staCiBPV
                OkValue,    
                
            -- INPUT SIGNAL ERROR/CLEAR COUNT   
            staCiLOSErCnt
                Counter32,  
            staCiLOSClCnt
                Counter32,  
            staCiBPVErCnt
                Counter32,  
            staCiBPVClCnt
                Counter32,  
            
            -- Module Status    
            staCiMStatus
                INTEGER
        }

    staCiChassis OBJECT-TYPE
        SYNTAX  INTEGER (1..1)
        MAX-ACCESS  not-accessible
        STATUS  current
        DESCRIPTION
        "Identifies which chassis is being addressed. 
        This chassis number, slot number, and port number uniquely identify each inventory entry.

        Note: In the SSU2000, this number is always one.
        (i.e. in the main chassis)
        "
    ::= { staCiEntry 1 }

    staCiSlot OBJECT-TYPE
        SYNTAX  INTEGER (1..20)
        MAX-ACCESS  not-accessible
        STATUS  current
        DESCRIPTION
        "Identifies which slot position is being addressed. 
        This chassis number, slot number, and port number uniquely identify each inventory entry.
        "
    ::= { staCiEntry 2 }


    staCiPort OBJECT-TYPE
        SYNTAX  INTEGER (1..3)
        MAX-ACCESS  not-accessible
        STATUS  current
        DESCRIPTION
        "Identifies which port is being addressed. 
        This chassis number, slot number, and port number uniquely identify each inventory entry.
        "
    ::= { staCiEntry 3 }


    staCiStatus OBJECT-TYPE
        SYNTAX  INTEGER
                {
                    ok(1),
                    selected(2),
                    disable(3),
                    fault(4)
                }
        MAX-ACCESS  read-only
        STATUS  current
        DESCRIPTION
        "Reports input port status.
        ok(1), -- port is enabled & operating without faults
        selected(2), -- port is selected as system reference
        disable(3), -- port is diabled
        fault(4) -- port is enabled & operating with fault(s)
        "
    ::= { staCiEntry 4 }

    staCiPhaseA OBJECT-TYPE
        SYNTAX  INTEGER (-1999999998..1999999998 | 1999999999)
        MAX-ACCESS  read-only
        STATUS  current
        DESCRIPTION
        "Reports input phase value versus clock A. 
        The phaseA is the current 1 second phase value in nanoseconds on clock A.

        The 1,999,999,999 is designated for invalid phase value.
        "
    ::= { staCiEntry 5 }

    staCiPhaseB OBJECT-TYPE
        SYNTAX  INTEGER (-1999999998..1999999998 | 1999999999)
        MAX-ACCESS  read-only
        STATUS  current
        DESCRIPTION
        "Reports input phase value versus clock B. 
        The phaseB is the current 1 second phase value in nanoseconds on clock B.

        The 1,999,999,999 is designated for invalid phase value.
        "
    ::= { staCiEntry 6 }

    staCiLOS OBJECT-TYPE
        SYNTAX  OkValue
        MAX-ACCESS  read-only
        STATUS  current
        DESCRIPTION
        "Reports input port has LOS fault.
        "
    ::= { staCiEntry 9 }

    staCiBPV OBJECT-TYPE
        SYNTAX  OkValue
        MAX-ACCESS  read-only
        STATUS  current
        DESCRIPTION
        "Reports input port has BPV fault.
        "
    ::= { staCiEntry 12 }

    staCiLOSErCnt OBJECT-TYPE
        SYNTAX  Counter32
        MAX-ACCESS  read-only
        STATUS  current
        DESCRIPTION
        "Reports input port LOS error count.
        "
    ::= { staCiEntry 14 }


    staCiLOSClCnt OBJECT-TYPE
        SYNTAX  Counter32
        MAX-ACCESS  read-only
        STATUS  current
        DESCRIPTION
        "Reports input port LOS clear count.
        "
    ::= { staCiEntry 15 }

    staCiBPVErCnt OBJECT-TYPE
        SYNTAX  Counter32
        MAX-ACCESS  read-only
        STATUS  current
        DESCRIPTION
        "Reports input port BPV error count.
        "
    ::= { staCiEntry 20 }


    staCiBPVClCnt OBJECT-TYPE
        SYNTAX  Counter32
        MAX-ACCESS  read-only
        STATUS  current
        DESCRIPTION
        "Reports input port BPV clear count.
        "
    ::= { staCiEntry 21 }

    staCiMStatus OBJECT-TYPE
        SYNTAX  INTEGER
                {
                    ok(1),
                    disable(2),
                    fault(3)
                }
        MAX-ACCESS  read-only
        STATUS  current
        DESCRIPTION
        "Reports input module status.
        ok(1), -- module is enabled and operating without faults
        disable(2), -- module is disabled
        fault(3) -- module is enabled and operating with fault(s)
        "
    ::= { staCiEntry 24 }

    -- **************************************************************
    -- SSU2000 SINE INPUT MODULE STATUS GROUP
    -- **************************************************************

    staSineInpTable OBJECT-TYPE
    SYNTAX  SEQUENCE OF StaSineiEntry
    MAX-ACCESS  not-accessible
    STATUS  current
    DESCRIPTION
    "A list of Sine Input status information.
    "
    ::= { statusSineInp 2 }


    staSineiEntry OBJECT-TYPE
    SYNTAX  StaSineiEntry
    MAX-ACCESS  not-accessible
    STATUS  current
    DESCRIPTION
    "Input port status attributes.
    "
    INDEX   { staSineiChassis, staSineiSlot, staSineiPort }
    ::= { staSineInpTable 1 }

    StaSineiEntry ::=
        SEQUENCE {
            staSineiChassis
                INTEGER,    
            staSineiSlot
                INTEGER,    
            staSineiPort
                INTEGER,
                    
            staSineiStatus
                INTEGER,    
            staSineiPhaseA
                INTEGER,    
            staSineiPhaseB
                INTEGER,    
                
            -- INPUT HARDWARE SIGNAL STATUS 
            staSineiLOS
                OkValue,    

            -- Module Status
            staSineiMStatus
                INTEGER,

            staSineiPql
                INTEGER,
                    
            -- MTIE THRESHOLD STATUS
            staSineiMtie1A
                INTEGER,
            staSineiMtie2A
                INTEGER,    
            staSineiMtie1B
                INTEGER,    
            staSineiMtie2B
                INTEGER,
                
            -- FREQUENCY THRESHOLD STATUS   
            staSineiFreqA
                OkValue,    
            staSineiFreqB
                OkValue                 
        }

    staSineiChassis OBJECT-TYPE
        SYNTAX  INTEGER (1..1)
        MAX-ACCESS  not-accessible
        STATUS  current
        DESCRIPTION
        "Identifies which chassis is being addressed. 
        This chassis number, slot number, and port number uniquely identify each inventory entry.

        Note: In the SSU2000, this number is always one.
        (i.e. in the main chassis)
        "
    ::= { staSineiEntry 1 }

    staSineiSlot OBJECT-TYPE
        SYNTAX  INTEGER (1..20)
        MAX-ACCESS  not-accessible
        STATUS  current
        DESCRIPTION
        "Identifies which slot position is being addressed. 
        This chassis number, slot number, and port number uniquely identify each inventory entry.
        "
    ::= { staSineiEntry 2 }


    staSineiPort OBJECT-TYPE
        SYNTAX  INTEGER (1..3)
        MAX-ACCESS  not-accessible
        STATUS  current
        DESCRIPTION
        "Identifies which port is being addressed. 
        This chassis number, slot number, and port number uniquely identify each inventory entry.
        "
    ::= { staSineiEntry 3 }


    staSineiStatus OBJECT-TYPE
        SYNTAX  INTEGER
                {
                    ok(1),
                    selected(2),
                    disable(3),
                    fault(4)
                }
        MAX-ACCESS  read-only
        STATUS  current
        DESCRIPTION
        "Reports input port status.
        ok(1), -- port is enabled & operating without faults
        selected(2), -- port is selected as system reference
        disable(3), -- port is diabled
        fault(4) -- port is enabled & operating with fault(s)
        "
    ::= { staSineiEntry 4 }

    staSineiPhaseA OBJECT-TYPE
        SYNTAX  INTEGER (-1999999998..1999999998 | 1999999999)
        MAX-ACCESS  read-only
        STATUS  current
        DESCRIPTION
        "Reports input phase value versus clock A. 
        The phaseA is the current 1 second phase value in nanoseconds on clock A.

        The 1,999,999,999 is designated for invalid phase value.
        "
    ::= { staSineiEntry 5 }

    staSineiPhaseB OBJECT-TYPE
        SYNTAX  INTEGER (-1999999998..1999999998 | 1999999999)
        MAX-ACCESS  read-only
        STATUS  current
        DESCRIPTION
        "Reports input phase value versus clock B. 
        The phaseB is the current 1 second phase value in nanoseconds on clock B.

        The 1,999,999,999 is designated for invalid phase value.
        "
    ::= { staSineiEntry 6 }

    staSineiLOS OBJECT-TYPE
        SYNTAX  OkValue
        MAX-ACCESS  read-only
        STATUS  current
        DESCRIPTION
        "Reports input port has LOS fault.
        "
    ::= { staSineiEntry 7 }

    staSineiMStatus OBJECT-TYPE
        SYNTAX  INTEGER
                {
                    ok(1),
                    disable(2),
                    fault(3)
                }
        MAX-ACCESS  read-only
        STATUS  current
        DESCRIPTION
        "Reports input module status.
        ok(1), -- module is enabled and operating without faults
        disable(2), -- module is disabled
        fault(3) -- module is enabled and operating with fault(s)
        "
    ::= { staSineiEntry 8 }

    staSineiPql OBJECT-TYPE
        SYNTAX  INTEGER (0 | 1..16)
        MAX-ACCESS  read-only
        STATUS  current
        DESCRIPTION
        "Reports input port Priority Quality Level (PQL). 
        The PQL is the current stratum level (read or provisioned) being reported by the port.
        If zero, it is invalid.
        "
    ::= { staSineiEntry 9 }

    staSineiMtie1A OBJECT-TYPE
        SYNTAX  INTEGER 
                {
                    ok(1),
                    mtie10(10),
                    mtie100(100),
                    mtie1000(1000),
                    mtie10000(10000),
                    mtie100000(100000)
                }
        MAX-ACCESS  read-only
        STATUS  current
        DESCRIPTION
        "Reports which MTIE limit 1 threshold was exceeded versus clock A.

        If ok, it means no error for MTIE limit 1 on clock A.
        If not, one of the 10/ 100/ 1000/ 10000/ 100000 seconds
        MTIE limit 1 threshold was exceeded versus clock A.
        "
    ::= { staSineiEntry 10 }

    staSineiMtie2A OBJECT-TYPE
        SYNTAX  INTEGER 
                {
                    ok(1),
                    mtie10(10),
                    mtie100(100),
                    mtie1000(1000),
                    mtie10000(10000),
                    mtie100000(100000)
                }
        MAX-ACCESS  read-only
        STATUS  current
        DESCRIPTION
        "Reports which MTIE limit 2 threshold was exceeded versus clock A.

        If ok, it means no error for MTIE limit 2 versus clock A.
        If not, one of the 10/ 100/ 1000/ 10000/ 100000 seconds
        MTIE limit 2 threshold was exceeded versus clock A.
        "
    ::= { staSineiEntry 11 }


    staSineiMtie1B OBJECT-TYPE
        SYNTAX  INTEGER 
                {
                    ok(1),
                    mtie10(10),
                    mtie100(100),
                    mtie1000(1000),
                    mtie10000(10000),
                    mtie100000(100000)
                }
        MAX-ACCESS  read-only
        STATUS  current
        DESCRIPTION
        "Reports which MTIE limit 1 threshold was exceeded verus clock B.

        If ok, it means no error for MTIE limit 1 versus clock B.
        If not, one of the 10/ 100/ 1000/ 10000/ 100000 seconds
        MTIE limit 1 threshold was exceeded versus clock B.
        "
    ::= { staSineiEntry 12 }


    staSineiMtie2B OBJECT-TYPE
        SYNTAX  INTEGER 
                {
                    ok(1),
                    mtie10(10),
                    mtie100(100),
                    mtie1000(1000),
                    mtie10000(10000),
                    mtie100000(100000)
                }
        MAX-ACCESS  read-only
        STATUS  current
        DESCRIPTION
        "Reports which MTIE limit 2 threshold was exceeded versus clock B.

        If ok, it means no error for MTIE limit 2 versus clock B.
        If not, one of the 10/ 100/ 1000/ 10000/ 100000 seconds
        MTIE limit 2 threshold was exceeded versus clock B.
        "
    ::= { staSineiEntry 13 }


    staSineiFreqA OBJECT-TYPE
        SYNTAX  OkValue
        MAX-ACCESS  read-only
        STATUS  current
        DESCRIPTION
        "Reports input port frequency threshold exceeded versus clock A.
        "
    ::= { staSineiEntry 14 }


    staSineiFreqB OBJECT-TYPE
        SYNTAX  OkValue
        MAX-ACCESS  read-only
        STATUS  current
        DESCRIPTION
        "Reports input port frequency threshold exceeded versus clock B.
        "
    ::= { staSineiEntry 15 }

    -- **************************************************************
    -- SSU2000 JAPANESE COMPOSITE CLOCK INPUT MODULE STATUS GROUP
    -- **************************************************************

    staJccInpTable OBJECT-TYPE
    SYNTAX  SEQUENCE OF StaJcciEntry
    MAX-ACCESS  not-accessible
    STATUS  current
    DESCRIPTION
        "A list of Composite Clock Input status information. 
        "
    ::= { statusJccInp 2 }


    staJcciEntry OBJECT-TYPE
    SYNTAX  StaJcciEntry
    MAX-ACCESS  not-accessible
    STATUS  current
    DESCRIPTION
    "Input port status attributes.
    "
    INDEX   { staCiChassis, staCiSlot, staCiPort }
    ::= { staJccInpTable 1 }

    StaJcciEntry ::=
        SEQUENCE {
            staJcciChassis
                INTEGER,    
            staJcciSlot
                INTEGER,    
            staJcciPort
                INTEGER,
                    
            staJcciStatus
                INTEGER,    
            staJcciPhaseA
                INTEGER,    
            staJcciPhaseB
                INTEGER,    
                
            -- INPUT HARDWARE SIGNAL STATUS 
            staJcciLOS
                OkValue,    
            staJcciBPV
                OkValue,    
            staJcci400Hz
                OnValue,
                
            -- Module Status    
            staJcciMStatus
                INTEGER 
        }

    staJcciChassis OBJECT-TYPE
        SYNTAX  INTEGER (1..1)
        MAX-ACCESS  not-accessible
        STATUS  current
        DESCRIPTION
        "Identifies which chassis is being addressed. 
        This chassis number, slot number, and port number uniquely identify each inventory entry.

        Note: In the SSU2000, this number is always one.
        (i.e. in the main chassis)
        "
    ::= { staJcciEntry 1 }

    staJcciSlot OBJECT-TYPE
        SYNTAX  INTEGER (1..20)
        MAX-ACCESS  not-accessible
        STATUS  current
        DESCRIPTION
        "Identifies which slot position is being addressed. 
        This chassis number, slot number, and port number uniquely identify each inventory entry.
        "
    ::= { staJcciEntry 2 }


    staJcciPort OBJECT-TYPE
        SYNTAX  INTEGER (1..3)
        MAX-ACCESS  not-accessible
        STATUS  current
        DESCRIPTION
        "Identifies which port is being addressed. 
        This chassis number, slot number, and port number uniquely identify each inventory entry.
        "
    ::= { staJcciEntry 3 }


    staJcciStatus OBJECT-TYPE
        SYNTAX  INTEGER
                {
                    ok(1),
                    selected(2),
                    disable(3),
                    fault(4)
                }
        MAX-ACCESS  read-only
        STATUS  current
        DESCRIPTION
        "Reports input port status.
        ok(1), -- port is enabled & operating without faults
        selected(2), -- port is selected as system reference
        disable(3),  -- port is diabled
        fault(4) -- port is enabled & operating with fault(s)
        "
    ::= { staJcciEntry 4 }

    staJcciPhaseA OBJECT-TYPE
        SYNTAX  INTEGER (-1999999998..1999999998 | 1999999999)
        MAX-ACCESS  read-only
        STATUS  current
        DESCRIPTION
        "Reports input phase value versus clock A. 
        The phaseA is the current 1 second phase value in nanoseconds on clock A.

        The 1,999,999,999 is designated for invalid phase value.
        "
    ::= { staJcciEntry 5 }

    staJcciPhaseB OBJECT-TYPE
        SYNTAX  INTEGER (-1999999998..1999999998 | 1999999999)
        MAX-ACCESS  read-only
        STATUS  current
        DESCRIPTION
        "Reports input phase value versus clock B. 
        The phaseB is the current 1 second phase value in nanoseconds on clock B.

        The 1,999,999,999 is designated for invalid phase value.
        "
    ::= { staJcciEntry 6 }

    staJcciLOS OBJECT-TYPE
        SYNTAX  OkValue
        MAX-ACCESS  read-only
        STATUS  current
        DESCRIPTION
        "Reports input port has LOS fault.
        "
    ::= { staJcciEntry 7 }

    staJcciBPV OBJECT-TYPE
        SYNTAX  OkValue
        MAX-ACCESS  read-only
        STATUS  current
        DESCRIPTION
        "Reports input port has BPV fault.
        "
    ::= { staJcciEntry 8 }

    staJcci400Hz OBJECT-TYPE
        SYNTAX  OnValue
        MAX-ACCESS  read-only
        STATUS  current
        DESCRIPTION
        "Reports input port has 400Hz Sync Signal or not.
        "
    ::= { staJcciEntry 9 }

    staJcciMStatus OBJECT-TYPE
        SYNTAX  INTEGER
                {
                    ok(1),
                    disable(2),
                    fault(3)
                }
        MAX-ACCESS  read-only
        STATUS  current
        DESCRIPTION
        "Reports input module status.
        ok(1), -- module is enabled and operating without faults
        disable(2), -- module is disabled
        fault(3) -- module is enabled and operating with fault(s)
        "
    ::= { staJcciEntry 10 }

    -- **************************************************************
    -- SSU2000 OUTPUT MODULE STATUS GROUP
    -- **************************************************************

    staOutTable OBJECT-TYPE
    SYNTAX  SEQUENCE OF StaOtEntry
    MAX-ACCESS  not-accessible
    STATUS  current
    DESCRIPTION
    "The list of Generic Output status information.
    "
    ::= { statusOut 2 }


    staOtEntry OBJECT-TYPE
    SYNTAX  StaOtEntry
    MAX-ACCESS  not-accessible
    STATUS  current
    DESCRIPTION
    "Output port status attributes.
    "
    INDEX   { staOtChassis, staOtSlot}
    ::= { staOutTable 1 }

    StaOtEntry ::=
        SEQUENCE {
            staOtChassis
                INTEGER,    
            staOtSlot
                INTEGER,    
            staOtStatus
                INTEGER,
            staOtClkSel
                INTEGER,
            staOtClka
                ActiveValue,
            staOtClkb
                ActiveValue,
            staOtClkc
                ActiveValue,
            staOtClkd
                ActiveValue,
            staOtRednt
                INTEGER,
            staOtPql
                INTEGER,
            staOtPortSta
                OCTET STRING
        }

    staOtChassis OBJECT-TYPE
        SYNTAX  INTEGER (1..5)
        MAX-ACCESS  not-accessible
        STATUS  current
        DESCRIPTION
        "Identifies which shelf is being addressed. 
        This chassis number and slot number uniquely identify each inventory entry.

        Note: The output module can reside on any chassis (1-5).
        "
    ::= { staOtEntry 1 }

    staOtSlot OBJECT-TYPE
        SYNTAX  INTEGER (1..20)
        MAX-ACCESS  not-accessible
        STATUS  current
        DESCRIPTION
        "Identifies which slot position is being addressed. 
        This chassis number and slot number uniquely identify each inventory entry.
        "
    ::= { staOtEntry 2 }


    staOtStatus OBJECT-TYPE
        SYNTAX  INTEGER
                {
                    ok(1),
                    disable(3),
                    fault(4),
                    reject(5)
                }
        MAX-ACCESS  read-only
        STATUS  current
        DESCRIPTION
        "Reports output port status.
        ok(1), -- modlule is enabled & operating without faults
        disable(3), -- module is diabled
        fault(4) -- module is enabled & operating with fault(s)
        reject(5) -- module type is mismatched with redundant module
        "
    ::= { staOtEntry 3 }

    staOtClkSel OBJECT-TYPE
        SYNTAX  INTEGER
                {
                    clka(1),
                    clkb(2),
                    clkc(3),
                    clkd(4),
                    none(5)
                }
        MAX-ACCESS  read-only
        STATUS  current
        DESCRIPTION
        "Reports which clock is selected for generating the output.
        clka(1), -- Clock A is selected as the Primary clock
        clkb(2), -- Clock B is selected as the Primary clock
        clkc(3), -- Clock C is selected as the Primary clock
        clkd(4), -- Clock D is selected as the Primary clock
        none(5) -- no clock is selected
        "
    ::= { staOtEntry 4 }

    staOtClka OBJECT-TYPE
        SYNTAX  ActiveValue
        MAX-ACCESS  read-only
        STATUS  current
        DESCRIPTION
        "Reports that clock A is available.
        "
    ::= { staOtEntry 5 }

    staOtClkb OBJECT-TYPE
        SYNTAX  ActiveValue
        MAX-ACCESS  read-only
        STATUS  current
        DESCRIPTION
        "Reports that clock B is available.
        "
    ::= { staOtEntry 6 }

    staOtClkc OBJECT-TYPE
        SYNTAX  ActiveValue
        MAX-ACCESS  read-only
        STATUS  current
        DESCRIPTION
        "Reports that clock C is available.
        "
    ::= { staOtEntry 7 }

    staOtClkd OBJECT-TYPE
        SYNTAX  ActiveValue
        MAX-ACCESS  read-only
        STATUS  current
        DESCRIPTION
            "Reports that clock D is available.
            "
    ::= { staOtEntry 8 }


    staOtRednt OBJECT-TYPE
        SYNTAX  INTEGER (0..20)
        MAX-ACCESS  read-only
        STATUS  current
        DESCRIPTION
        "Reports the adjacent slot number if this module is the output module redundant pair. 
        If this module is not redundant, zero is reported.
            "
    ::= { staOtEntry 9 }

    staOtPql OBJECT-TYPE
        SYNTAX  INTEGER (0 | 1..16)
        MAX-ACCESS  read-only
        STATUS  current
        DESCRIPTION
        "Reports the Priority Quality Level (PQL) being generated.
        If zero, it is invalid or Not Applicable.
        "
    ::= { staOtEntry 10 }

    staOtPortSta OBJECT-TYPE
        SYNTAX  OCTET STRING (SIZE (20))
        MAX-ACCESS  read-only
        STATUS  current
        DESCRIPTION
        "Reports the status for ports 1-20.
        1st digit represents port 1, 20th digit represents port 20
        1 = ok
        2 = not used
        3 = internal port fault
        4 = external port fault
        5 = fault
        6 = squelch
        "
    ::= { staOtEntry 11 }


    -- **************************************************************
    -- SSU2000 DS1 LRM MODULE STATUS GROUP
    -- **************************************************************
    staLrmMTable OBJECT-TYPE
    SYNTAX  SEQUENCE OF StaLrmMEntry
    MAX-ACCESS  not-accessible
    STATUS  current
    DESCRIPTION
    "A list of DS1 LRM module status information.
    "
    ::= { statusLrm 2 }


    staLrmMEntry OBJECT-TYPE
    SYNTAX  StaLrmMEntry
    MAX-ACCESS  not-accessible
    STATUS  current
    DESCRIPTION
    "DS1 LRM module status attributes.
    "
    INDEX   { staLrmMChassis, staLrmMSlot}
    ::= { staLrmMTable 1 }

    StaLrmMEntry ::=
        SEQUENCE {
            staLrmMChassis
                INTEGER,    
            staLrmMSlot
                INTEGER,    
            staLrmMStatus
                INTEGER,
            staLrmMRefSrc
                INTEGER,
            staLrmMCtaId
                INTEGER
        }

    staLrmMChassis OBJECT-TYPE
        SYNTAX  INTEGER (1..5)
        MAX-ACCESS  not-accessible
        STATUS  current
        DESCRIPTION
        "Identifies which shelf is being addressed. 
        This chassis number and slot number uniquely identify each inventory entry.

        Note: The output module can reside on any chassis (1-5).
        "
    ::= { staLrmMEntry 1 }

    staLrmMSlot OBJECT-TYPE
        SYNTAX  INTEGER (1..20)
        MAX-ACCESS  not-accessible
        STATUS  current
        DESCRIPTION
        "Identifies which slot position is being addressed. 
        This chassis number and slot number uniquely identify each inventory entry.
        "
    ::= { staLrmMEntry 2 }

    staLrmMStatus OBJECT-TYPE
        SYNTAX  INTEGER
                {
                    enable(1),
                    disable(2)
                }
        MAX-ACCESS  read-only
        STATUS  current
        DESCRIPTION
        "Reports the LRM module state.
        enable(1),  -- module is enabled
        disable(2), -- module is disabled
        "
    ::= { staLrmMEntry 3 }

    staLrmMRefSrc OBJECT-TYPE
        SYNTAX  INTEGER
                {
                    clka(1),
                    clkb(2),
                    clkc(3),
                    clkd(4),
                    none(5),
                    pllflt(6)
                }
        MAX-ACCESS  read-only
        STATUS  current
        DESCRIPTION
        "Reports which clock is selected for generating the output and status.
        clka(1), -- clock A is selected
        clkb(2), -- clock B is selected
        clkc(3), -- clock C is selected
        clkd(4), -- clock D is selected
        none(5), -- no clock is selected
        pllflt(6) -- clock selected, but module's clock PLL is unlocked
            "
    ::= { staLrmMEntry 4 }

    staLrmMCtaId OBJECT-TYPE
        SYNTAX  INTEGER
                {
                    dual(1),
                    quad(2),
                    none(3),
                    unknown(4)
                }
        MAX-ACCESS  read-only
        STATUS  current
        DESCRIPTION
        "Reports if CTA is installed or not, if installed it reports which type, 2 ports or quad (4) ports.
        If not installed, none is shown. 
        If id is not recognized, unknown is shown.
        "
    ::= { staLrmMEntry 5 }


    -- **************************************************************
    -- SSU2000 DS1 LRM PORT STATUS GROUP
    -- **************************************************************
    staLrmPTable OBJECT-TYPE
    SYNTAX  SEQUENCE OF StaLrmPEntry
    MAX-ACCESS  not-accessible
    STATUS  current
    DESCRIPTION
    "A list of DS1 LRM port status information.
    "
    ::= { statusLrm 3 }


    staLrmPEntry OBJECT-TYPE
    SYNTAX  StaLrmPEntry
    MAX-ACCESS  not-accessible
    STATUS  current
    DESCRIPTION
    "DS1 LRM module status attributes.
    "
    INDEX   { staLrmPChassis, staLrmPSlot, staLrmPPort}
    ::= { staLrmPTable 1 }

    StaLrmPEntry ::=
        SEQUENCE {
            staLrmPChassis
                INTEGER,    
            staLrmPSlot
                INTEGER,    
            staLrmPPort
                INTEGER,    
            staLrmPStatus
                INTEGER,
            staLrmPFrame
                INTEGER,
            staLrmPLos
                OkValue,
            staLrmPAis
                OkValue,
            staLrmPLof
                OkValue,
            staLrmPBpv
                OkValue,
            staLrmPSlip
                OkValue,
            staLrmPSlips
                Counter32,
            staLrmPLosSide2
                OkValue,
            staLrmPBpvTestTime
                Counter32,
            staLrmPBpv60SRate
                DisplayString,
            staLrmPBpv24HRate
                DisplayString,
            staLrmPBpvErrSecs
                Counter32,
            staLrmPBpvSevErrSecs
                Counter32,
            staLrmPBpvSevErrRatio
                DisplayString
        }

    staLrmPChassis OBJECT-TYPE
        SYNTAX  INTEGER (1..5)
        MAX-ACCESS  not-accessible
        STATUS  current
        DESCRIPTION
        "Identifies which chassis is being addressed. 
        This chassis number and slot number uniquely identify each inventory entry.

        Note: The output module can reside on any chassis (1-5).
        "
    ::= { staLrmPEntry 1 }

    staLrmPSlot OBJECT-TYPE
        SYNTAX  INTEGER (1..20)
        MAX-ACCESS  not-accessible
        STATUS  current
        DESCRIPTION
        "Identifies which chassis is being addressed. 
        This chassis number and slot number uniquely identify each inventory entry.
        "
    ::= { staLrmPEntry 2 }

    staLrmPPort OBJECT-TYPE
        SYNTAX  INTEGER (1..4)
        MAX-ACCESS  not-accessible
        STATUS  current
        DESCRIPTION
        "Identifies which port is being addressed. 
        This chassis number and slot number uniquely identify each inventory entry.
        "
    ::= { staLrmPEntry 3 }

    staLrmPStatus OBJECT-TYPE
        SYNTAX  INTEGER
                {
                    ok(1),      -- port is functioning
                    cut(2),     -- port is in cut-through mode
                    disable(3)  -- port is disabled
                }
        MAX-ACCESS  read-only
        STATUS  current
        DESCRIPTION
        "Reports LRM Port status.
		ok(1), -- port is functioning
		cut(2), -- port is in cut-through mode
		disable(3) -- port is disabled
        "
    ::= { staLrmPEntry 4 }

    staLrmPFrame OBJECT-TYPE
        SYNTAX  INTEGER
                {
                    d4(1),      -- D4 signal
                    esf(2),     -- ESF signal
                    none(3)     -- indicate Loss Of Frame
                }
        MAX-ACCESS  read-only
        STATUS  current
        DESCRIPTION
        "Reports LRM Port frame status.
		d4(1), -- D4 signal
		esf(2), -- ESF signal
		none(3) -- indicate Loss Of Frame
        "
    ::= { staLrmPEntry 5 }

    staLrmPLos OBJECT-TYPE
        SYNTAX  OkValue
        MAX-ACCESS  read-only
        STATUS  current
        DESCRIPTION
        "Reports LRM Port LOS status.
        "
    ::= { staLrmPEntry 6 }

    staLrmPAis OBJECT-TYPE
        SYNTAX  OkValue
        MAX-ACCESS  read-only
        STATUS  current
        DESCRIPTION
        "Reports LRM Port AIS status.
        "
    ::= { staLrmPEntry 7 }

    staLrmPLof OBJECT-TYPE
        SYNTAX  OkValue
        MAX-ACCESS  read-only
        STATUS  current
        DESCRIPTION
        "Reports LRM Port LOF status.
        "
    ::= { staLrmPEntry 8 }

    staLrmPBpv OBJECT-TYPE
        SYNTAX  OkValue
        MAX-ACCESS  read-only
        STATUS  current
        DESCRIPTION
        "Reports LRM Port BPV status.
        "
    ::= { staLrmPEntry 9 }

    staLrmPSlip OBJECT-TYPE
        SYNTAX  OkValue
        MAX-ACCESS  read-only
        STATUS  current
        DESCRIPTION
            "Reports LRM Port SLIP status.
            If over the past 24 hours period, the slip count exceeds the threshold, the slip alarm is set.
            "
    ::= { staLrmPEntry 10 }

    staLrmPSlips OBJECT-TYPE
        SYNTAX  Counter32
        MAX-ACCESS  read-only
        STATUS  current
        DESCRIPTION
            "Reports LRM Port slip counts.
            "
    ::= { staLrmPEntry 11 }

    staLrmPLosSide2 OBJECT-TYPE
        SYNTAX  OkValue
        MAX-ACCESS  read-only
        STATUS  current
        DESCRIPTION
        "Reports LRM Port LOS on SIDE2 status.
        "
    ::= { staLrmPEntry 12 }

    staLrmPBpvTestTime OBJECT-TYPE
        SYNTAX  Counter32
        MAX-ACCESS  read-only
        STATUS  current
        DESCRIPTION
        "Reports length of time (in seconds) the BPV has been under tested.
        "
    ::= { staLrmPEntry 13 }

    staLrmPBpv60SRate OBJECT-TYPE
        SYNTAX  DisplayString (SIZE (0..32))
        MAX-ACCESS  read-only
        STATUS  current
        DESCRIPTION
        "Reports BPV Error Rate per second in 60-second window.
        The format is an ascii text string in float number.
        "
    ::= { staLrmPEntry 14 }

    staLrmPBpv24HRate OBJECT-TYPE
        SYNTAX  DisplayString (SIZE (0..32))
        MAX-ACCESS  read-only
        STATUS  current
        DESCRIPTION
        "Reports BPV Error Rate per second in 86400-second (24 hours) window.
        The format is an ascii text string in float number.
        "
    ::= { staLrmPEntry 15 }

    staLrmPBpvErrSecs OBJECT-TYPE
        SYNTAX  Counter32
        MAX-ACCESS  read-only
        STATUS  current
        DESCRIPTION
        "Reports accumulated BPV Errored Seconds.
        "
    ::= { staLrmPEntry 16 }

    staLrmPBpvSevErrSecs OBJECT-TYPE
        SYNTAX  Counter32
        MAX-ACCESS  read-only
        STATUS  current
        DESCRIPTION
        "Reports accumulated BPV Severely Errored Seconds.
        "
    ::= { staLrmPEntry 17 }

    staLrmPBpvSevErrRatio OBJECT-TYPE
        SYNTAX  DisplayString (SIZE (0..32))
        MAX-ACCESS  read-only
        STATUS  current
        DESCRIPTION
        "Reports BPV Severely Error Ratio.
        The format is an ascii text string in float number.
        "
    ::= { staLrmPEntry 18 }


    -- **************************************************************
    -- SSU2000 E1 LRM MODULE STATUS GROUP
    -- **************************************************************
    staLrme1MTable OBJECT-TYPE
    SYNTAX  SEQUENCE OF StaLrme1MEntry
    MAX-ACCESS  not-accessible
    STATUS  current
    DESCRIPTION
    "A list of E1 LRM port status information.
    "
    ::= { statusLrmE1 2 }


    staLrme1MEntry OBJECT-TYPE
    SYNTAX  StaLrme1MEntry
    MAX-ACCESS  not-accessible
    STATUS  current
    DESCRIPTION
    "E1 LRM module status attributes.
    "
    INDEX   { staLrme1MChassis, staLrme1MSlot}
    ::= { staLrme1MTable 1 }

    StaLrme1MEntry ::=
        SEQUENCE {
            staLrme1MChassis
                INTEGER,    
            staLrme1MSlot
                INTEGER,    
            staLrme1MStatus
                INTEGER,
            staLrme1MRefSrc
                INTEGER,
            staLrme1MCtaId
                INTEGER
        }

    staLrme1MChassis OBJECT-TYPE
        SYNTAX  INTEGER (1..5)
        MAX-ACCESS  not-accessible
        STATUS  current
        DESCRIPTION
        "Identifies which chassis is being addressed. 
        This chassis number and slot number uniquely identify each inventory entry.

        Note: The output module can reside on any chassis (1-5).
        "
    ::= { staLrme1MEntry 1 }

    staLrme1MSlot OBJECT-TYPE
        SYNTAX  INTEGER (1..20)
        MAX-ACCESS  not-accessible
        STATUS  current
        DESCRIPTION
        "Identifies which slot is being addressed. 
        This chassis number and slot number uniquely identify each inventory entry.
        "
    ::= { staLrme1MEntry 2 }

    staLrme1MStatus OBJECT-TYPE
        SYNTAX  INTEGER
                {
                    enable(1),
                    disable(2)
                }
        MAX-ACCESS  read-only
        STATUS  current
        DESCRIPTION
        "Reports the LRM module state.
        enable(1),  -- module is enabled
        disable(2), -- module is disabled
        "
    ::= { staLrme1MEntry 3 }

    staLrme1MRefSrc OBJECT-TYPE
        SYNTAX  INTEGER
                {
                    clka(1),
                    clkb(2),
                    clkc(3),
                    clkd(4),
                    none(5),
                    pllflt(6)
                }
        MAX-ACCESS  read-only
        STATUS  current
        DESCRIPTION
        "Reports which clock is selected for generating the output and status.
        clka(1), -- clock A is selected
        clkb(2), -- clock B is selected
        clkc(3), -- clock C is selected
        clkd(4), -- clock D is selected
        none(5), -- no clock is selected
        pllflt(6) -- clock selected, but module's clock PLL is unlocked
		"
    ::= { staLrme1MEntry 4 }

    staLrme1MCtaId OBJECT-TYPE
        SYNTAX  INTEGER
                {
                    dual(1),
                    quad(2),
                    none(3),
                    unknown(4)
                }
        MAX-ACCESS  read-only
        STATUS  current
        DESCRIPTION
        "Reports if CTA is installed or not.
        If installed it reports which type, 2 ports or quad (4) ports.
        If not installed, none is shown. 
        If id is not recognized, unknown is shown.
        "
    ::= { staLrme1MEntry 5 }


    -- **************************************************************
    -- SSU2000 E1 LRM PORT STATUS GROUP
    -- **************************************************************
    staLrme1PTable OBJECT-TYPE
    SYNTAX  SEQUENCE OF StaLrme1PEntry
    MAX-ACCESS  not-accessible
    STATUS  current
    DESCRIPTION
    "A list of E1 LRM port status information.
    "
    ::= { statusLrmE1 3 }


    staLrme1PEntry OBJECT-TYPE
    SYNTAX  StaLrme1PEntry
    MAX-ACCESS  not-accessible
    STATUS  current
    DESCRIPTION
    "E1 LRM module status attributes.
    "
    INDEX   { staLrme1PChassis, staLrme1PSlot, staLrme1PPort}
    ::= { staLrme1PTable 1 }

    StaLrme1PEntry ::=
        SEQUENCE {
            staLrme1PChassis
                INTEGER,    
            staLrme1PSlot
                INTEGER,    
            staLrme1PPort
                INTEGER,    
            staLrme1PStatus
                INTEGER,
            staLrme1PFrame
                OnValue,
            staLrme1PLos
                OkValue,
            staLrme1PAis
                OkValue,
            staLrme1PLof
                OkValue,
            staLrme1PBpv
                OkValue,
            staLrme1PSlip
                OkValue,
            staLrme1PSlips
                Counter32,
            staLrme1PLosSide2
                OkValue,
            staLrme1PBpv60SRate
                DisplayString,
            staLrme1PBpv24HRate
                DisplayString,
            staLrme1PBpvErrSecs
                Counter32,
            staLrme1PBpvSevErrSecs
                Counter32,
            staLrme1PBpvSevErrRatio
                DisplayString
        }

    staLrme1PChassis OBJECT-TYPE
        SYNTAX  INTEGER (1..5)
        MAX-ACCESS  not-accessible
        STATUS  current
        DESCRIPTION
        "Identifies which chassis is being addressed. 
        This chassis number and slot number uniquely identify each inventory entry.

        Note: The output module can reside on any chassis (1-5).
        "
    ::= { staLrme1PEntry 1 }

    staLrme1PSlot OBJECT-TYPE
        SYNTAX  INTEGER (1..20)
        MAX-ACCESS  not-accessible
        STATUS  current
        DESCRIPTION
        "Identifies which slot is being addressed. 
        This chassis number and slot number uniquely identify each inventory entry.
        "
    ::= { staLrme1PEntry 2 }

    staLrme1PPort OBJECT-TYPE
        SYNTAX  INTEGER (1..4)
        MAX-ACCESS  not-accessible
        STATUS  current
        DESCRIPTION
        "Identifies which port is being addressed. 
        This chassis number and slot number uniquely identify each inventory entry.
        "
    ::= { staLrme1PEntry 3 }

    staLrme1PStatus OBJECT-TYPE
        SYNTAX  INTEGER
                {
                    ok(1),      -- port is functioning
                    cut(2),     -- port is in cut-through mode
                    disable(3)  -- port is disabled
                }
        MAX-ACCESS  read-only
        STATUS  current
        DESCRIPTION
        "Reports LRM Port status.
		ok(1), -- port is functioning
		cut(2), -- port is in cut-through mode
		disable(3) -- port is disabled
        "
    ::= { staLrme1PEntry 4 }

    staLrme1PFrame OBJECT-TYPE
        SYNTAX  OnValue
        MAX-ACCESS  read-only
        STATUS  current
        DESCRIPTION
        "Reports LRM Port frame status.
		cas(1), -- CAS signal
		ccs(2), -- CCS signal
		none(3) -- indicate Loss Of Frame
        "
    ::= { staLrme1PEntry 5 }

    staLrme1PLos OBJECT-TYPE
        SYNTAX  OkValue
        MAX-ACCESS  read-only
        STATUS  current
        DESCRIPTION
            "Reports LRM Port LOS status.
            "
    ::= { staLrme1PEntry 6 }

    staLrme1PAis OBJECT-TYPE
        SYNTAX  OkValue
        MAX-ACCESS  read-only
        STATUS  current
        DESCRIPTION
            "Reports LRM Port AIS status.
            "
    ::= { staLrme1PEntry 7 }

    staLrme1PLof OBJECT-TYPE
        SYNTAX  OkValue
        MAX-ACCESS  read-only
        STATUS  current
        DESCRIPTION
            "Reports LRM Port LOF status.
            "
    ::= { staLrme1PEntry 8 }

    staLrme1PBpv OBJECT-TYPE
        SYNTAX  OkValue
        MAX-ACCESS  read-only
        STATUS  current
        DESCRIPTION
            "Reports LRM Port BPV status.
            "
    ::= { staLrme1PEntry 9 }

    staLrme1PSlip OBJECT-TYPE
        SYNTAX  OkValue
        MAX-ACCESS  read-only
        STATUS  current
        DESCRIPTION
            "Reports LRM Port SLIP status.
            If over the past 24 hours period, the slip count exceeds the threshold, the slip alarm is set.
            "
    ::= { staLrme1PEntry 10 }

    staLrme1PSlips OBJECT-TYPE
        SYNTAX  Counter32
        MAX-ACCESS  read-only
        STATUS  current
        DESCRIPTION
            "Reports LRM Port slip counts.
            "
    ::= { staLrme1PEntry 11 }

    staLrme1PLosSide2 OBJECT-TYPE
        SYNTAX  OkValue
        MAX-ACCESS  read-only
        STATUS  current
        DESCRIPTION
            "Reports LRM Port LOS on SIDE2 status.
            "
    ::= { staLrme1PEntry 12 }

    staLrme1PBpv60SRate OBJECT-TYPE
        SYNTAX  DisplayString (SIZE (0..32))
        MAX-ACCESS  read-only
        STATUS  current
        DESCRIPTION
        "Reports length of time (in seconds) the BPV has been under tested.
        The format is an ascii text string in float number.
        "
    ::= { staLrme1PEntry 13 }

    staLrme1PBpv24HRate OBJECT-TYPE
        SYNTAX  DisplayString (SIZE (0..32))
        MAX-ACCESS  read-only
        STATUS  current
        DESCRIPTION
        "Reports BPV Error Rate per second in 86400-second (24 hours) window.
        The format is an ascii text string in float number.
        "
    ::= { staLrme1PEntry 14 }

    staLrme1PBpvErrSecs OBJECT-TYPE
        SYNTAX  Counter32
        MAX-ACCESS  read-only
        STATUS  current
        DESCRIPTION
        "Reports accumulated BPV Errored Seconds.
        "
    ::= { staLrme1PEntry 15 }

    staLrme1PBpvSevErrSecs OBJECT-TYPE
        SYNTAX  Counter32
        MAX-ACCESS  read-only
        STATUS  current
        DESCRIPTION
        "Reports accumulated BPV Severely Errored Seconds.
        "
    ::= { staLrme1PEntry 16 }

    staLrme1PBpvSevErrRatio OBJECT-TYPE
        SYNTAX  DisplayString (SIZE (0..32))
        MAX-ACCESS  read-only
        STATUS  current
        DESCRIPTION
        "Reports BPV Severely Error Ratio.
        The format is an ascii text string in float number.
        "
    ::= { staLrme1PEntry 17 }


    -- **************************************************************
    -- SSU2000 PACKETIME NTP MODULE STATUS GROUP
    -- **************************************************************

    staPtNtpTable OBJECT-TYPE
    SYNTAX  SEQUENCE OF StaPtNtpEntry
    MAX-ACCESS  not-accessible
    STATUS  current
    DESCRIPTION
    "A list of PackeTime NTP status information.
    "
    ::= { statusPtNtp 1 }


    staPtNtpEntry OBJECT-TYPE
    SYNTAX  StaPtNtpEntry
    MAX-ACCESS  not-accessible
    STATUS  current
    DESCRIPTION
    "PackeTime NTP status attributes.
    "
INDEX   { staPtNtpChassis, staPtNtpSlot}
    ::= { staPtNtpTable 1 }

    StaPtNtpEntry ::=
        SEQUENCE {
            staPtNtpChassis
                INTEGER,    
            staPtNtpSlot
                INTEGER,    
            staPtNtpStatus
                INTEGER,    
            staPtNtpClkSel
                INTEGER,
            staPtNtpClka
                ActiveValue,
            staPtNtpClkb
                ActiveValue,
            staPtNtpClkc
                ActiveValue,
            staPtNtpClkd
                ActiveValue,
            staPtNtpRednt
                INTEGER,
            staPtNtpModState
                INTEGER,
            staPtNtpPAState
                INTEGER,
            staPtNtpPBState
                INTEGER,
            staPtNtpTod
                OnValue,
            staPtNtpCommit
                INTEGER
        }

    staPtNtpChassis OBJECT-TYPE
        SYNTAX  INTEGER (1..5)
        MAX-ACCESS  not-accessible
        STATUS  current
        DESCRIPTION
        "Identifies which chassis is being addressed. 
        This chassis number and slot number uniquely identify each inventory entry.
        "
    ::= { staPtNtpEntry 1 }

    staPtNtpSlot OBJECT-TYPE
        SYNTAX  INTEGER (1..20)
        MAX-ACCESS  not-accessible
        STATUS  current
        DESCRIPTION
        "Identifies which slot position is being addressed. 
        This chassis number and slot number uniquely identify each inventory entry.
        "
    ::= { staPtNtpEntry 2 }


    staPtNtpStatus OBJECT-TYPE
        SYNTAX  INTEGER
                {
                    ok(1),
                    disable(3),
                    fault(4),
                    reject(5)
                }
        MAX-ACCESS  read-only
        STATUS  current
        DESCRIPTION
        "The PackeTime NTP module status.
        ok(1), -- module is enabled and operating without faults
        disable(3), -- module is disabled
        fault(4), -- module is enabled and operating with fault(s)
        reject(5) -- module type between redundant modules do not agree
        "
    ::= { staPtNtpEntry 3 }

    staPtNtpClkSel OBJECT-TYPE
        SYNTAX  INTEGER
                {
                    clka(1),
                    clkb(2),
                    clkc(3),
                    clkd(4),
                    none(5)
                }
        MAX-ACCESS  read-only
        STATUS  current
        DESCRIPTION
        "Reports which clock reference is selected to generate the output reference.
        clka(1), -- Clock A is selected as the Primary clock
        clkb(2), -- Clock B is selected as the Primary clock
        clkc(3), -- Clock C is selected as the Primary clock
        clkd(4), -- Clock D is selected as the Primary clock
        none(5) -- no clock is selected
        "
    ::= { staPtNtpEntry 4 }

    staPtNtpClka OBJECT-TYPE
        SYNTAX  ActiveValue
        MAX-ACCESS  read-only
        STATUS  current
        DESCRIPTION
        "Reports that clock A is available.
        "
    ::= { staPtNtpEntry 5 }

    staPtNtpClkb OBJECT-TYPE
        SYNTAX  ActiveValue
        MAX-ACCESS  read-only
        STATUS  current
        DESCRIPTION
        "Reports that clock B is available.
        "
    ::= { staPtNtpEntry 6 }

    staPtNtpClkc OBJECT-TYPE
        SYNTAX  ActiveValue
        MAX-ACCESS  read-only
        STATUS  current
        DESCRIPTION
        "Reports that clock C is available.
        "
    ::= { staPtNtpEntry 7 }

    staPtNtpClkd OBJECT-TYPE
        SYNTAX  ActiveValue
        MAX-ACCESS  read-only
        STATUS  current
        DESCRIPTION
        "Reports that clock D is available.
        "
    ::= { staPtNtpEntry 8 }

    staPtNtpRednt OBJECT-TYPE
        SYNTAX  INTEGER (0..20)
        MAX-ACCESS  read-only
        STATUS  current
        DESCRIPTION
        "Reports the adjacent slot number if this module is the redundant pair. 
        If this module is not redundant, zero is reported.
        "
    ::= { staPtNtpEntry 9 }

    staPtNtpModState OBJECT-TYPE
        SYNTAX  INTEGER
                {
                    active(1),
                    stdby(2),
                    fault(3),
                    stdalone(4)
                }
        MAX-ACCESS  read-only
        STATUS  current
        DESCRIPTION
        "Reports the current operational mode.
        active(1), --If the module is in redundant pair and selected, it shall return active.
        stdby(2), --If the module is in redundant pair but not selected, it shall return stdby (standby).
        fault(3), --If the module disabled, it will return fault.
        stdalone(4) --If the module is not redundant pair, it shall return stdalone (standalone).
        "
    ::= { staPtNtpEntry 10 }

    staPtNtpPAState OBJECT-TYPE
        SYNTAX  INTEGER
                {
                    active(1),
                    stdby(2),
                    fault(3),
                    stdalone(4)
                }
        MAX-ACCESS  read-only
        STATUS  current
        DESCRIPTION
        "Reports the current operational mode.
        active(1), --If service ports are bonded and selected, it shall return active.
        stdby(2), --If service ports are bonded but not selected, it shall return stdby (standby).
        fault(3), --Service port is faulted.
        stdalone(4) --If service ports are not bonded , it shall return stdalone (standalone).
        "
    ::= { staPtNtpEntry 11 }

    staPtNtpPBState OBJECT-TYPE
        SYNTAX  INTEGER
                {
                    active(1),
                    stdby(2),
                    fault(3),
                    stdalone(4)
                }
        MAX-ACCESS  read-only
        STATUS  current
        DESCRIPTION
        "Reports the current operational mode.
        active(1), --If service ports are bonded and selected, it shall return active.
        stdby(2), --If service ports are bonded but not selected, it shall return stdby (standby).
        fault(3), --Service port is faulted.
        stdalone(4) --If service ports are not bonded , it shall return stdalone (standalone).
        "
    ::= { staPtNtpEntry 12 }

    staPtNtpTod OBJECT-TYPE
        SYNTAX  OnValue
        MAX-ACCESS  read-only
        STATUS  current
        DESCRIPTION
        "Reports if the NTP Time of Day is valid or invalid.
        "
    ::= { staPtNtpEntry 13 }

    staPtNtpCommit OBJECT-TYPE
        SYNTAX  INTEGER
                {
                    done(1),
                    prog(2)
                }
        MAX-ACCESS  read-only
        STATUS  current
        DESCRIPTION
        "Reports the Commit command status.
        1 = done
        2 = in progress
        "
    ::= { staPtNtpEntry 14 }


    -- **************************************************************
    -- **************************************************************
    -- SSU2000 SETUP GROUP
    -- **************************************************************
    -- **************************************************************


    -- **************************************************************
    -- SSU2000 COMMUNICATION MODULE SETUP GROUP
    -- **************************************************************

    setCmId OBJECT-TYPE
        SYNTAX  DisplayString (SIZE (7))
        MAX-ACCESS  read-only 
        STATUS  current
        DESCRIPTION
        "The system identifier, the value is always 'SSU2000'.
        "
    ::= { setupCom 1 }

    setCmInfo OBJECT-TYPE
        SYNTAX  DisplayString (SIZE (0..255))
        MAX-ACCESS  read-only 
        STATUS  current
        DESCRIPTION
        "Symmetricom contact information.
        This displays the Symmetricom address, phone, and fax numbers.
        "
    ::= { setupCom 2 }

    setCmVer OBJECT-TYPE
        SYNTAX  DisplayString (SIZE (0..100))
        MAX-ACCESS  read-only 
        STATUS  current
        DESCRIPTION
        "Reports Communication module's software version
        "
    ::= { setupCom 3 }

    setCmName OBJECT-TYPE
        SYNTAX  DisplayString (SIZE (1..20))
        MAX-ACCESS  read-write 
        STATUS  current
        DESCRIPTION
        "Set the user assigned name for the SSU2000.

        Note: Use caution when changing this, TL1 sessions use the unit name as the target id (tid).
        "
    ::= { setupCom 4 }



    -- **************************************************************
    -- SSU2000 CLOCK MODULE SETUP GROUP
    -- **************************************************************

    setClkTable OBJECT-TYPE
    SYNTAX  SEQUENCE OF SetCkEntry
    MAX-ACCESS  not-accessible
    STATUS  current
    DESCRIPTION
    "A list of clock status and setting information.
    "
    ::= { setupClk 1 }


    setCkEntry OBJECT-TYPE
    SYNTAX  SetCkEntry
    MAX-ACCESS  not-accessible
    STATUS  current
	DESCRIPTION
    "Clock status and setting attributes.
    "
    INDEX   { setCkChassis, setCkSlot}
    ::= { setClkTable 1 }

    SetCkEntry ::=
        SEQUENCE {
            setCkChassis
                INTEGER,    
            setCkSlot
                INTEGER,    
            setCkWarmup
                INTEGER,    
            setCkMinTau
                INTEGER,    
            setCkMaxTau
                INTEGER,    
            setCkPLLMode
                INTEGER,
            setCkTodTimeout                 
                INTEGER,
            setCkFreqTimeout                 
                INTEGER
        }

    setCkChassis OBJECT-TYPE
        SYNTAX  INTEGER (1..5)
        MAX-ACCESS  not-accessible
        STATUS  current
        DESCRIPTION
        "Identifies which chassis is being addressed. 
        This chassis number and slot number uniquely identify each inventory entry.

        Note: In the SSU2000, this number is always one. (i.e. in the main chassis)
        "
    ::= { setCkEntry 1 }

    setCkSlot OBJECT-TYPE
        SYNTAX  INTEGER (1..20)
        MAX-ACCESS  not-accessible
        STATUS  current
        DESCRIPTION
        "Identifies which slot is being addressed. 
        This slot number and chassis number uniquely identify each inventory entry.

        Note: In the SSU2000, valid slots for Clocks are slot 1 and slot 12.
        "
    ::= { setCkEntry 2 }

    setCkWarmup OBJECT-TYPE
        SYNTAX  INTEGER (900..3600)
        MAX-ACCESS  read-write
        STATUS  current
        DESCRIPTION
        "Set the clock warmup time in seconds.
        "
    ::= { setCkEntry 3 }


    setCkMinTau OBJECT-TYPE
        SYNTAX  INTEGER (150..10000)
        MAX-ACCESS  read-write
        STATUS  current
        DESCRIPTION
        "Set the clock minimum tau. 
        The mintau is the starting time constant value during Locked mode.
        "
    ::= { setCkEntry 4 }

    setCkMaxTau OBJECT-TYPE
        SYNTAX  INTEGER (150..10000)
        MAX-ACCESS  read-write
        STATUS  current
        DESCRIPTION
        "Set the clock max tau. 
        The maxtau is the final time constant value during Locked mode.
        "
    ::= { setCkEntry 5 }


 
    setCkPLLMode OBJECT-TYPE
        SYNTAX  INTEGER
                {
                    acq(2),
                    lock(3),
                    hold(4)
                }
        MAX-ACCESS  read-write
        STATUS  current
        DESCRIPTION
        "Set the clock operating mode to ACQ/ LOCK/ HOLD.
         Note: When WRITE is to request Clock to change its operating mode, but
           when READ, it returns status of current operating mode. If current is 
		   operating mode is Warmup, it will return as HOLD.
        "
    ::= { setCkEntry 6 }

    setCkTodTimeout OBJECT-TYPE
        SYNTAX  INTEGER (60..10000)
        MAX-ACCESS  read-write
        STATUS  current
        DESCRIPTION
        "Set the TODSRC Timeout. 
        The TOD Traceability Timeout shall allow the system to operate without a valid 
        TOD source for some amount of time before indicating the ToD source is invalid.  
        The timer shall have a user settable range from 60 to 10000 minutes,  
        with a default value of 1440.           
        "
    ::= { setCkEntry 7 }

    setCkFreqTimeout OBJECT-TYPE
        SYNTAX  INTEGER (60..10000)
        MAX-ACCESS  read-write
        STATUS  current
        DESCRIPTION
        "Set the Frequency Timeout. 
        The Frequency Traceability Timeout shall allow the system to operate without a valid 
        input reference for some amount of time before indicating the frequency source is invalid.  
        The timer shall have a user settable range from 60 to 10000 minutes,  
        with a default value of 1440.           
        "
    ::= { setCkEntry 8 }


    -- **************************************************************
    -- SSU2000 GPS MODULE SETUP GROUP
    -- **************************************************************

    setGpsTable OBJECT-TYPE
    SYNTAX  SEQUENCE OF SetGpsEntry
    MAX-ACCESS  not-accessible
    STATUS  current
    DESCRIPTION
        "A list of GPS status and setting information.
        "
    ::= { setupGps 1 }

    setGpsEntry OBJECT-TYPE
    SYNTAX  SetGpsEntry
    MAX-ACCESS  not-accessible
    STATUS  current
    DESCRIPTION
    "GPS status and setting attributes.
    "
    INDEX   { setGpsChassis, setGpsSlot}
    ::= { setGpsTable 1 }


    SetGpsEntry ::=
        SEQUENCE {
            setGpsChassis
                INTEGER,    
            setGpsSlot
                INTEGER,
            setGpsEngine
                INTEGER,
            setGpsProvPql
                INTEGER,
            setGpsPriority
                INTEGER,
            setGpsPdop
                INTEGER,
            setGpsPosel
                INTEGER,
            setGpsTimel
                INTEGER,
            setGpsAvg
                INTEGER,
            setGpsLat
                TLatAndLon,
            setGpsLon
                TLatAndLon,
            setGpsHgt
                TAntHeight,
            setGpsZeroPhase
                INTEGER,
            setGpsTodsrcPriority
                INTEGER,
            setGpsTodsrcCompensation
                INTEGER,
            setGnssConsMode
                INTEGER    
        }

    setGpsChassis OBJECT-TYPE
        SYNTAX  INTEGER (1..1)
        MAX-ACCESS  not-accessible
        STATUS  current
        DESCRIPTION
        "Identifies which chassis is being addressed. 
        This chassis number and slot number uniquely identify each inventory entry.

        Note: In the SSU2000, this number is always one. (i.e. in the main chassis)
        "
    ::= { setGpsEntry 1 }

    setGpsSlot OBJECT-TYPE
        SYNTAX  INTEGER (1..20)
        MAX-ACCESS  not-accessible
        STATUS  current
        DESCRIPTION
        "Identifies which slot position is being addressed. 
        This chassis number and slot number uniquely identify each inventory entry.

        Note: In the SSU2000, valid slots for GPS are slot 3 and slot 5.
        "
    ::= { setGpsEntry 2 }

    setGpsEngine OBJECT-TYPE
        SYNTAX  INTEGER
                {
                    na(1),
                    unknown(2),
                    mot(3),
                    nvs(4)
                }
        MAX-ACCESS  read-only
        STATUS  current
        DESCRIPTION
        "Reports the GPS engine manufacturer.
        na(1), -- not available
        unknown(2), -- unknown
        mot(3) -- motorola (or motorola compatible)
        nvs(4) -- NVS engine (or GLONASS compatible)
        "
    ::= { setGpsEntry 3 }

    setGpsProvPql OBJECT-TYPE
        SYNTAX  INTEGER (1..9)
        MAX-ACCESS  read-write
        STATUS  current
        DESCRIPTION
        "Set the input port provisioned Priority Quality Level (PQL) value.
        Note: Valid values are 1 - 9.
        "
    ::= { setGpsEntry 4 }


    setGpsPriority OBJECT-TYPE
        SYNTAX  INTEGER (0..10)
        MAX-ACCESS  read-write
        STATUS  current
        DESCRIPTION
        "Set the input port priority level.
        The 0 is for monitor-only mode. 
        The 1 is the highest priority.
        The 10 is the lowest priority.
        "
    ::= { setGpsEntry 5 }

    setGpsPdop OBJECT-TYPE
        SYNTAX  INTEGER (3..10)
        MAX-ACCESS  read-write
        STATUS  current
        DESCRIPTION
        "Set the PDOP mask [3 to 10].
        "
    ::= { setGpsEntry 6 }

    setGpsPosel OBJECT-TYPE
        SYNTAX  INTEGER (0..90)
        MAX-ACCESS  read-write
        STATUS  current
        DESCRIPTION
        "Set the minimum satellite elevation mask for positioning [0 to 90 deg].
        "
    ::= { setGpsEntry 7 }

    setGpsTimel OBJECT-TYPE
        SYNTAX  INTEGER (0..90)
        MAX-ACCESS  read-write
        STATUS  current
        DESCRIPTION
        "Set the minimum satellite elevation mask for timing [0 to 90 deg].
        "
    ::= { setGpsEntry 8 }

    setGpsAvg OBJECT-TYPE
        SYNTAX  INTEGER (20..3600)
        MAX-ACCESS  read-write
        STATUS  current
        DESCRIPTION
        "Set satellite position averaging value [20-3600].
		Mot GPS:  (20 - 3600) of averages for the calculated position fixes
		NVS GNSS: (20 - 1440) of averaging minutes
        "
    ::= { setGpsEntry 9 }

    setGpsLat OBJECT-TYPE
        SYNTAX  TLatAndLon
        MAX-ACCESS  read-write
        STATUS  current
        DESCRIPTION
        "Set the antenna latitude of the GPS antenna.

        The format is +dd:mm:ss.ss or -dd:mm:ss.ss
        The latitude is +/- 90 deg.
        "
    ::= { setGpsEntry 10 }

    setGpsLon OBJECT-TYPE
        SYNTAX  TLatAndLon
        MAX-ACCESS  read-write
        STATUS  current
        DESCRIPTION
        "Set the antenna longitude of the GPS antenna.

        The format is +dd:mm:ss.ss or -dd:mm:ss.ss
        The longitude  is +/- 180 deg.
        "
    ::= { setGpsEntry 11 }

    setGpsHgt OBJECT-TYPE
        SYNTAX  TAntHeight
        MAX-ACCESS  read-write
        STATUS  current
        DESCRIPTION
        "Set the antenna height (meter) of the GPS antenna.

        The format is +hh.hh or -hh.hh
        The height is +/- 10000.0 meters.
        "
    ::= { setGpsEntry 12 }


    setGpsZeroPhase OBJECT-TYPE
        SYNTAX  INTEGER
                {
                    zeroPhA(1),
                    zeroPhB(2),
                    zeroPhAB(3)
                }
        MAX-ACCESS  read-write
        STATUS  current
        DESCRIPTION
        "Set phase error to zero for this GPS port.
        ZEROPHA - set phase A error to zero,
        ZEROPHB - set phase B error to zero,
        ZEROPHAB - set phase A and B to zero.

        Note: This field only is meaningful during the write operation.
        "
    ::= { setGpsEntry 13 }


    setGpsTodsrcPriority OBJECT-TYPE
        SYNTAX  INTEGER (0..8)
        MAX-ACCESS  read-write
        STATUS  current
        DESCRIPTION
            "Set the TODSRC (Time-Of-Day Source) priority.
            The priority is the for the specified module as the TOD Source, default is 0, range can be 0 through 8. 
            Value 1 is the highest and 8 is the lowest. 
            If the value is zero, the specified module cannot be TOD Source.
            "
    ::= { setGpsEntry 14 }

    setGpsTodsrcCompensation OBJECT-TYPE
        SYNTAX  INTEGER (0..250)
        MAX-ACCESS  read-write
        STATUS  current
        DESCRIPTION
        "Set the Antenna cable delay compensation {0 - 250} in the case of GPS 
        TOD Source(s) or the delay induced by the cable(s) used to connect 
        expansion shelves where the PackeTime ToD Source(s) is located in 
        relationship to the Main shelf. The time offset shall have a 100nS 
        resolution, thus the Delay value shall be multiplied by 100nS to 
        provide 1PPS compensation. 

        Valid user compensation values range is 0 thru 250 for a total compensation range of 0 to 25000nS (25uS). 
        "
    ::= { setGpsEntry 15 }
    
    setGnssConsMode OBJECT-TYPE
        SYNTAX  INTEGER
                {
                    gps(1),
                    glonass(2),
                    gpsGlonass(3)
                }
        MAX-ACCESS  read-write
        STATUS  current
        DESCRIPTION
        "Set constellation mode of GNSS engine.
        gps(1), -- The constellation mode of gnss engine is gps.
        glonass(2), -- The constellation mode of gnss engine is glonass
        gpsGlonass(3), -- The constellation mode of gnss engine is gps+glonass.
        "
    ::= { setGpsEntry 16 }

    -- ******************************************
    -- GPS INPUT ALARM THRESHOLD SETTING
    -- ******************************************

    setAlmThGpsInpTable OBJECT-TYPE
    SYNTAX  SEQUENCE OF SetMgEntry
    MAX-ACCESS  not-accessible
    STATUS  current
    DESCRIPTION
        "A list of GPS input alarm attribute setup information. 
        "
    ::= { setupGps 2 }


    setMgEntry OBJECT-TYPE
    SYNTAX  SetMgEntry
    MAX-ACCESS  not-accessible
    STATUS  current
    DESCRIPTION
    "Input alarm attributes and settings.
    setMgChassis
        Identifies which chassis is being addressed. 
    setMgSlot
        Identifies which slot position is being addressed. 
    setMgMtieStd
        Set the input port setting of the MTIE limits to predefined values.
    setMgMtie10EL1
        Set the input port MTIE 10 seconds error threshold for the first limit setting.
    setMgMtie10EL2
        Set the input port MTIE 10 seconds error threshold for the second limit setting.
    setMgMtie10CL1
        Set the input port MTIE 10 seconds clear threshold for the first limit setting.
    setMgMtie10CL2
        Set the input port MTIE 10 seconds clear threshold for the second limit setting.
    setMgMtie100EL1
        Set the input port MTIE 100 seconds error threshold for the first limit setting.
    setMgMtie100EL2
        Set the input port MTIE 100 seconds error threshold for the second limit setting.
    setMgMtie100CL1
        Set the input port MTIE 100 seconds clear threshold for the first limit setting.
    setMgMtie100CL2
        Set the input port MTIE 100 seconds clear threshold for the second limit setting.
    setMgMtie1000EL1
        Set the input port MTIE 1000 seconds error threshold for the first limit setting.
    setMgMtie1000EL2
        Set the input port MTIE 1000 seconds error threshold for the second limit setting.
    setMgMtie1000CL1
        Set the input port MTIE 1000 seconds clear threshold for the first limit setting.
    setMgMtie1000CL2
        Set the input port MTIE 1000 seconds clear threshold for the second limit setting.
    setMgMtie10000EL1
        Set the input port MTIE 10000 seconds error threshold for the first limit setting.
    setMgMtie10000EL2
        Set the input port MTIE 10000 seconds error threshold for the second limit setting.
    setMgMtie10000CL1
        Set the input port MTIE 10000 seconds clear threshold for the first limit setting.
    setMgMtie10000CL2
        Set the input port MTIE 10000 seconds clear threshold for the second limit setting.
    setMgMtie100000EL1
        Set the input port MTIE 100000 seconds error threshold for the first limit setting.
    setMgMtie100000EL2
        Set the input port MTIE 100000 seconds error threshold for the second limit setting.
    setMgMtie100000CL1
        Set the input port MTIE 100000 seconds clear threshold for the first limit setting.
    setMgMtie100000CL2
        Set the input port MTIE 100000 seconds clear threshold for the second limit setting.
    setMgFreqAErrLmt
        Set the input port frequency error threshold for clock A.
    setMgFreqAClrLmt
        Set the input port frequency clear threshold for clock A.
    setMgFreqATau
        Set the Time constant (tau), in seconds, used for the calculation of the Average Frequency versus clock A.
    setMgFreqBErrLmt
        Set the input port frequency error threshold for clock B.
    setMgFreqBClrLmt
        Set the input port frequency clear threshold for clock B.
    setMgFreqBTau
        Set the Time constant (tau), in seconds, used for the calculation of the Average Frequency versus clock B.
    "
    INDEX   { setMgChassis, setMgSlot }
    ::= { setAlmThGpsInpTable 1 }


    SetMgEntry ::=
        SEQUENCE {
            setMgChassis
                INTEGER,    
            setMgSlot
                INTEGER,    
            
            -- MTIE Threshold Setting
            setMgMtieStd
                INTEGER,

            setMgMtie10EL1
                INTEGER,
            setMgMtie10EL2
                INTEGER,
            setMgMtie10CL1
                INTEGER,
            setMgMtie10CL2
                INTEGER,

            setMgMtie100EL1
                INTEGER,
            setMgMtie100EL2
                INTEGER,
            setMgMtie100CL1
                INTEGER,
            setMgMtie100CL2
                INTEGER,

            setMgMtie1000EL1
                INTEGER,
            setMgMtie1000EL2
                INTEGER,
            setMgMtie1000CL1
                INTEGER,
            setMgMtie1000CL2
                INTEGER,

            setMgMtie10000EL1
                INTEGER,
            setMgMtie10000EL2
                INTEGER,
            setMgMtie10000CL1
                INTEGER,
            setMgMtie10000CL2
                INTEGER,

            setMgMtie100000EL1
                INTEGER,
            setMgMtie100000EL2
                INTEGER,
            setMgMtie100000CL1
                INTEGER,
            setMgMtie100000CL2
                INTEGER,

            -- FREQ Threshold Setting
            setMgFreqAErrLmt
                INTEGER,
            setMgFreqAClrLmt
                INTEGER,
            setMgFreqATau
                INTEGER,

            setMgFreqBErrLmt
                INTEGER,
            setMgFreqBClrLmt
                INTEGER,
            setMgFreqBTau
                INTEGER
        }


    setMgChassis OBJECT-TYPE
        SYNTAX  INTEGER (1..1)
        MAX-ACCESS  not-accessible
        STATUS  current
        DESCRIPTION
        "Identifies which chassis is being addressed. 
        This chassis number and slot number uniquely identify each inventory entry.

        Note: In the SSU2000, this number is always one. (i.e. in the main chassis)
        "
    ::= { setMgEntry 1 }

    setMgSlot OBJECT-TYPE
        SYNTAX  INTEGER (1..20)
        MAX-ACCESS  not-accessible
        STATUS  current
        DESCRIPTION
        "Identifies which slot position is being addressed. 
        This chassis number and slot number uniquely identify each inventory entry.

        Note: In the SSU2000, valid slots for GPS are slot 3 and slot 5.
        "
    ::= { setMgEntry 2 }

    setMgMtieStd OBJECT-TYPE
        SYNTAX  INTEGER
                {
                    prs(1),
                    ds1(2),
                    g811(3),
                    g823(4)
                }
        MAX-ACCESS  read-write
        STATUS  current
        DESCRIPTION
        "Set the input port setting of the MTIE limits to predefined values.
        prs(1), -- ANSI T1.101 PRS MTIE MASK
        ds1(2), -- ANSI T1.101 DS1 MTIE MASK
        g811(3), -- G.811 (PRC) MTIE MASK
        g823(4) -- G.823 (SSU) MTIE MASK

        This field is only meaningful for a write operation. 
        "
    ::= { setMgEntry 3 }

    setMgMtie10EL1 OBJECT-TYPE
        SYNTAX  INTEGER (0..60000)
        MAX-ACCESS  read-write
        STATUS  current
        DESCRIPTION
        "Set the input port MTIE 10 seconds error threshold for the first limit setting.
        "
    ::= { setMgEntry 4 }

    setMgMtie10EL2 OBJECT-TYPE
        SYNTAX  INTEGER (0..60000)
        MAX-ACCESS  read-write
        STATUS  current
        DESCRIPTION
        "Set the input port MTIE 10 seconds error threshold for the second limit setting.
        "
    ::= { setMgEntry 5 }

    setMgMtie10CL1 OBJECT-TYPE
        SYNTAX  INTEGER (0..60000)
        MAX-ACCESS  read-write
        STATUS  current
        DESCRIPTION
        "Set the input port MTIE 10 seconds clear threshold for the first limit setting.
        "
    ::= { setMgEntry 6 }

    setMgMtie10CL2 OBJECT-TYPE
        SYNTAX  INTEGER (0..60000)
        MAX-ACCESS  read-write
        STATUS  current
        DESCRIPTION
            "Set the input port MTIE 10 seconds clear threshold for the second limit setting.
            "
    ::= { setMgEntry 7 }


    setMgMtie100EL1 OBJECT-TYPE
        SYNTAX  INTEGER (0..60000)
        MAX-ACCESS  read-write
        STATUS  current
        DESCRIPTION
        "Set the input port MTIE 100 seconds error threshold for the first limit setting.
        "
    ::= { setMgEntry 8 }

    setMgMtie100EL2 OBJECT-TYPE
        SYNTAX  INTEGER (0..60000)
        MAX-ACCESS  read-write
        STATUS  current
        DESCRIPTION
        "Set the input port MTIE 100 seconds error threshold for the second limit setting.
        "
    ::= { setMgEntry 9 }

    setMgMtie100CL1 OBJECT-TYPE
        SYNTAX  INTEGER (0..60000)
        MAX-ACCESS  read-write
        STATUS  current
        DESCRIPTION
        "Set the input port MTIE 100 seconds clear threshold for the first limit setting.
        "
    ::= { setMgEntry 10 }

    setMgMtie100CL2 OBJECT-TYPE
        SYNTAX  INTEGER (0..60000)
        MAX-ACCESS  read-write
        STATUS  current
        DESCRIPTION
        "Set the input port MTIE 100 seconds clear threshold for the second limit setting.
        "
    ::= { setMgEntry 11 }


    setMgMtie1000EL1 OBJECT-TYPE
        SYNTAX  INTEGER (0..60000)
        MAX-ACCESS  read-write
        STATUS  current
        DESCRIPTION
        "Set the input port MTIE 1000 seconds error threshold for the first limit setting.
        "
    ::= { setMgEntry 12 }

    setMgMtie1000EL2 OBJECT-TYPE
        SYNTAX  INTEGER (0..60000)
        MAX-ACCESS  read-write
        STATUS  current
        DESCRIPTION
        "Set the input port MTIE 1000 seconds error threshold for the second limit setting.
        "
    ::= { setMgEntry 13 }

    setMgMtie1000CL1 OBJECT-TYPE
        SYNTAX  INTEGER (0..60000)
        MAX-ACCESS  read-write
        STATUS  current
        DESCRIPTION
        "Set the input port MTIE 1000 seconds clear threshold for the first limit setting.
        "
    ::= { setMgEntry 14 }

    setMgMtie1000CL2 OBJECT-TYPE
        SYNTAX  INTEGER (0..60000)
        MAX-ACCESS  read-write
        STATUS  current
        DESCRIPTION
        "Set the input port MTIE 1000 seconds clear threshold for the second limit setting.
        "
    ::= { setMgEntry 15 }

    setMgMtie10000EL1 OBJECT-TYPE
        SYNTAX  INTEGER (0..60000)
        MAX-ACCESS  read-write
        STATUS  current
        DESCRIPTION
        "Set the input port MTIE 10000 seconds error threshold for the first limit setting.
        "
::= { setMgEntry 16 }

    setMgMtie10000EL2 OBJECT-TYPE
        SYNTAX  INTEGER (0..60000)
        MAX-ACCESS  read-write
        STATUS  current
        DESCRIPTION
        "Set the input port MTIE 10000 seconds error threshold for the second limit setting.
        "
    ::= { setMgEntry 17 }


    setMgMtie10000CL1 OBJECT-TYPE
        SYNTAX  INTEGER (0..60000)
        MAX-ACCESS  read-write
        STATUS  current
        DESCRIPTION
        "Set the input port MTIE 10000 seconds clear threshold for the first limit setting.
        "
    ::= { setMgEntry 18 }

    setMgMtie10000CL2 OBJECT-TYPE
        SYNTAX  INTEGER (0..60000)
        MAX-ACCESS  read-write
        STATUS  current
        DESCRIPTION
        "Set the input port MTIE 10000 seconds clear threshold for the second limit setting.
        "
    ::= { setMgEntry 19 }


    setMgMtie100000EL1 OBJECT-TYPE
        SYNTAX  INTEGER (0..60000)
        MAX-ACCESS  read-write
        STATUS  current
        DESCRIPTION
        "Set the input port MTIE 100000 seconds error threshold for the first limit setting.
        "
    ::= { setMgEntry 20 }

    setMgMtie100000EL2 OBJECT-TYPE
        SYNTAX  INTEGER (0..60000)
        MAX-ACCESS  read-write
        STATUS  current
        DESCRIPTION
        "Set the input port MTIE 100000 seconds error threshold for the second limit setting.
        "
    ::= { setMgEntry 21 }


    setMgMtie100000CL1 OBJECT-TYPE
        SYNTAX  INTEGER (0..60000)
        MAX-ACCESS  read-write
        STATUS  current
        DESCRIPTION
        "Set the input port MTIE 100000 seconds clear threshold for the first limit setting.
        "
    ::= { setMgEntry 22 }

    setMgMtie100000CL2 OBJECT-TYPE
        SYNTAX  INTEGER (0..60000)
        MAX-ACCESS  read-write
        STATUS  current
        DESCRIPTION
        "Set the input port MTIE 100000 seconds clear threshold for the second limit setting.
        "
    ::= { setMgEntry 23 }

    setMgFreqAErrLmt OBJECT-TYPE
        SYNTAX  INTEGER (0..10000000)
        MAX-ACCESS  read-write
        STATUS  current
        DESCRIPTION
        "Set the input port frequency error threshold for clock A.
        "
    ::= { setMgEntry 24 }

    setMgFreqAClrLmt OBJECT-TYPE
        SYNTAX  INTEGER (0..10000000)
        MAX-ACCESS  read-write
        STATUS  current
        DESCRIPTION
        "Set the input port frequency clear threshold for clock A.
        "
    ::= { setMgEntry 25 }

    setMgFreqATau OBJECT-TYPE
        SYNTAX  INTEGER (10..1000)
        MAX-ACCESS  read-write
        STATUS  current
        DESCRIPTION
        "Set the Time constant (tau), in seconds, used for the calculation of the Average Frequency versus clock A.
        "
    ::= { setMgEntry 26 }


    setMgFreqBErrLmt OBJECT-TYPE
        SYNTAX  INTEGER (0..10000000)
        MAX-ACCESS  read-write
        STATUS  current
        DESCRIPTION
        "Set the input port frequency error threshold for clock B.
        "
    ::= { setMgEntry 27 }

    setMgFreqBClrLmt OBJECT-TYPE
        SYNTAX  INTEGER (0..10000000)
        MAX-ACCESS  read-write
        STATUS  current
        DESCRIPTION
        "Set the input port frequency clear threshold for clock B.
        "
    ::= { setMgEntry 28 }

    setMgFreqBTau OBJECT-TYPE
        SYNTAX  INTEGER (10..1000)
        MAX-ACCESS  read-write
        STATUS  current
        DESCRIPTION
        "Set the Time constant (tau), in seconds, used for the calculation of the Average Frequency versus clock B.
        "
    ::= { setMgEntry 29 }


    -- **************************************************************
    -- SSU2000 DS1/E1 INPUT MODULE SETUP GROUP
    -- **************************************************************


    -- ******************************************
    -- DS1/E1 INPUT MODULE SETTING
    -- ******************************************

    setDs1E1InpTable OBJECT-TYPE
    SYNTAX  SEQUENCE OF SetDiEntry
    MAX-ACCESS  not-accessible
    STATUS  current
    DESCRIPTION
        "The list of DS1/E1 attribute setup information. 
        "
    ::= { setupDs1E1Inp 2 }


    setDiEntry OBJECT-TYPE
    SYNTAX  SetDiEntry
    MAX-ACCESS  not-accessible
    STATUS  current
    DESCRIPTION
    "Input status and settings attributes.
    "
INDEX   { setDiChassis, setDiSlot, setDiPort }
    ::= { setDs1E1InpTable 1 }

    SetDiEntry ::=
        SEQUENCE {
            setDiChassis
                INTEGER,    
            setDiSlot
                INTEGER,    
            setDiPort
                INTEGER,    
            setDiEnable
                EnaValue,
            setDiFrame
                INTEGER,
            setDiZS
                OnValue,
            setDiCRC
                OnValue,
            setDiSSM
                OnValue,
            setDiProvPql
                INTEGER,
            setDiPriority
                INTEGER,
            setDiGain
                OnValue,
            setDiCSFlt
                INTEGER,
            setDiE1SsmBit
                INTEGER,
            setDiZeroPhase
                INTEGER,
            setDiMtieCalc
                INTEGER
        }

    setDiChassis OBJECT-TYPE
        SYNTAX  INTEGER (1..1)
        MAX-ACCESS  not-accessible
        STATUS  current
        DESCRIPTION
        "Identifies which chassis is being addressed. 
        This chassis number and slot number uniquely identify each inventory entry.

        Note: The input module can only reside in chassis 1 (main chassis).
        "
    ::= { setDiEntry 1 }

    setDiSlot OBJECT-TYPE
        SYNTAX  INTEGER (1..20)
        MAX-ACCESS  not-accessible
        STATUS  current
        DESCRIPTION
        "Identifies which slot position is being addressed. 
        This chassis number and slot number uniquely identify each inventory entry.
        "
    ::= { setDiEntry 2 }


    setDiPort OBJECT-TYPE
        SYNTAX  INTEGER (1..3)
        MAX-ACCESS  not-accessible
        STATUS  current
        DESCRIPTION
        "Identifies which port is being addressed. 
        This chassis number and slot number uniquely identify each inventory entry.
        "
    ::= { setDiEntry 3 }


    setDiEnable OBJECT-TYPE
        SYNTAX  EnaValue
        MAX-ACCESS  read-write
        STATUS  current
        DESCRIPTION
        "Set the input port to enabled or disabled.
        "
    ::= { setDiEntry 4 }


    setDiFrame OBJECT-TYPE
        SYNTAX  INTEGER
                {
                    esf(1),
                    d4(2),
                    ccs(3),
                    cas(4),
                    mhz1(5),
                    khz1544(6),
                    khz2048(7),
                    mhz5(8),
                    mhz10(9)
                }
        MAX-ACCESS  read-write
        STATUS  current
        DESCRIPTION
        "Set the input framing type or clock frequency. 
        esf(1), -- T1 ESF 
        d4(2), -- T1 D4
        ccs(3), -- E1 CCS
        cas(4), -- E1 CAS
        mhz1(5), -- Clock 1MHz
        khz1544(6), -- Clock 1544kHz
        khz2048(7), -- Clock 2048kHz
        mhz5(8), -- Clock 5MHz
        mhz10(9) -- Clock 10MHz
        "
    ::= { setDiEntry 5 }

    setDiZS OBJECT-TYPE
        SYNTAX  OnValue
        MAX-ACCESS  read-write
        STATUS  current
        DESCRIPTION
        "Set Zero Supression (ZS) on the input port to enabled or disabled.
        "
    ::= { setDiEntry 6 }

    setDiCRC OBJECT-TYPE
        SYNTAX  OnValue
        MAX-ACCESS  read-write
        STATUS  current
        DESCRIPTION
        "Set CRC verificaiton on the input port to enabled or disabled.
        "
    ::= { setDiEntry 7 }

    setDiSSM OBJECT-TYPE
        SYNTAX  OnValue
        MAX-ACCESS  read-write
        STATUS  current
        DESCRIPTION
        "Set Sync Status Messaging (SSM) on the input port to enabled or disabled..
        "
    ::= { setDiEntry 8 }

    setDiProvPql OBJECT-TYPE
        SYNTAX  INTEGER (1..9)
        MAX-ACCESS  read-write
        STATUS  current
        DESCRIPTION
        "Set the input port provisioned Priority Quality Level (PQL).

        Note: Valid values are 1 - 9.
        "
    ::= { setDiEntry 9 }


    setDiPriority OBJECT-TYPE
        SYNTAX  INTEGER (0..10)
        MAX-ACCESS  read-write
        STATUS  current
        DESCRIPTION
        "Set the input port priority level.
        '0' = monitoring, 
        '1' = highest priority,
        '10' = lowest priority.
        "
    ::= { setDiEntry 10 }

    setDiGain OBJECT-TYPE
        SYNTAX  OnValue
        MAX-ACCESS  read-write
        STATUS  current
        DESCRIPTION
        "Set the input port gain setting to enabled or disabled.
        "
    ::= { setDiEntry 11 }

    setDiCSFlt OBJECT-TYPE
        SYNTAX  INTEGER
                {
                    off(1),
                    low(2),
                    high(3),
                    na(4)
                }
        MAX-ACCESS  read-write
        STATUS  current
        DESCRIPTION
        "Set input Port 1 for external Cesium (CS) fault alarm logic level. 
        off(1), -- function is disabled
        low(2), -- function is enabled, will trigger on low (0V) level
        high(3), -- function is enabled, will trigger on high (+5v) level
        na(4) -- not applicable

        Note: only available for port one.
        "
    ::= { setDiEntry 12 }

    setDiE1SsmBit OBJECT-TYPE
        SYNTAX  INTEGER (4..8)
        MAX-ACCESS  read-write
        STATUS  current
        DESCRIPTION
        "Set the input port E1 Sync Status Message (SSM) bit position.

        This command is only meaningful for the E1 input module.
        For DS1, this value is always 4, and has no meaning (i.e. not used).
        "
    ::= { setDiEntry 13 }


    setDiZeroPhase OBJECT-TYPE
        SYNTAX  INTEGER
                {
                    zeroPhA(1),
                    zeroPhB(2),
                    zeroPhAB(3)
                }
        MAX-ACCESS  read-write
        STATUS  current
        DESCRIPTION
        "Set the phase error to zero for this input port.
        ZEROPHA - set phase A error to zero,
        ZEROPHB - set phase B error to zero,
        ZEROPHAB - set phase A and B to zero.

        Note: This field only is meaningful during the write operation.
        "
    ::= { setDiEntry 14 }

    setDiMtieCalc OBJECT-TYPE
        SYNTAX  INTEGER
                {
                    hz40(1),
                    hz1(2)
                }
        MAX-ACCESS  read-write
        STATUS  current
        DESCRIPTION
        "Reports MTIE calculator (40Hz or 1Hz) being used

        The number represents the input port setting for MTIE Calculator measurement. 
        - 40Hz - Selects the 40Hz MTIE values to set/clear MTIE alarms
        - 1Hz - Selects the 1Hz MTIE values to set/clear MTIE alarms

        Note: only available for port one.
        "
    ::= { setDiEntry 15 }


    -- ******************************************
    -- DS1/E1 INPUT ALARM THRESHOLD SETTING
    -- ******************************************

    setAlmThDs1E1InpTable OBJECT-TYPE
    SYNTAX  SEQUENCE OF SetMiEntry
    MAX-ACCESS  not-accessible
    STATUS  current
    DESCRIPTION
    "A list of DS1/E1 input alarm attributes and settings information.
    "
    ::= { setupDs1E1Inp 4 }


    setMiEntry OBJECT-TYPE
    SYNTAX  SetMiEntry
    MAX-ACCESS  not-accessible
    STATUS  current
    DESCRIPTION
    "Input alarm attributes and settings.
    setMiChassis
        Identifies which chassis is being addressed. 
    setMiSlot
        Identifies which slot position is being addressed. 
    setMiPort
        Identifies which port position is being addressed. 
    setMiMtieStd
        Set the input port setting of the MTIE limits to predefined values.
    setMiMtie10EL1
        Set the input port MTIE 10 seconds error threshold for the first limit setting.
    setMiMtie10EL2
        Set the input port MTIE 10 seconds error threshold for the second limit setting.
    setMiMtie10CL1
        Set the input port MTIE 10 seconds clear threshold for the first limit setting.
    setMiMtie10CL2
        Set the input port MTIE 10 seconds clear threshold for the second limit setting.
    setMiMtie100EL1
        Set the input port MTIE 100 seconds error threshold for the first limit setting.
    setMiMtie100EL2
        Set the input port MTIE 100 seconds error threshold for the second limit setting.
    setMiMtie100CL1
        Set the input port MTIE 100 seconds clear threshold for the first limit setting.
    setMiMtie100CL2
        Set the input port MTIE 100 seconds clear threshold for the second limit setting.
    setMiMtie1000EL1
        Set the input port MTIE 1000 seconds error threshold for the first limit setting.
    setMiMtie1000EL2
        Set the input port MTIE 1000 seconds error threshold for the second limit setting.
    setMiMtie1000CL1
        Set the input port MTIE 1000 seconds clear threshold for the first limit setting.
    setMiMtie1000CL2
        Set the input port MTIE 1000 seconds clear threshold for the second limit setting.
    setMiMtie10000EL1
        Set the input port MTIE 10000 seconds error threshold for the first limit setting.
    setMiMtie10000EL2
        Set the input port MTIE 10000 seconds error threshold for the second limit setting.
    setMiMtie10000CL1
        Set the input port MTIE 10000 seconds clear threshold for the first limit setting.
    setMiMtie10000CL2
        Set the input port MTIE 10000 seconds clear threshold for the second limit setting.
    setMiMtie100000EL1
        Set the input port MTIE 100000 seconds error threshold for the first limit setting.
    setMiMtie100000EL2
        Set the input port MTIE 100000 seconds error threshold for the second limit setting.
    setMiMtie100000CL1
        Set the input port MTIE 100000 seconds clear threshold for the first limit setting.
    setMiMtie100000CL2
        Set the input port MTIE 100000 seconds clear threshold for the second limit setting.
    setMiFreqAErrLmt
        Set the input port frequency error threshold for clock A.
    setMiFreqAClrLmt
        Set the input port frequency clear threshold for clock A.
    setMiFreqATau
        Set the Time constant (tau), in seconds, used for the calculation of the Average Frequency versus clock A.
    setMiFreqBErrLmt
        Set the input port frequency error threshold for clock B.
    setMiFreqBClrLmt
        Set the input port frequency clear threshold for clock B.
    setMiFreqBTau
        Set the Time constant (tau), in seconds, used for the calculation of the Average Frequency versus clock B.
    setMiLOSErrCnt
        Set the input port error count threshold for LOS signal faults.
    setMiLOSClrCnt
        Set the input port clear count threshold for LOS signal faults.
    setMiAISErrCnt
        Set the input port error count threshold for AIS signal faults.
    setMiAISClrCnt
        Set the input port clear count threshold for AIS signal faults.
    setMiOOFErrCnt
        Set the input port error count threshold for OOF signal faults.
    setMiOOFClrCnt
        Set the input port clear count threshold for OOF signal faults.
    setMiBPVErrCnt
        Set the input port error count threshold for BPV signal faults.
    setMiBPVClrCnt
        Set the input port clear count threshold for BPV signal faults.
    setMiCRCErrCnt
        Set the input port error count threshold for CRC signal faults.
    setMiCRCClrCnt
        Set the input port clear count threshold for CRC signal faults.
    "
    INDEX   { setMiChassis, setMiSlot, setMiPort }
    ::= { setAlmThDs1E1InpTable 1 }


    SetMiEntry ::=
        SEQUENCE {
            setMiChassis
                INTEGER,    
            setMiSlot
                INTEGER,    
            setMiPort
                INTEGER,
            
            -- MTIE Threshold Setting
            setMiMtieStd
                INTEGER,

            setMiMtie10EL1
                INTEGER,
            setMiMtie10EL2
                INTEGER,
            setMiMtie10CL1
                INTEGER,
            setMiMtie10CL2
                INTEGER,

            setMiMtie100EL1
                INTEGER,
            setMiMtie100EL2
                INTEGER,
            setMiMtie100CL1
                INTEGER,
            setMiMtie100CL2
                INTEGER,

            setMiMtie1000EL1
                INTEGER,
            setMiMtie1000EL2
                INTEGER,
            setMiMtie1000CL1
                INTEGER,
            setMiMtie1000CL2
                INTEGER,

            setMiMtie10000EL1
                INTEGER,
            setMiMtie10000EL2
                INTEGER,
            setMiMtie10000CL1
                INTEGER,
            setMiMtie10000CL2
                INTEGER,

            setMiMtie100000EL1
                INTEGER,
            setMiMtie100000EL2
                INTEGER,
            setMiMtie100000CL1
                INTEGER,
            setMiMtie100000CL2
                INTEGER,

            -- FREQ Threshold Setting
            setMiFreqAErrLmt
                INTEGER,
            setMiFreqAClrLmt
                INTEGER,
            setMiFreqATau
                INTEGER,

            setMiFreqBErrLmt
                INTEGER,
            setMiFreqBClrLmt
                INTEGER,
            setMiFreqBTau
                INTEGER,

            -- SIGNAL Threshold Setting
            setMiLOSErrCnt
                INTEGER,
            setMiLOSClrCnt
                INTEGER,
            setMiAISErrCnt
                INTEGER,
            setMiAISClrCnt
                INTEGER,
            setMiOOFErrCnt
                INTEGER,
            setMiOOFClrCnt
                INTEGER,
            setMiBPVErrCnt
                INTEGER,
            setMiBPVClrCnt
                INTEGER,
            setMiCRCErrCnt
                INTEGER,
            setMiCRCClrCnt
                INTEGER
        }


    setMiChassis OBJECT-TYPE
        SYNTAX  INTEGER (1..1)
        MAX-ACCESS  not-accessible
        STATUS  current
        DESCRIPTION
        "Identifies which chassis is being addressed. 
        This chassis number, slot number, and port number uniquely identify each inventory entry.

        Note: In the SSU2000, this number is always one. (i.e. in the main chassis)
        "
    ::= { setMiEntry 1 }

    setMiSlot OBJECT-TYPE
        SYNTAX  INTEGER (1..20)
        MAX-ACCESS  not-accessible
        STATUS  current
        DESCRIPTION
        "Identifies which slot is being addressed. 
        This chassis number, slot number, and port number uniquely identify each inventory entry.
        "
    ::= { setMiEntry 2 }


    setMiPort OBJECT-TYPE
        SYNTAX  INTEGER (1..3)
        MAX-ACCESS  not-accessible
        STATUS  current
        DESCRIPTION
        "Identifies which slot is being addressed. 
        This chassis number, slot number, and port number uniquely identify each inventory entry.
        "
    ::= { setMiEntry 3 }

    setMiMtieStd OBJECT-TYPE
        SYNTAX  INTEGER
                {
                    prs(1),
                    ds1(2),
                    g811(3),
                    g823(4)
                }
        MAX-ACCESS  read-write
        STATUS  current
        DESCRIPTION
        "Set the input port setting of the MTIE limits to predefined values.
        prs(1), -- ANSI T1.101 PRS MTIE MASK
        ds1(2), -- ANSI T1.101 DS1 MTIE MASK
        g811(3), -- G.811 (PRC) MTIE MASK
        g823(4) -- G.823 (SSU) MTIE MASK

        This field is only meaningful for a write operation. 
        "
    ::= { setMiEntry 4 }

    setMiMtie10EL1 OBJECT-TYPE
        SYNTAX  INTEGER (0..60000)
        MAX-ACCESS  read-write
        STATUS  current
        DESCRIPTION
        "Set the input port MTIE 10 seconds error threshold for the first limit setting.
        "
    ::= { setMiEntry 5 }

    setMiMtie10EL2 OBJECT-TYPE
        SYNTAX  INTEGER (0..60000)
        MAX-ACCESS  read-write
        STATUS  current
        DESCRIPTION
        "Set the input port MTIE 10 seconds error threshold for the second limit setting.
        "
    ::= { setMiEntry 6 }

    setMiMtie10CL1 OBJECT-TYPE
        SYNTAX  INTEGER (0..60000)
        MAX-ACCESS  read-write
        STATUS  current
        DESCRIPTION
            "Set the input port MTIE 10 seconds clear threshold for the first limit setting.
            "
    ::= { setMiEntry 7 }

    setMiMtie10CL2 OBJECT-TYPE
        SYNTAX  INTEGER (0..60000)
        MAX-ACCESS  read-write
        STATUS  current
        DESCRIPTION
        "Set the input port MTIE 10 seconds clear threshold for the second limit setting.
        "
    ::= { setMiEntry 8 }



    setMiMtie100EL1 OBJECT-TYPE
        SYNTAX  INTEGER (0..60000)
        MAX-ACCESS  read-write
        STATUS  current
        DESCRIPTION
        "Set the input port MTIE 100 seconds error threshold for the first limit setting.
        "
    ::= { setMiEntry 9 }

    setMiMtie100EL2 OBJECT-TYPE
        SYNTAX  INTEGER (0..60000)
        MAX-ACCESS  read-write
        STATUS  current
        DESCRIPTION
        "Set the input port MTIE 100 seconds error threshold for the second limit setting.
        "
    ::= { setMiEntry 10 }

    setMiMtie100CL1 OBJECT-TYPE
        SYNTAX  INTEGER (0..60000)
        MAX-ACCESS  read-write
        STATUS  current
        DESCRIPTION
        "Set the input port MTIE 100 seconds clear threshold for the first limit setting.
        "
    ::= { setMiEntry 11 }

    setMiMtie100CL2 OBJECT-TYPE
        SYNTAX  INTEGER (0..60000)
        MAX-ACCESS  read-write
        STATUS  current
        DESCRIPTION
        "Set the input port MTIE 100 seconds clear threshold for the second limit setting.
        "
    ::= { setMiEntry 12 }


    setMiMtie1000EL1 OBJECT-TYPE
        SYNTAX  INTEGER (0..60000)
        MAX-ACCESS  read-write
        STATUS  current
        DESCRIPTION
        "Set the input port MTIE 1000 seconds error threshold for the first limit setting.
        "
    ::= { setMiEntry 13 }

    setMiMtie1000EL2 OBJECT-TYPE
        SYNTAX  INTEGER (0..60000)
        MAX-ACCESS  read-write
        STATUS  current
        DESCRIPTION
        "Set the input port MTIE 1000 seconds error threshold for the second limit setting.
        "
    ::= { setMiEntry 14 }

    setMiMtie1000CL1 OBJECT-TYPE
        SYNTAX  INTEGER (0..60000)
        MAX-ACCESS  read-write
        STATUS  current
        DESCRIPTION
        "Set the input port MTIE 1000 seconds clear threshold for the first limit setting.
        "
    ::= { setMiEntry 15 }

    setMiMtie1000CL2 OBJECT-TYPE
        SYNTAX  INTEGER (0..60000)
        MAX-ACCESS  read-write
        STATUS  current
        DESCRIPTION
        "Set the input port MTIE 1000 seconds clear threshold for the second limit setting.
        "
    ::= { setMiEntry 16 }



    setMiMtie10000EL1 OBJECT-TYPE
        SYNTAX  INTEGER (0..60000)
        MAX-ACCESS  read-write
        STATUS  current
        DESCRIPTION
        "Set the input port MTIE 10000 seconds error threshold for the first limit setting.
        "
    ::= { setMiEntry 17 }

    setMiMtie10000EL2 OBJECT-TYPE
        SYNTAX  INTEGER (0..60000)
        MAX-ACCESS  read-write
        STATUS  current
        DESCRIPTION
        "Set the input port MTIE 10000 seconds error threshold for the second limit setting.
        "
    ::= { setMiEntry 18 }


    setMiMtie10000CL1 OBJECT-TYPE
        SYNTAX  INTEGER (0..60000)
        MAX-ACCESS  read-write
        STATUS  current
        DESCRIPTION
        "Set the input port MTIE 10000 seconds clear threshold for the first limit setting.
        "
    ::= { setMiEntry 19 }

    setMiMtie10000CL2 OBJECT-TYPE
        SYNTAX  INTEGER (0..60000)
        MAX-ACCESS  read-write
        STATUS  current
        DESCRIPTION
        "Set the input port MTIE 10000 seconds clear threshold for the second limit setting.
        "
    ::= { setMiEntry 20 }


    setMiMtie100000EL1 OBJECT-TYPE
        SYNTAX  INTEGER (0..60000)
        MAX-ACCESS  read-write
        STATUS  current
        DESCRIPTION
        "Set the input port MTIE 100000 seconds error threshold for the first limit setting.
        "
    ::= { setMiEntry 21 }

    setMiMtie100000EL2 OBJECT-TYPE
        SYNTAX  INTEGER (0..60000)
        MAX-ACCESS  read-write
        STATUS  current
        DESCRIPTION
        "Set the input port MTIE 100000 seconds error threshold for the second limit setting.
        "
    ::= { setMiEntry 22 }


    setMiMtie100000CL1 OBJECT-TYPE
        SYNTAX  INTEGER (0..60000)
        MAX-ACCESS  read-write
        STATUS  current
        DESCRIPTION
        "Set the input port MTIE 100000 seconds clear threshold for the first limit setting.
        "
    ::= { setMiEntry 23 }

    setMiMtie100000CL2 OBJECT-TYPE
        SYNTAX  INTEGER (0..60000)
        MAX-ACCESS  read-write
        STATUS  current
        DESCRIPTION
        "Set the input port MTIE 100000 seconds clear threshold for the second limit setting.
        "
    ::= { setMiEntry 24 }



    setMiFreqAErrLmt OBJECT-TYPE
        SYNTAX  INTEGER (0..10000000)
        MAX-ACCESS  read-write
        STATUS  current
        DESCRIPTION
        "Set the input port frequency error threshold for clock A.
        "
    ::= { setMiEntry 25 }

    setMiFreqAClrLmt OBJECT-TYPE
        SYNTAX  INTEGER (0..10000000)
        MAX-ACCESS  read-write
        STATUS  current
        DESCRIPTION
        "Set the input port frequency clear threshold for clock A.
        "
    ::= { setMiEntry 26 }

    setMiFreqATau OBJECT-TYPE
        SYNTAX  INTEGER (10..1000)
        MAX-ACCESS  read-write
        STATUS  current
        DESCRIPTION
        "Set the time constant (tau), in seconds, used for the calculation of the Average Frequency for clock A.
        "
    ::= { setMiEntry 27 }


    setMiFreqBErrLmt OBJECT-TYPE
        SYNTAX  INTEGER (0..10000000)
        MAX-ACCESS  read-write
        STATUS  current
        DESCRIPTION
        "Set the input port frequency error threshold for clock B.
        "
    ::= { setMiEntry 28 }

    setMiFreqBClrLmt OBJECT-TYPE
        SYNTAX  INTEGER (0..10000000)
        MAX-ACCESS  read-write
        STATUS  current
        DESCRIPTION
        "Set the input port frequency clear threshold for clock B.
        "
    ::= { setMiEntry 29 }

    setMiFreqBTau OBJECT-TYPE
        SYNTAX  INTEGER (10..1000)
        MAX-ACCESS  read-write
        STATUS  current
        DESCRIPTION
        "Set the time constant (tau), in seconds, used for the calculation of the Average Frequency for clock B.
        "
    ::= { setMiEntry 30 }

    setMiLOSErrCnt OBJECT-TYPE
        SYNTAX  INTEGER (1..100)
        MAX-ACCESS  read-write
        STATUS  current
        DESCRIPTION
        "Set the input port error count threshold for LOS signal faults.
        "
    ::= { setMiEntry 31 }

    setMiLOSClrCnt OBJECT-TYPE
        SYNTAX  INTEGER (1..100)
        MAX-ACCESS  read-write
        STATUS  current
        DESCRIPTION
        "Set the input port clear count threshold for LOS signal faults.
        "
    ::= { setMiEntry 32 }

    setMiAISErrCnt OBJECT-TYPE
        SYNTAX  INTEGER (1..100)
        MAX-ACCESS  read-write
        STATUS  current
        DESCRIPTION
        "Set the input port error count threshold for AIS signal faults.
        "
    ::= { setMiEntry 33 }

    setMiAISClrCnt OBJECT-TYPE
        SYNTAX  INTEGER (1..100)
        MAX-ACCESS  read-write
        STATUS  current
        DESCRIPTION
        "Set the input port clear count threshold for AIS signal faults.
        "
    ::= { setMiEntry 34 }

    setMiOOFErrCnt OBJECT-TYPE
        SYNTAX  INTEGER (1..10000)
        MAX-ACCESS  read-write
        STATUS  current
        DESCRIPTION
        "Set the input port error count threshold for OOF signal faults.
        "
    ::= { setMiEntry 35 }

    setMiOOFClrCnt OBJECT-TYPE
        SYNTAX  INTEGER (1..10000)
        MAX-ACCESS  read-write
        STATUS  current
        DESCRIPTION
        "Set the input port clear count threshold for OOF signal faults.
        "
    ::= { setMiEntry 36 }

    setMiBPVErrCnt OBJECT-TYPE
        SYNTAX  INTEGER (1..10000)
        MAX-ACCESS  read-write
        STATUS  current
        DESCRIPTION
        "Set the input port error count threshold for BPV signal faults.
        "
    ::= { setMiEntry 37 }

    setMiBPVClrCnt OBJECT-TYPE
        SYNTAX  INTEGER (1..10000)
        MAX-ACCESS  read-write
        STATUS  current
        DESCRIPTION
        "Set the input port clear count threshold for BPV signal faults.
        "
    ::= { setMiEntry 38 }

    setMiCRCErrCnt OBJECT-TYPE
        SYNTAX  INTEGER (1..10000)
        MAX-ACCESS  read-write
        STATUS  current
        DESCRIPTION
        "Set the input port error count hreshold for CRC signal faults.
        "
    ::= { setMiEntry 39 }

    setMiCRCClrCnt OBJECT-TYPE
        SYNTAX  INTEGER (1..10000)
        MAX-ACCESS  read-write
        STATUS  current
        DESCRIPTION
        "Set the input port clear count threshold for CRC signal faults.
        "
    ::= { setMiEntry 40 }


    -- **************************************************************
    -- SSU2000 COMPOSITE CLOCK INPUT MODULE SETUP GROUP
    -- **************************************************************


    -- ******************************************
    -- COMPOSITE CLOCK INPUT MODULE SETTING
    -- ******************************************

    setCcInpTable OBJECT-TYPE
    SYNTAX  SEQUENCE OF SetCiEntry
    MAX-ACCESS  not-accessible
    STATUS  current
    DESCRIPTION
        "The list of CC Input attribute setup information. 
        "
    ::= { setupCcInp 2 }


    setCiEntry OBJECT-TYPE
    SYNTAX  SetCiEntry
    MAX-ACCESS  not-accessible
    STATUS  current
    DESCRIPTION
    "Input status and settings attributes.
    "
    INDEX   { setCiChassis, setCiSlot, setCiPort }
    ::= { setCcInpTable 1 }

    SetCiEntry ::=
        SEQUENCE {
            setCiChassis
                INTEGER,    
            setCiSlot
                INTEGER,    
            setCiPort
                INTEGER,    
            setCiEnable
                EnaValue,
            setCiProvPql
                INTEGER,
            setCiPriority
                INTEGER,
            setCiZeroPhase
                INTEGER
        }

    setCiChassis OBJECT-TYPE
        SYNTAX  INTEGER (1..1)
        MAX-ACCESS  not-accessible
        STATUS  current
        DESCRIPTION
        "Identifies which chassis is being addressed. 
        This chassis number and slot number uniquely identify each inventory entry.

        Note: The input module can only reside in chassis 1 (main chassis).
        "
    ::= { setCiEntry 1 }

    setCiSlot OBJECT-TYPE
        SYNTAX  INTEGER (1..20)
        MAX-ACCESS  not-accessible
        STATUS  current
        DESCRIPTION
        "Identifies which slot position is being addressed. 
        This chassis number and slot number uniquely identify each inventory entry.
        "
    ::= { setCiEntry 2 }


    setCiPort OBJECT-TYPE
        SYNTAX  INTEGER (1..3)
        MAX-ACCESS  not-accessible
        STATUS  current
        DESCRIPTION
        "Identifies which port position is being addressed. 
        This chassis number and slot number uniquely identify each inventory entry.
        "
    ::= { setCiEntry 3 }


    setCiEnable OBJECT-TYPE
        SYNTAX  EnaValue
        MAX-ACCESS  read-write
        STATUS  current
        DESCRIPTION
        "Set the input port to enabled or disabled.
        "
    ::= { setCiEntry 4 }

    setCiProvPql OBJECT-TYPE
        SYNTAX  INTEGER (1..9)
        MAX-ACCESS  read-write
        STATUS  current
        DESCRIPTION
        "Set the input port provisioned Priority Quality Level (PQL).

        Note: Valid values are 1 - 9.
        "
    ::= { setCiEntry 7 }


    setCiPriority OBJECT-TYPE
        SYNTAX  INTEGER (0..10)
        MAX-ACCESS  read-write
        STATUS  current
        DESCRIPTION
        "Set the input port priority level.
        '0' = monitoring, 
        '1' = highest priority,
        '10' = lowest priority.
        "
    ::= { setCiEntry 8 }


    setCiZeroPhase OBJECT-TYPE
        SYNTAX  INTEGER
                {
                    zeroPhA(1),
                    zeroPhB(2),
                    zeroPhAB(3)
                }
        MAX-ACCESS  read-write
        STATUS  current
        DESCRIPTION
        "Set the phase error to zero for this input port.
        ZEROPHA - set phase A error to zero,
        ZEROPHB - set phase B error to zero,
        ZEROPHAB - set phase A and B to zero.

        Note: This field only is meaningful during the write operation.
        "
    ::= { setCiEntry 9 }



    -- ******************************************
    -- CCINP ALARM THRESHOLD SETTING
    -- ******************************************

    setAlmThCcInpTable OBJECT-TYPE
    SYNTAX  SEQUENCE OF SetCimEntry
    MAX-ACCESS  not-accessible
    STATUS  current
    DESCRIPTION
    "A list of CC input alarm attributes and settings information.
    "
    ::= { setupCcInp 4 }


    setCimEntry OBJECT-TYPE
    SYNTAX  SetCimEntry
    MAX-ACCESS  not-accessible
    STATUS  current
    DESCRIPTION
    "Input alarm attributes and settings.
    setMiChassis
        Identifies which chassis is being addressed. 
    setMiSlot
        Identifies which slot position is being addressed. 
    setMiPort
        Identifies which port position is being addressed. 
    setCimLOSErrCnt
        Set the input port error count threshold for LOS signal faults.
    setCimLOSClrCnt
        Set the input port clear count threshold for LOS signal faults.
    setCimBPVErrCnt
        Set the input port error count threshold for BPV signal faults.
    setCimBPVClrCnt
        Set the input port clear count threshold for BPV signal faults.
    "
    INDEX   { setCimChassis, setCimSlot, setCimPort }
    ::= { setAlmThCcInpTable 1 }


    SetCimEntry ::=
        SEQUENCE {
            setCimChassis
                INTEGER,    
            setCimSlot
                INTEGER,    
            setCimPort
                INTEGER,

            -- SIGNAL Threshold Setting
            setCimLOSErrCnt
                INTEGER,
            setCimLOSClrCnt
                INTEGER,
            setCimBPVErrCnt
                INTEGER,
            setCimBPVClrCnt
                INTEGER
        }


    setCimChassis OBJECT-TYPE
        SYNTAX  INTEGER (1..1)
        MAX-ACCESS  not-accessible
        STATUS  current
        DESCRIPTION
        "Identifies which chassis is being addressed. 
        This chassis number, slot number, and port number uniquely identify each inventory entry.

        Note: In the SSU2000, this number is always one. (i.e. in the main chassis)
        "
    ::= { setCimEntry 1 }

    setCimSlot OBJECT-TYPE
        SYNTAX  INTEGER (1..20)
        MAX-ACCESS  not-accessible
        STATUS  current
        DESCRIPTION
        "Identifies which slot is being addressed. 
        This chassis number, slot number, and port number uniquely identify each inventory entry.
        "
    ::= { setCimEntry 2 }


    setCimPort OBJECT-TYPE
        SYNTAX  INTEGER (1..3)
        MAX-ACCESS  not-accessible
        STATUS  current
        DESCRIPTION
        "Identifies which port is being addressed. 
        This chassis number, slot number, and port number uniquely identify each inventory entry.
        "
    ::= { setCimEntry 3 }

    setCimLOSErrCnt OBJECT-TYPE
        SYNTAX  INTEGER (1..100)
        MAX-ACCESS  read-write
        STATUS  current
        DESCRIPTION
        "Set the input port error count threshold for LOS signal faults.
        "
    ::= { setCimEntry 4 }

    setCimLOSClrCnt OBJECT-TYPE
        SYNTAX  INTEGER (1..100)
        MAX-ACCESS  read-write
        STATUS  current
        DESCRIPTION
        "Set the input port clear count threshold for LOS signal faults.
        "
    ::= { setCimEntry 5 }

    setCimBPVErrCnt OBJECT-TYPE
        SYNTAX  INTEGER (1..10000)
        MAX-ACCESS  read-write
        STATUS  current
        DESCRIPTION
        "Set the input port error count threshold for BPV signal faults.
        "
    ::= { setCimEntry 10 }

    setCimBPVClrCnt OBJECT-TYPE
        SYNTAX  INTEGER (1..10000)
        MAX-ACCESS  read-write
        STATUS  current
        DESCRIPTION
        "Set the input port clear count threshold for BPV signal faults.
        "
    ::= { setCimEntry 11 }


    -- ******************************************
    -- JAPANESE SINE INPUT MODULE SETTING
    -- ******************************************

    setSineInpTable OBJECT-TYPE
    SYNTAX  SEQUENCE OF SetSineiEntry
    MAX-ACCESS  not-accessible
    STATUS  current
    DESCRIPTION
        "The list of Sine Input attribute setup information. 
        "
    ::= { setupSineInp 2 }


    setSineiEntry OBJECT-TYPE
    SYNTAX  SetSineiEntry
    MAX-ACCESS  not-accessible
    STATUS  current
    DESCRIPTION
    "Input status and settings attributes.
    "
    INDEX   { setSineiChassis, setSineiSlot, setSineiPort }
    ::= { setSineInpTable 1 }

    SetSineiEntry ::=
        SEQUENCE {
            setSineiChassis
                INTEGER,    
            setSineiSlot
                INTEGER,    
            setSineiPort
                INTEGER,    
            setSineiEnable
                EnaValue,
            setSineiFrequency
                INTEGER,
            setSineiProvPql
                INTEGER,
            setSineiPriority
                INTEGER,
            setSineiCSFlt
                INTEGER,

            setSineiZeroPhase
                INTEGER
        }

    setSineiChassis OBJECT-TYPE
        SYNTAX  INTEGER (1..1)
        MAX-ACCESS  not-accessible
        STATUS  current
        DESCRIPTION
        "Identifies which chassis is being addressed. 
        This chassis number and slot number uniquely identify each inventory entry.

        Note: The input module can only reside in chassis 1 (main chassis).
        "
    ::= { setSineiEntry 1 }

    setSineiSlot OBJECT-TYPE
        SYNTAX  INTEGER (1..20)
        MAX-ACCESS  not-accessible
        STATUS  current
        DESCRIPTION
        "Identifies which slot position is being addressed. 
        This chassis number and slot number uniquely identify each inventory entry.
        "
    ::= { setSineiEntry 2 }


    setSineiPort OBJECT-TYPE
        SYNTAX  INTEGER (1..3)
        MAX-ACCESS  not-accessible
        STATUS  current
        DESCRIPTION
        "Identifies which port position is being addressed. 
        This chassis number and slot number uniquely identify each inventory entry.
        "
    ::= { setSineiEntry 3 }


    setSineiEnable OBJECT-TYPE
        SYNTAX  EnaValue
        MAX-ACCESS  read-write
        STATUS  current
        DESCRIPTION
        "Set the input port to enabled or disabled.
        "
    ::= { setSineiEntry 4 }


    setSineiFrequency OBJECT-TYPE
        SYNTAX  INTEGER (1544|6312)
        MAX-ACCESS  read-write
        STATUS  current
        DESCRIPTION
            "Set input signal frequency. 
            The frequency can be set: 1.544MHZ/ 6.312MHz.
            "
    ::= { setSineiEntry 5 }

    setSineiProvPql OBJECT-TYPE
        SYNTAX  INTEGER (1..9)
        MAX-ACCESS  read-write
        STATUS  current
        DESCRIPTION
        "Set the input port provisioned Priority Quality Level (PQL).

        Note: Valid values are 1 - 9.
        "
    ::= { setSineiEntry 6 }


    setSineiPriority OBJECT-TYPE
        SYNTAX  INTEGER (0..10)
        MAX-ACCESS  read-write
        STATUS  current
        DESCRIPTION
        "Set the input port priority level.
        '0' = monitoring, 
        '1' = highest priority,
        '10' = lowest priority.
        "
    ::= { setSineiEntry 7 }


    setSineiCSFlt OBJECT-TYPE
        SYNTAX  INTEGER
                {
                    off(1),
                    low(2),
                    high(3),
                    na(4)
                }
        MAX-ACCESS  read-write
        STATUS  current
        DESCRIPTION
        "Set input Port 1 for external Cesium (CS) fault alarm logic level. 
        off(1), -- function is disabled
        low(2), -- function is enabled, will trigger on low (0V) level
        high(3), -- function is enabled, will trigger on high (+5v) level
        na(4) -- not applicable

        Note: only available for port one.
        "
    ::= { setSineiEntry 8 }

    setSineiZeroPhase OBJECT-TYPE
        SYNTAX  INTEGER
                {
                    zeroPhA(1),
                    zeroPhB(2),
                    zeroPhAB(3)
                }
        MAX-ACCESS  read-write
        STATUS  current
        DESCRIPTION
        "Set the phase error to zero for this input port.
        ZEROPHA - set phase A error to zero,
        ZEROPHB - set phase B error to zero,
        ZEROPHAB - set phase A and B to zero.

        Note: This field only is meaningful during the write operation.
        "
    ::= { setSineiEntry 9 }



    -- *******************************************
    -- JAPANESE SINE INPUT ALARM THRESHOLD SETTING
    -- *******************************************

    setAlmThSineInpTable OBJECT-TYPE
    SYNTAX  SEQUENCE OF SetMsiEntry
    MAX-ACCESS  not-accessible
    STATUS  current
    DESCRIPTION
    "A list of Sine input alarm attributes and settings information.
    "
    ::= { setupSineInp 4 }

    setMsiEntry OBJECT-TYPE
    SYNTAX  SetMsiEntry
    MAX-ACCESS  not-accessible
    STATUS  current
    DESCRIPTION
    "Input alarm attributes and settings.
    setMsiChassis
        Identifies which chassis is being addressed. 
    setMsiSlot
        Identifies which slot position is being addressed. 
    setMsiPort
        Identifies which port position is being addressed. 
    setMsiMtieStd
        Set the input port setting of the MTIE limits to predefined values.
    setMsiMtie10EL1
        Set the input port MTIE 10 seconds error threshold for the first limit setting.
    setMsiMtie10EL2
        Set the input port MTIE 10 seconds error threshold for the second limit setting.
    setMsiMtie10CL1
        Set the input port MTIE 10 seconds clear threshold for the first limit setting.
    setMsiMtie10CL2
        Set the input port MTIE 10 seconds clear threshold for the second limit setting.
    setMsiMtie100EL1
        Set the input port MTIE 100 seconds error threshold for the first limit setting.
    setMsiMtie100EL2
        Set the input port MTIE 100 seconds error threshold for the second limit setting.
    setMsiMtie100CL1
        Set the input port MTIE 100 seconds clear threshold for the first limit setting.
    setMsiMtie100CL2
        Set the input port MTIE 100 seconds clear threshold for the second limit setting.
    setMsiMtie1000EL1
        Set the input port MTIE 1000 seconds error threshold for the first limit setting.
    setMsiMtie1000EL2
        Set the input port MTIE 1000 seconds error threshold for the second limit setting.
    setMsiMtie1000CL1
        Set the input port MTIE 1000 seconds clear threshold for the first limit setting.
    setMsiMtie1000CL2
        Set the input port MTIE 1000 seconds clear threshold for the second limit setting.
    setMsiMtie10000EL1
        Set the input port MTIE 10000 seconds error threshold for the first limit setting.
    setMsiMtie10000EL2
        Set the input port MTIE 10000 seconds error threshold for the second limit setting.
    setMsiMtie10000CL1
        Set the input port MTIE 10000 seconds clear threshold for the first limit setting.
    setMsiMtie10000CL2
        Set the input port MTIE 10000 seconds clear threshold for the second limit setting.
    setMsiMtie100000EL1
        Set the input port MTIE 100000 seconds error threshold for the first limit setting.
    setMsiMtie100000EL2
        Set the input port MTIE 100000 seconds error threshold for the second limit setting.
    setMsiMtie100000CL1
        Set the input port MTIE 100000 seconds clear threshold for the first limit setting.
    setMsiMtie100000CL2
        Set the input port MTIE 100000 seconds clear threshold for the second limit setting.
    setMsiFreqAErrLmt
        Set the input port frequency error threshold for clock A.
    setMsiFreqAClrLmt
        Set the input port frequency clear threshold for clock A.
    setMsiFreqATau
        Set the Time constant (tau), in seconds, used for the calculation of the Average Frequency versus clock A.
    setMsiFreqBErrLmt
        Set the input port frequency error threshold for clock B.
    setMsiFreqBClrLmt
        Set the input port frequency clear threshold for clock B.
    setMsiFreqBTau
        Set the Time constant (tau), in seconds, used for the calculation of the Average Frequency versus clock B.
    "
    INDEX   { setMsiChassis, setMsiSlot, setMsiPort }
    ::= { setAlmThSineInpTable 1 }

    SetMsiEntry ::=
        SEQUENCE {
            setMsiChassis
                INTEGER,    
            setMsiSlot
                INTEGER,    
            setMsiPort
                INTEGER,
            
            -- MTIE Threshold Setting
            setMsiMtieStd
                INTEGER,

            setMsiMtie10EL1
                INTEGER,
            setMsiMtie10EL2
                INTEGER,
            setMsiMtie10CL1
                INTEGER,
            setMsiMtie10CL2
                INTEGER,

            setMsiMtie100EL1
                INTEGER,
            setMsiMtie100EL2
                INTEGER,
            setMsiMtie100CL1
                INTEGER,
            setMsiMtie100CL2
                INTEGER,

            setMsiMtie1000EL1
                INTEGER,
            setMsiMtie1000EL2
                INTEGER,
            setMsiMtie1000CL1
                INTEGER,
            setMsiMtie1000CL2
                INTEGER,

            setMsiMtie10000EL1
                INTEGER,
            setMsiMtie10000EL2
                INTEGER,
            setMsiMtie10000CL1
                INTEGER,
            setMsiMtie10000CL2
                INTEGER,

            setMsiMtie100000EL1
                INTEGER,
            setMsiMtie100000EL2
                INTEGER,
            setMsiMtie100000CL1
                INTEGER,
            setMsiMtie100000CL2
                INTEGER,

            -- FREQ Threshold Setting
            setMsiFreqAErrLmt
                INTEGER,
            setMsiFreqAClrLmt
                INTEGER,
            setMsiFreqATau
                INTEGER,

            setMsiFreqBErrLmt
                INTEGER,
            setMsiFreqBClrLmt
                INTEGER,
            setMsiFreqBTau
                INTEGER
        }

    setMsiChassis OBJECT-TYPE
        SYNTAX  INTEGER (1..1)
        MAX-ACCESS  not-accessible
        STATUS  current
        DESCRIPTION
        "Identifies which chassis is being addressed. 
        This chassis number, slot number, and port number uniquely identify each inventory entry.

        Note: In the SSU2000, this number is always one. (i.e. in the main chassis)
        "
    ::= { setMsiEntry 1 }

    setMsiSlot OBJECT-TYPE
        SYNTAX  INTEGER (1..20)
        MAX-ACCESS  not-accessible
        STATUS  current
        DESCRIPTION
        "Identifies which slot is being addressed. 
        This chassis number, slot number, and port number uniquely identify each inventory entry.
        "
    ::= { setMsiEntry 2 }


    setMsiPort OBJECT-TYPE
        SYNTAX  INTEGER (1..3)
        MAX-ACCESS  not-accessible
        STATUS  current
        DESCRIPTION
        "Identifies which port is being addressed. 
        This chassis number, slot number, and port number uniquely identify each inventory entry.
        "
    ::= { setMsiEntry 3 }

    setMsiMtieStd OBJECT-TYPE
        SYNTAX  INTEGER
                {
                    prs(1),
                    ds1(2),
                    g811(3),
                    g823(4)
                }
        MAX-ACCESS  read-write
        STATUS  current
        DESCRIPTION
        "Set the input port setting of the MTIE limits to predefined values.
        prs(1), -- ANSI T1.101 PRS MTIE MASK
        ds1(2), -- ANSI T1.101 DS1 MTIE MASK
        g811(3), -- G.811 (PRC) MTIE MASK
        g823(4) -- G.823 (SSU) MTIE MASK

        This field is only meaningful for a write operation. 
        "
    ::= { setMsiEntry 4 }

    setMsiMtie10EL1 OBJECT-TYPE
        SYNTAX  INTEGER (0..60000)
        MAX-ACCESS  read-write
        STATUS  current
        DESCRIPTION
        "Set the input port MTIE 10 seconds error threshold for the first limit setting.
        "
    ::= { setMsiEntry 5 }

    setMsiMtie10EL2 OBJECT-TYPE
        SYNTAX  INTEGER (0..60000)
        MAX-ACCESS  read-write
        STATUS  current
        DESCRIPTION
        "Set the input port MTIE 10 seconds error threshold for the second limit setting.
        "
    ::= { setMsiEntry 6 }

    setMsiMtie10CL1 OBJECT-TYPE
        SYNTAX  INTEGER (0..60000)
        MAX-ACCESS  read-write
        STATUS  current
        DESCRIPTION
        "Set the input port MTIE 10 seconds clear threshold for the first limit setting.
        "
    ::= { setMsiEntry 7 }

    setMsiMtie10CL2 OBJECT-TYPE
        SYNTAX  INTEGER (0..60000)
        MAX-ACCESS  read-write
        STATUS  current
        DESCRIPTION
        "Set the input port MTIE 10 seconds clear threshold for the second limit setting.
        "
    ::= { setMsiEntry 8 }



    setMsiMtie100EL1 OBJECT-TYPE
        SYNTAX  INTEGER (0..60000)
        MAX-ACCESS  read-write
        STATUS  current
        DESCRIPTION
        "Set the input port MTIE 100 seconds error threshold for the first limit setting.
        "
    ::= { setMsiEntry 9 }

    setMsiMtie100EL2 OBJECT-TYPE
        SYNTAX  INTEGER (0..60000)
        MAX-ACCESS  read-write
        STATUS  current
        DESCRIPTION
        "Set the input port MTIE 100 seconds error threshold for the second limit setting.
        "
    ::= { setMsiEntry 10 }

    setMsiMtie100CL1 OBJECT-TYPE
        SYNTAX  INTEGER (0..60000)
        MAX-ACCESS  read-write
        STATUS  current
        DESCRIPTION
        "Set the input port MTIE 100 seconds clear threshold for the first limit setting.
        "
    ::= { setMsiEntry 11 }

    setMsiMtie100CL2 OBJECT-TYPE
        SYNTAX  INTEGER (0..60000)
        MAX-ACCESS  read-write
        STATUS  current
        DESCRIPTION
        "Set the input port MTIE 100 seconds clear threshold for the second limit setting.
        "
    ::= { setMsiEntry 12 }


    setMsiMtie1000EL1 OBJECT-TYPE
        SYNTAX  INTEGER (0..60000)
        MAX-ACCESS  read-write
        STATUS  current
        DESCRIPTION
        "Set the input port MTIE 1000 seconds error threshold for the first limit setting.
        "
    ::= { setMsiEntry 13 }

    setMsiMtie1000EL2 OBJECT-TYPE
        SYNTAX  INTEGER (0..60000)
        MAX-ACCESS  read-write
        STATUS  current
        DESCRIPTION
        "Set the input port MTIE 1000 seconds error threshold for the second limit setting.
        "
    ::= { setMsiEntry 14 }

    setMsiMtie1000CL1 OBJECT-TYPE
        SYNTAX  INTEGER (0..60000)
        MAX-ACCESS  read-write
        STATUS  current
        DESCRIPTION
        "Set the input port MTIE 1000 seconds clear threshold for the first limit setting.
        "
    ::= { setMsiEntry 15 }

    setMsiMtie1000CL2 OBJECT-TYPE
        SYNTAX  INTEGER (0..60000)
        MAX-ACCESS  read-write
        STATUS  current
        DESCRIPTION
        "Set the input port MTIE 1000 seconds clear threshold for the second limit setting.
        "
    ::= { setMsiEntry 16 }



    setMsiMtie10000EL1 OBJECT-TYPE
        SYNTAX  INTEGER (0..60000)
        MAX-ACCESS  read-write
        STATUS  current
        DESCRIPTION
        "Set the input port MTIE 10000 seconds error threshold for the first limit setting.
        "
    ::= { setMsiEntry 17 }

    setMsiMtie10000EL2 OBJECT-TYPE
        SYNTAX  INTEGER (0..60000)
        MAX-ACCESS  read-write
        STATUS  current
        DESCRIPTION
        "Set the input port MTIE 10000 seconds error threshold for the second limit setting.
        "
    ::= { setMsiEntry 18 }


    setMsiMtie10000CL1 OBJECT-TYPE
        SYNTAX  INTEGER (0..60000)
        MAX-ACCESS  read-write
        STATUS  current
        DESCRIPTION
        "Set the input port MTIE 10000 seconds clear threshold for the first limit setting.
        "
    ::= { setMsiEntry 19 }

    setMsiMtie10000CL2 OBJECT-TYPE
        SYNTAX  INTEGER (0..60000)
        MAX-ACCESS  read-write
        STATUS  current
        DESCRIPTION
        "Set the input port MTIE 10000 seconds clear threshold for the second limit setting.
        "
    ::= { setMsiEntry 20 }


    setMsiMtie100000EL1 OBJECT-TYPE
        SYNTAX  INTEGER (0..60000)
        MAX-ACCESS  read-write
        STATUS  current
        DESCRIPTION
        "Set the input port MTIE 100000 seconds error threshold for the first limit setting.
        "
    ::= { setMsiEntry 21 }

    setMsiMtie100000EL2 OBJECT-TYPE
        SYNTAX  INTEGER (0..60000)
        MAX-ACCESS  read-write
        STATUS  current
        DESCRIPTION
        "Set the input port MTIE 100000 seconds error threshold for the second limit setting.
        "
    ::= { setMsiEntry 22 }

    setMsiMtie100000CL1 OBJECT-TYPE
        SYNTAX  INTEGER (0..60000)
        MAX-ACCESS  read-write
        STATUS  current
        DESCRIPTION
        "Set the input port MTIE 100000 seconds clear threshold for the first limit setting.
        "
    ::= { setMsiEntry 23 }

    setMsiMtie100000CL2 OBJECT-TYPE
        SYNTAX  INTEGER (0..60000)
        MAX-ACCESS  read-write
        STATUS  current
        DESCRIPTION
        "Set the input port MTIE 100000 seconds clear threshold for the second limit setting.
        "
    ::= { setMsiEntry 24 }



    setMsiFreqAErrLmt OBJECT-TYPE
        SYNTAX  INTEGER (0..10000000)
        MAX-ACCESS  read-write
        STATUS  current
        DESCRIPTION
            "Sets input port frequency error threshold for clock A.
            "
    ::= { setMsiEntry 25 }

    setMsiFreqAClrLmt OBJECT-TYPE
        SYNTAX  INTEGER (0..10000000)
        MAX-ACCESS  read-write
        STATUS  current
        DESCRIPTION
            "Sets input port frequency clear threshold for clock A.
            "
    ::= { setMsiEntry 26 }

    setMsiFreqATau OBJECT-TYPE
        SYNTAX  INTEGER (10..1000)
        MAX-ACCESS  read-write
        STATUS  current
        DESCRIPTION
        "Sets the time constant (tau), in seconds, used for the calculation of the Average Frequency for clock A.
        "
    ::= { setMsiEntry 27 }


    setMsiFreqBErrLmt OBJECT-TYPE
        SYNTAX  INTEGER (0..10000000)
        MAX-ACCESS  read-write
        STATUS  current
        DESCRIPTION
            "Sets input port frequency error threshold for clock B.
            "
    ::= { setMsiEntry 28 }

    setMsiFreqBClrLmt OBJECT-TYPE
        SYNTAX  INTEGER (0..10000000)
        MAX-ACCESS  read-write
        STATUS  current
        DESCRIPTION
            "Sets input port frequency clear threshold for clock B.
            "
    ::= { setMsiEntry 29 }

    setMsiFreqBTau OBJECT-TYPE
        SYNTAX  INTEGER (10..1000)
        MAX-ACCESS  read-write
        STATUS  current
        DESCRIPTION
        "Sets the time constant (tau), in seconds, used for the calculation of the Average Frequency for clock B.
        "
    ::= { setMsiEntry 30 }

    -- ******************************************
    -- JAPANESE CC INPUT MODULE SETTING
    -- ******************************************

    setJccInpTable OBJECT-TYPE
    SYNTAX  SEQUENCE OF SetJcciEntry
    MAX-ACCESS  not-accessible
    STATUS  current
    DESCRIPTION
        "The list of CC Input attribute setup information. 
        "
   ::= { setupJccInp 2 }


    setJcciEntry OBJECT-TYPE
    SYNTAX  SetJcciEntry
    MAX-ACCESS  not-accessible
    STATUS  current
    DESCRIPTION
    "Input status and settings attributes.
    "
    INDEX   { setJcciChassis, setJcciSlot, setJcciPort }
    ::= { setJccInpTable 1 }

    SetJcciEntry ::=
        SEQUENCE {
            setJcciChassis
                INTEGER,    
            setJcciSlot
                INTEGER,    
            setJcciPort
                INTEGER,    
            setJcciEnable
                EnaValue,
            setJcciProvPql
                INTEGER,
            setJcciPriority
                INTEGER,
            setJcci400Hz
                OnValue,

            setJcciZeroPhase
                INTEGER
        }

    setJcciChassis OBJECT-TYPE
        SYNTAX  INTEGER (1..1)
        MAX-ACCESS  not-accessible
        STATUS  current
        DESCRIPTION
        "Identifies which chassis is being addressed. 
        This chassis number and slot number uniquely identify each inventory entry.

        Note: The input module can only reside in chassis 1 (main chassis).
        "
    ::= { setJcciEntry 1 }

    setJcciSlot OBJECT-TYPE
        SYNTAX  INTEGER (1..20)
        MAX-ACCESS  not-accessible
        STATUS  current
        DESCRIPTION
        "Identifies which slot position is being addressed. 
        This chassis number and slot number uniquely identify each inventory entry.
        "
    ::= { setJcciEntry 2 }


    setJcciPort OBJECT-TYPE
        SYNTAX  INTEGER (1..3)
        MAX-ACCESS  not-accessible
        STATUS  current
        DESCRIPTION
        "Identifies which port position is being addressed. 
        This chassis number and slot number uniquely identify each inventory entry.
        "
    ::= { setJcciEntry 3 }


    setJcciEnable OBJECT-TYPE
        SYNTAX  EnaValue
        MAX-ACCESS  read-write
        STATUS  current
        DESCRIPTION
        "Set the input port to enabled or disabled.
        "
    ::= { setJcciEntry 4 }


    setJcciProvPql OBJECT-TYPE
        SYNTAX  INTEGER (1..9)
        MAX-ACCESS  read-write
        STATUS  current
        DESCRIPTION
        "Set the input port provisioned Priority Quality Level (PQL).

        Note: Valid values are 1 - 9.
        "
    ::= { setJcciEntry 5 }


    setJcciPriority OBJECT-TYPE
        SYNTAX  INTEGER (0..10)
        MAX-ACCESS  read-write
        STATUS  current
        DESCRIPTION
        "Set the input port priority level.
        '0' = monitoring, 
        '1' = highest priority,
        '10' = lowest priority.
        "
    ::= { setJcciEntry 6 }

    setJcci400Hz OBJECT-TYPE
        SYNTAX  OnValue
        MAX-ACCESS  read-write
        STATUS  current
        DESCRIPTION
        "Set the input port 400Hz signal attribute.
        "
    ::= { setJcciEntry 7 }

    setJcciZeroPhase OBJECT-TYPE
        SYNTAX  INTEGER
                {
                    zeroPhA(1),
                    zeroPhB(2),
                    zeroPhAB(3)
                }
        MAX-ACCESS  read-write
        STATUS  current
        DESCRIPTION
        "Set the phase error to zero for this input port.
        ZEROPHA - set phase A error to zero,
        ZEROPHB - set phase B error to zero,
        ZEROPHAB - set phase A and B to zero.

        Note: This field only is meaningful during the write operation.
        "
    ::= { setJcciEntry 8 }


    -- **************************************************************
    -- SSU2000 DS1/E1 OUT SETUP GROUP
    -- **************************************************************

    -- ******************************************
    -- DS1 OUTPUT MODULE
    -- ******************************************

    setDsTable OBJECT-TYPE
    SYNTAX  SEQUENCE OF SetDsEntry
    MAX-ACCESS  not-accessible
    STATUS  current
    DESCRIPTION
        "A list of DS1 output module status and settings.
        "
    ::= { setupDs1Out 2 }


    setDsEntry OBJECT-TYPE
    SYNTAX  SetDsEntry
    MAX-ACCESS  not-accessible
    STATUS  current
    DESCRIPTION
    "Set DS1 output attributes.
    "
    INDEX   { setDsChassis, setDsSlot}
    ::= { setDsTable 1 }

    SetDsEntry ::=
        SEQUENCE {
            setDsChassis
                INTEGER,    
            setDsSlot
                INTEGER,    
            setDsFrame
                INTEGER,    
            setDsBypass
                OnValue,    
            setDsZs
                OnValue,    
            setDsEnable
                OCTET STRING,   
            setDsLength
                OCTET STRING    
        }

    setDsChassis OBJECT-TYPE
        SYNTAX  INTEGER (1..5)
        MAX-ACCESS  not-accessible
        STATUS  current
        DESCRIPTION
        "Identifies which chassis is being addressed. 
        This chassis number and slot number uniquely identify each inventory entry.
        "
    ::= { setDsEntry 1 }

    setDsSlot OBJECT-TYPE
        SYNTAX  INTEGER (1..20)
        MAX-ACCESS  not-accessible
        STATUS  current
        DESCRIPTION
        "Identifies which slot is being addressed. 
        This chassis number and slot number uniquely identify each inventory entry.
        "
    ::= { setDsEntry 2 }


    setDsFrame OBJECT-TYPE
        SYNTAX  INTEGER
                {
                    esf(1),
                    d4(2)
                }
        MAX-ACCESS  read-write
        STATUS  current
        DESCRIPTION
        "Set the output signal framing mode. 
        The T1 framing mode is ESF or D4.
        "
    ::= { setDsEntry 3 }

    setDsBypass OBJECT-TYPE
        SYNTAX  OnValue
        MAX-ACCESS  read-write
        STATUS  current
        DESCRIPTION
        "Set Clock C, or bypass mode, to enable or disable.
        "
    ::= { setDsEntry 4 }

    setDsZs OBJECT-TYPE
        SYNTAX  OnValue
        MAX-ACCESS  read-write
        STATUS  current
        DESCRIPTION
        "Set the Zero Suppression to enable or disable.
        "
    ::= { setDsEntry 5 }


    setDsEnable OBJECT-TYPE
        SYNTAX  OCTET STRING (SIZE (20))
        MAX-ACCESS  read-write
        STATUS  current
        DESCRIPTION
        "Set the output ports to enabled or disabled.
           1 = enabled
           2 = disabled

        Note: Byte 1 = port 1, byte 20 = port 20.
        "
    ::= { setDsEntry 6 }

    setDsLength OBJECT-TYPE
        SYNTAX  OCTET STRING (SIZE (20))
        MAX-ACCESS  read-write
        STATUS  current
        DESCRIPTION
        "Set the cable length compensation for the output port.

        Cable length definitions:
        1 = 133 ft
        2 = 266 ft
        3 = 399 ft
        4 = 533 ft
        5 = 655 ft

        Note: Byte 1 = port 1, byte 20 = port 20.
        "
    ::= { setDsEntry 7 }



    -- ******************************************
    -- E1 OUTPUT MODULE
    -- ******************************************

    setE1Table OBJECT-TYPE
    SYNTAX  SEQUENCE OF SetE1Entry
    MAX-ACCESS  not-accessible
    STATUS  current
    DESCRIPTION
        "A list of DS1 output module status and settings.
        "
    ::= { setupE1Out 2 }


    setE1Entry OBJECT-TYPE
    SYNTAX  SetE1Entry
    MAX-ACCESS  not-accessible
    STATUS  current
    DESCRIPTION
    "Set DS1 output attributes.
    "
    INDEX   { setE1Chassis, setE1Slot}
    ::= { setE1Table 1 }

    SetE1Entry ::=
        SEQUENCE {
            setE1Chassis
                INTEGER,    
            setE1Slot
                INTEGER,    
            setE1Frame
                INTEGER,    
            setE1Bypass
                OnValue,    
            setE1Zs
                OnValue,    
            setE1Crc
                OnValue,    
            setE1SsmBit
                INTEGER,    
            setE1Enable
                OCTET STRING    
        }

    setE1Chassis OBJECT-TYPE
        SYNTAX  INTEGER (1..5)
        MAX-ACCESS  not-accessible
        STATUS  current
        DESCRIPTION
        "Identifies which chassis is being addressed. 
        This chassis number and slot number uniquely identify each inventory entry.
        "
    ::= { setE1Entry 1 }

    setE1Slot OBJECT-TYPE
        SYNTAX  INTEGER (1..20)
        MAX-ACCESS  not-accessible
        STATUS  current
        DESCRIPTION
        "Identifies which slot is being addressed. 
        This chassis number and slot number uniquely identify each inventory entry.
        "
    ::= { setE1Entry 2 }


    setE1Frame OBJECT-TYPE
        SYNTAX  INTEGER
                {
                    ccs(1),
                    cas(2)
                }
        MAX-ACCESS  read-write
        STATUS  current
        DESCRIPTION
        "Set the output signal framing mode. 
        1=ccs
        2=cas
        "
    ::= { setE1Entry 3 }

    setE1Bypass OBJECT-TYPE
        SYNTAX  OnValue
        MAX-ACCESS  read-write
        STATUS  current
        DESCRIPTION
        "Set Clock C, or bypass mode, to enable or disable.
        "
    ::= { setE1Entry 4 }

    setE1Zs OBJECT-TYPE
        SYNTAX  OnValue
        MAX-ACCESS  read-write
        STATUS  current
        DESCRIPTION
        "Set the Zero Suppression to enable or disable.
        "
    ::= { setE1Entry 5 }

    setE1Crc OBJECT-TYPE
        SYNTAX  OnValue
        MAX-ACCESS  read-write
        STATUS  current
        DESCRIPTION
        "Set the CRC error checking to enable or disable.
        "
    ::= { setE1Entry 6 }


    setE1SsmBit OBJECT-TYPE
        SYNTAX  INTEGER (4..8)
        MAX-ACCESS  read-write
        STATUS  current
        DESCRIPTION
        "Set output module E1 SSM bit position.
        bit=4 - 8

        Note: This field is only valid for E1 output module.
        "
    ::= { setE1Entry 7 }

    setE1Enable OBJECT-TYPE
        SYNTAX  OCTET STRING (SIZE(20))
        MAX-ACCESS  read-write
        STATUS  current
        DESCRIPTION
        "Set the output ports to enabled or disabled.
           1 = enabled
           2 = disabled

        Note: Byte 1 = port 1, byte 20 = port 20.
        "
    ::= { setE1Entry 8 }



    -- ******************************************
    -- 2048kHz OUTPUT MODULE
    -- ******************************************

    setCoTable OBJECT-TYPE
    SYNTAX  SEQUENCE OF SetCoEntry
    MAX-ACCESS  not-accessible
    STATUS  current
    DESCRIPTION
        "A list of 2048kHz output module status and settings.
        "
    ::= { setup2048Out 2 }

    setCoEntry OBJECT-TYPE
    SYNTAX  SetCoEntry
    MAX-ACCESS  not-accessible
    STATUS  current
    DESCRIPTION
    "Set 2048kHz output attributes.
    "
    INDEX   { setCoChassis, setCoSlot}
    ::= { setCoTable 1 }

    SetCoEntry ::=
        SEQUENCE {
            setCoChassis
                INTEGER,    
            setCoSlot
                INTEGER,    
            setCoBypass
                OnValue,    
            setCoFltMode
                INTEGER,    
            setCoEnable
                OCTET STRING,   
            setCoSquelch
                OCTET STRING    
        }

    setCoChassis OBJECT-TYPE
        SYNTAX  INTEGER (1..5)
        MAX-ACCESS  not-accessible
        STATUS  current
        DESCRIPTION
        "Identifies which chassis is being addressed. 
        This chassis number and slot number uniquely identify each inventory entry.
        "
    ::= { setCoEntry 1 }

    setCoSlot OBJECT-TYPE
        SYNTAX  INTEGER (1..20)
        MAX-ACCESS  not-accessible
        STATUS  current
        DESCRIPTION
        "Identifies which slot is being addressed. 
        This chassis number and slot number uniquely identify each inventory entry.
        "
    ::= { setCoEntry 2 }

    setCoBypass OBJECT-TYPE
        SYNTAX  OnValue
        MAX-ACCESS  read-write
        STATUS  current
        DESCRIPTION
        "Set Clock C, or bypass mode, to enable or disable.
        "
    ::= { setCoEntry 3 }

    setCoFltMode OBJECT-TYPE
        SYNTAX  INTEGER
                {
                    off(1),
                    on(2),
                    auto(3)
                }
        MAX-ACCESS  read-write
        STATUS  current
        DESCRIPTION
            "Set the signal fault mode for low level output signals
            off(1), -- will turn off the output and requires user issued command to turn it back on
            on(2), -- will not turn off when fault detected
            auto(3) -- will turn off the output and automatically turn back on when fault clears
            "
    ::= { setCoEntry 4 }

    setCoEnable OBJECT-TYPE
        SYNTAX  OCTET STRING (SIZE(20))
        MAX-ACCESS  read-write
        STATUS  current
        DESCRIPTION
        "Set the output ports to enabled or disabled.
           1 = enabled
           2 = disabled

        Note: Byte 1 = port 1, byte 20 = port 20.
        "
    ::= { setCoEntry 5 }

    setCoSquelch OBJECT-TYPE
        SYNTAX  OCTET STRING (SIZE(20))
        MAX-ACCESS  read-write
        STATUS  current
        DESCRIPTION
            "Set PQL threshold to turn port off.
            If the system PQL is below the PWL threshold the port is turned off (i.e. squelched).   
            
            Note: Byte 1 = port 1, byte 20 = port 20.
            The PQL value of each byte defined as follows:
            0 = disabled
            1-16 = Provision PQL value
            "
    ::= { setCoEntry 6 }

    -- ******************************************
    -- COMPOSITE CLOCK OUTPUT MODULE
    -- ******************************************

    setCcTable OBJECT-TYPE
    SYNTAX  SEQUENCE OF SetCcEntry
    MAX-ACCESS  not-accessible
    STATUS  current
    DESCRIPTION
        "A list of Composite Clock (CC) output module status and settings.
        "
    ::= { setupCCOut 2 }

    setCcEntry OBJECT-TYPE
    SYNTAX  SetCcEntry
    MAX-ACCESS  not-accessible
    STATUS  current
    DESCRIPTION
    "Set CC output attributes.
    "
    INDEX   { setCcChassis, setCcSlot}
    ::= { setCcTable 1 }

    SetCcEntry ::=
        SEQUENCE {
            setCcChassis
                INTEGER,    
            setCcSlot
                INTEGER,    
            setCcBypass
                OnValue,    
            setCcEnable
                OCTET STRING,   
            setCcDuty
                OCTET STRING,   
            setCcComp
                OCTET STRING    
        }

    setCcChassis OBJECT-TYPE
        SYNTAX  INTEGER (1..5)
        MAX-ACCESS  not-accessible
        STATUS  current
        DESCRIPTION
        "Identifies which chassis is being addressed. 
        This chassis number and slot number uniquely identify each CC Output entry.
        "
    ::= { setCcEntry 1 }

    setCcSlot OBJECT-TYPE
        SYNTAX  INTEGER (1..20)
        MAX-ACCESS  not-accessible
        STATUS  current
        DESCRIPTION
        "Identifies which slot is being addressed. 
        This chassis number and slot number uniquely identify each CC Output entry.
        "
    ::= { setCcEntry 2 }

    setCcBypass OBJECT-TYPE
        SYNTAX  OnValue
        MAX-ACCESS  read-write
        STATUS  current
        DESCRIPTION
        "Set Clock C, or bypass mode, to enable or disable.
        "
    ::= { setCcEntry 3 }

    setCcEnable OBJECT-TYPE
        SYNTAX  OCTET STRING (SIZE(20))
        MAX-ACCESS  read-write
        STATUS  current
        DESCRIPTION
        "Set the output ports to enabled or disabled.
           1 = enabled
           2 = disabled

        Note: Byte 1 = port 1, byte 20 = port 20.
        "
    ::= { setCcEntry 4 }


    setCcDuty OBJECT-TYPE
        SYNTAX  OCTET STRING (SIZE(20))
        MAX-ACCESS  read-write
        STATUS  current
        DESCRIPTION
        "Set the output duty cycle for the output ports.
        1 = 63/37 duty cycle.
        2 = 50/50 duty cycle.

        Note: Byte 1 = port 1, byte 20 = port 20.
        "
    ::= { setCcEntry 5 }


    setCcComp OBJECT-TYPE
        SYNTAX  OCTET STRING (SIZE(20))
        MAX-ACCESS  read-write
        STATUS  current
        DESCRIPTION
        "Set the output phase (cable) compensation for the output ports.

        The equivalent cable length:
        1 = 2200 ft,
        2 = 1925 ft,
        3 = 1650 ft, 
        4 = 1375 ft,
        5 = 1100 ft,
        6 = 825 ft,
        7 = 550 ft,
        8 = 275 ft.

        Note: Byte 1 = port 1, byte 20 = port 20.
        "
    ::= { setCcEntry 6 }


    -- ******************************************
    -- RS422 OUTPUT MODULE
    -- ******************************************

    set422oTable OBJECT-TYPE
    SYNTAX  SEQUENCE OF Set422oEntry
    MAX-ACCESS  not-accessible
    STATUS  current
    DESCRIPTION
        "A list of 2048kHz output module status and settings.
        "
    ::= { setup422Out 2 }

    set422oEntry OBJECT-TYPE
    SYNTAX  Set422oEntry
    MAX-ACCESS  not-accessible
    STATUS  current
    DESCRIPTION
    "Set 422 output attributes.
    "
    INDEX   { set422oChassis, set422oSlot}
    ::= { set422oTable 1 }

    Set422oEntry ::=
        SEQUENCE {
            set422oChassis
                INTEGER,    
            set422oSlot
                INTEGER,    
            set422oBypass
                OnValue,    
            set422oFltMode
                INTEGER,    
            set422oEnable
                OCTET STRING,   
            set422oFrequency
                OCTET STRING    
        }

    set422oChassis OBJECT-TYPE
        SYNTAX  INTEGER (1..5)
        MAX-ACCESS  not-accessible
        STATUS  current
        DESCRIPTION
        "Identifies which chassis is being addressed. 
        This chassis number and slot number uniquely identify each inventory entry.
        "
    ::= { set422oEntry 1 }

    set422oSlot OBJECT-TYPE
        SYNTAX  INTEGER (1..20)
        MAX-ACCESS  not-accessible
        STATUS  current
        DESCRIPTION
        "Identifies which slot is being addressed. 
        This chassis number and slot number uniquely identify each inventory entry.
        "
    ::= { set422oEntry 2 }

    set422oBypass OBJECT-TYPE
        SYNTAX  OnValue
        MAX-ACCESS  read-write
        STATUS  current
        DESCRIPTION
        "Set Clock C, or bypass mode, to enable or disable.
        "
    ::= { set422oEntry 3 }

    set422oFltMode OBJECT-TYPE
        SYNTAX  INTEGER
                {
                    off(1),
                    on(2),
                    auto(3)
                }
        MAX-ACCESS  read-write
        STATUS  current
        DESCRIPTION
            "Set the signal fault mode for low level output signals
            off(1), -- will turn off the output and requires user issued command to turn it back on
            on(2), -- will not turn off when fault detected
            auto(3) -- will turn off the output and automatically turn back on when fault clears
            "
    ::= { set422oEntry 4 }

    set422oEnable OBJECT-TYPE
        SYNTAX  OCTET STRING (SIZE(20))
        MAX-ACCESS  read-write
        STATUS  current
        DESCRIPTION
        "Set the output ports to enabled or disabled.
           1 = enabled
           2 = disabled

        Note: Byte 1 = port 1, byte 20 = port 20.
        "
    ::= { set422oEntry 5 }

    set422oFrequency OBJECT-TYPE
        SYNTAX  OCTET STRING (SIZE(20))
        MAX-ACCESS  read-write
        STATUS  current
        DESCRIPTION
        "Set frequency for each port on an RS422 output module.

           word 1 = port 1, word 10 = port 10.
           The frequency value of each port defined as follows:
           0 = 4kHz, 1-512 = 8kHz to 4096kHz with 8kHz per step.

         Note: each port use 2-bytes to set frequency.
           User can only set frequency on port 1 thru port 10.
           The port 1 and 11, port 2 and 12,.., port 10 and 20 have the same frequency setting.
           For example, when you set port1, you are set the same frequency for port 11.
       "
    ::= { set422oEntry 6 }


    -- ******************************************
    -- Selectable E1/2048 OUTPUT MODULE
    -- ******************************************

    setE12048oTable OBJECT-TYPE
    SYNTAX  SEQUENCE OF SetE12048oEntry
    MAX-ACCESS  not-accessible
    STATUS  current
    DESCRIPTION
        "A list of E1/2048 output module status and settings.
        "
    ::= { setupE12048Out 2 }

    setE12048oEntry OBJECT-TYPE
    SYNTAX  SetE12048oEntry
    MAX-ACCESS  not-accessible
    STATUS  current
    DESCRIPTION
    "Set E1/2048 output attributes.
    "
    INDEX   { setE12048oChassis, setE12048oSlot}
    ::= { setE12048oTable 1 }

    SetE12048oEntry ::=
        SEQUENCE {
            setE12048oChassis
                INTEGER,    
            setE12048oSlot
                INTEGER,    
            setE12048oBypass
                OnValue,    
            setE12048oZs
                OnValue,    
            setE12048oSignal
                OCTET STRING,   
            setE12048oEnable
                OCTET STRING,   
            setE12048oSquelch
                OCTET STRING,   
            setE12048oFrame
                INTEGER,    
            setE12048oCrc
                OnValue,    
            setE12048oSsm
                OnValue,    
            setE12048oSsmBit
                INTEGER 
        }

    setE12048oChassis OBJECT-TYPE
        SYNTAX  INTEGER (1..5)
        MAX-ACCESS  not-accessible
        STATUS  current
        DESCRIPTION
        "Identifies which chassis is being addressed. 
        This chassis number and slot number uniquely identify each inventory entry.
        "
    ::= { setE12048oEntry 1 }

    setE12048oSlot OBJECT-TYPE
        SYNTAX  INTEGER (1..20)
        MAX-ACCESS  not-accessible
        STATUS  current
        DESCRIPTION
        "Identifies which slot is being addressed. 
        This chassis number and slot number uniquely identify each inventory entry.
        "
    ::= { setE12048oEntry 2 }

    setE12048oBypass OBJECT-TYPE
        SYNTAX  OnValue
        MAX-ACCESS  read-write
        STATUS  current
        DESCRIPTION
        "Set Clock C, or bypass mode, to enable or disable.
        "
    ::= { setE12048oEntry 3 }

    setE12048oZs OBJECT-TYPE
        SYNTAX  OnValue
        MAX-ACCESS  read-write
        STATUS  current
        DESCRIPTION
        "Set the Zero Suppression to enable or disable.
        "
    ::= { setE12048oEntry 4 }

    setE12048oSignal OBJECT-TYPE
        SYNTAX  OCTET STRING (SIZE(20))
        MAX-ACCESS  read-write
        STATUS  current
        DESCRIPTION
        "Set the output ports to E1 or 2048kHz.
        1 = E1
        2 = 2048 kHz

        Note: byte 1 = port 1, byte 20 = port 20.
        "
    ::= { setE12048oEntry 5 }

    setE12048oEnable OBJECT-TYPE
        SYNTAX  OCTET STRING (SIZE(20))
        MAX-ACCESS  read-write
        STATUS  current
        DESCRIPTION
        "Set the output ports to enabled or disabled.
        1 = enabled
        2 = disabled

        Note: Byte 1 = port 1, byte 20 = port 20.
        "
    ::= { setE12048oEntry 6 }

    setE12048oSquelch OBJECT-TYPE
        SYNTAX  OCTET STRING (SIZE(20))
        MAX-ACCESS  read-write
        STATUS  current
        DESCRIPTION
        "Set the PQL squelch threshold for each port.
        If a PQL threshold is below the system PQL, this port is turned off (i.e. squelched).   
        0 = disabled
        1-16 = Provision PQL value

        Note: Byte 1 = port 1, byte 20 = port 20.
        "
    ::= { setE12048oEntry 7 }

    setE12048oFrame OBJECT-TYPE
        SYNTAX  INTEGER
                {
                    ccs(1),
                    cas(2)
                }
        MAX-ACCESS  read-write
        STATUS  current
        DESCRIPTION
        "Set E1 output signal framer mode.
        1 = CCS
        2 = CAS
        "
    ::= { setE12048oEntry 8 }

    setE12048oCrc OBJECT-TYPE
        SYNTAX  OnValue
        MAX-ACCESS  read-write
        STATUS  current
        DESCRIPTION
        "Set E1 output CRC error checking to on or off.
        "
    ::= { setE12048oEntry 9 }

    setE12048oSsm OBJECT-TYPE
        SYNTAX  OnValue
        MAX-ACCESS  read-write
        STATUS  current
        DESCRIPTION
        "Set E1 output SSM generation to on or off.
        "
    ::= { setE12048oEntry 10 }

    setE12048oSsmBit OBJECT-TYPE
        SYNTAX  INTEGER (4..8)
        MAX-ACCESS  read-write
        STATUS  current
        DESCRIPTION
        "Set E1 output SSM bit position.
        bit position = 4 - 8

        Note: This field is only valid for E1 output module.
        "
    ::= { setE12048oEntry 11 }

    -- ******************************************
    -- DS1 LRM MODULE
    -- ******************************************

    setLrmPTable OBJECT-TYPE
    SYNTAX  SEQUENCE OF SetLrmPEntry
    MAX-ACCESS  not-accessible
    STATUS  current
    DESCRIPTION
        "A list of DS1 LRM ports status and settings.
        "
    ::= { setupLrm 2 }

    setLrmPEntry OBJECT-TYPE
    SYNTAX  SetLrmPEntry
    MAX-ACCESS  not-accessible
    STATUS  current
    DESCRIPTION
    "Set DS1 LRM attributes.
    "
    INDEX   { setLrmPChassis, setLrmPSlot, setLrmPPort}
    ::= { setLrmPTable 1 }

    SetLrmPEntry ::=
        SEQUENCE {
            setLrmPChassis
                INTEGER,    
            setLrmPSlot
                INTEGER,    
            setLrmPPort
                INTEGER,    
            setLrmPEnable
                OnValue,    
            setLrmPLbo
                INTEGER,    
            setLrmPSlip
                INTEGER,    
            setLrmPBpv
                INTEGER,    
            setLrmPFlt
                INTEGER,    
            setLrmPCid
                DisplayString   
        }

    setLrmPChassis OBJECT-TYPE
        SYNTAX  INTEGER (1..5)
        MAX-ACCESS  not-accessible
        STATUS  current
        DESCRIPTION
        "Identifies which chassis is being addressed. 
        This chassis number, slot and port number uniquely identify each inventory entry.
        "
    ::= { setLrmPEntry 1 }

    setLrmPSlot OBJECT-TYPE
        SYNTAX  INTEGER (1..20)
        MAX-ACCESS  not-accessible
        STATUS  current
        DESCRIPTION
        "Identifies which slot is being addressed. 
        This chassis number, slot, and port number uniquely identify each inventory entry.
        "
    ::= { setLrmPEntry 2 }

    setLrmPPort OBJECT-TYPE
        SYNTAX  INTEGER (1..4)
        MAX-ACCESS  not-accessible
        STATUS  current
        DESCRIPTION
        "Identifies which port is being addressed. 
        This chassis number, slot, and port number uniquely identify each inventory entry.
        "
    ::= { setLrmPEntry 3 }

    setLrmPEnable OBJECT-TYPE
        SYNTAX  OnValue
        MAX-ACCESS  read-write
        STATUS  current
        DESCRIPTION
        "Set the LRM ports to enabled or disabled.
        "
    ::= { setLrmPEntry 4 }

    setLrmPLbo OBJECT-TYPE
        SYNTAX  INTEGER
                {
                    lbo133ft(1),
                    lbo266ft(2),
                    lbo399ft(3),
                    lbo533ft(4),
                    lbo655ft(5)
                }
        MAX-ACCESS  read-write
        STATUS  current
        DESCRIPTION
            "Set the Line Build-Out for the LRM port.
            1=lbo133ft
            2=lbo266ft
            3=lbo399ft
            4=lbo533ft
            5=lbo655ft
           "
    ::= { setLrmPEntry 5 }

    setLrmPSlip OBJECT-TYPE
        SYNTAX  INTEGER (0..255)
        MAX-ACCESS  read-write
        STATUS  current
        DESCRIPTION
            "Set the slip error threshold in 24 hours period and the value zero shall clear the slip accumulated errors.
            "
    ::= { setLrmPEntry 6 }

    setLrmPBpv OBJECT-TYPE
        SYNTAX  INTEGER
                {
                    clr(1),     -- clear the accumulated BPV errors
                    nop(2)      -- no operation
                }
        MAX-ACCESS  read-write
        STATUS  current
        DESCRIPTION
            "Clear the accumulated BPV errors
            clr(1),     -- clear the accumulated BPV errors
            nop(2)      -- no operation

            Note: This field only has meaning for a write operation.
            "
    ::= { setLrmPEntry 7 }

    setLrmPFlt OBJECT-TYPE
        SYNTAX  INTEGER
                {
                    squelch(1),     
                    ais(2)       
                }
        MAX-ACCESS  read-write
        STATUS  current
        DESCRIPTION
            "Set the Side 1 fault strategy
            "
    ::= { setLrmPEntry 8 }

    setLrmPCid OBJECT-TYPE
        SYNTAX  DisplayString (SIZE (0..43))
        MAX-ACCESS  read-write
        STATUS  current
        DESCRIPTION
            "Set the circuit id for LRM port
            The circuit id is an 0-43 character string with all ascii printable characters.
            "
    ::= { setLrmPEntry 9 }


    -- ******************************************
    -- E1 LRM MODULE
    -- ******************************************

    setLrme1PTable OBJECT-TYPE
    SYNTAX  SEQUENCE OF SetLrme1PEntry
    MAX-ACCESS  not-accessible
    STATUS  current
    DESCRIPTION
        "A list of E1 LRM ports status and settings.
        "
    ::= { setupLrmE1 2 }

    setLrme1PEntry OBJECT-TYPE
    SYNTAX  SetLrme1PEntry
    MAX-ACCESS  not-accessible
    STATUS  current
    DESCRIPTION
    "Set E1 LRM attributes.
    "
    INDEX   { setLrme1PChassis, setLrme1PSlot, setLrme1PPort}
    ::= { setLrme1PTable 1 }

    SetLrme1PEntry ::=
        SEQUENCE {
            setLrme1PChassis
                INTEGER,    
            setLrme1PSlot
                INTEGER,    
            setLrme1PPort
                INTEGER,    
            setLrme1PEnable
                OnValue,    
            setLrme1PSlip
                INTEGER,    
            setLrme1PBpv
                INTEGER,    
            setLrme1PFlt
                INTEGER,    
            setLrme1PCid
                DisplayString   
        }

    setLrme1PChassis OBJECT-TYPE
        SYNTAX  INTEGER (1..5)
        MAX-ACCESS  not-accessible
        STATUS  current
        DESCRIPTION
        "Identifies which chassis is being addressed. 
        This chassis number, slot and port number uniquely identify each inventory entry.
        "
    ::= { setLrme1PEntry 1 }

    setLrme1PSlot OBJECT-TYPE
        SYNTAX  INTEGER (1..20)
        MAX-ACCESS  not-accessible
        STATUS  current
        DESCRIPTION
        "Identifies which slot is being addressed. 
        This chassis number, slot and port number uniquely identify each inventory entry.
        "
    ::= { setLrme1PEntry 2 }

    setLrme1PPort OBJECT-TYPE
        SYNTAX  INTEGER (1..4)
        MAX-ACCESS  not-accessible
        STATUS  current
        DESCRIPTION
        "Identifies which port is being addressed. 
        This chassis number, slot and port number uniquely identify each inventory entry.
        "
    ::= { setLrme1PEntry 3 }

    setLrme1PEnable OBJECT-TYPE
        SYNTAX  OnValue
        MAX-ACCESS  read-write
        STATUS  current
        DESCRIPTION
        "Set the LRM ports to enabled or disabled.
        "
    ::= { setLrme1PEntry 4 }

    setLrme1PSlip OBJECT-TYPE
        SYNTAX  INTEGER (0..255)
        MAX-ACCESS  read-write
        STATUS  current
        DESCRIPTION
            "Set the slip error threshold in 24 hours period and the value zero shall clear the slip accumulated errors.
            "
    ::= { setLrme1PEntry 5 }

    setLrme1PBpv OBJECT-TYPE
        SYNTAX  INTEGER
                {
                    clr(1),     -- clear the accumulated BPV errors
                    nop(2)      -- no operation
                }
        MAX-ACCESS  read-write
        STATUS  current
        DESCRIPTION
            "Clear the accumulated BPV errors
            clr(1),     -- clear the accumulated BPV errors
            nop(2)      -- no operation

            Note: This field only has meaning for a write operation.
            "
    ::= { setLrme1PEntry 6 }

    setLrme1PFlt OBJECT-TYPE
        SYNTAX  INTEGER
                {
                    squelch(1),     
                    ais(2)       
                }
        MAX-ACCESS  read-write
        STATUS  current
        DESCRIPTION
            "Set the Side 1 fault strategy
            "
    ::= { setLrme1PEntry 7 }

    setLrme1PCid OBJECT-TYPE
        SYNTAX  DisplayString (SIZE (0..43))
        MAX-ACCESS  read-write
        STATUS  current
        DESCRIPTION
            "Set the circuit id for LRM port
            The circuit id is an 0-43 character string with all ascii printable characters.
            "
    ::= { setLrme1PEntry 8 }


    -- ******************************************
    -- JAPANESE SINE OUTPUT MODULE
    -- ******************************************

    setSineoTable OBJECT-TYPE
    SYNTAX  SEQUENCE OF SetSineoEntry
    MAX-ACCESS  not-accessible
    STATUS  current
    DESCRIPTION
        "A list of Sine output status and settings.
        "
    ::= { setupSineOut 2 }

    setSineoEntry OBJECT-TYPE
    SYNTAX  SetSineoEntry
    MAX-ACCESS  not-accessible
    STATUS  current
    DESCRIPTION
    "Set E1 LRM attributes.
    "
    INDEX   { setSineoChassis, setSineoSlot}
    ::= { setSineoTable 1 }

    SetSineoEntry ::=
        SEQUENCE {
            setSineoChassis
                INTEGER,    
            setSineoSlot
                INTEGER,    
            setSineoBypass
                OnValue,    
            setSineoFrequency
                INTEGER,    
            setSineoEnable
                OCTET STRING,   
            setSineoSquelch
                OCTET STRING    
        }

    setSineoChassis OBJECT-TYPE
        SYNTAX  INTEGER (1..5)
        MAX-ACCESS  not-accessible
        STATUS  current
        DESCRIPTION
        "Identifies which chassis is being addressed. 
        This chassis number and slot number uniquely identify each inventory entry.
        "
    ::= { setSineoEntry 1 }

    setSineoSlot OBJECT-TYPE
        SYNTAX  INTEGER (1..20)
        MAX-ACCESS  not-accessible
        STATUS  current
        DESCRIPTION
        "Identifies which slot is being addressed. 
        This chassis number and slot number uniquely identify each inventory entry.
        "
    ::= { setSineoEntry 2 }

    setSineoBypass OBJECT-TYPE
        SYNTAX  OnValue
        MAX-ACCESS  read-write
        STATUS  current
        DESCRIPTION
        "Set Clock C, or bypass mode, to enable or disable.
        "
    ::= { setSineoEntry 3 }

    setSineoFrequency OBJECT-TYPE
        SYNTAX  INTEGER (1544|6312)
        MAX-ACCESS  read-write
        STATUS  current
        DESCRIPTION
            "Set the output frequency 1.544 or 6.312 MHz.
            "
    ::= { setSineoEntry 4 }

    setSineoEnable OBJECT-TYPE
        SYNTAX  OCTET STRING (SIZE(20))
        MAX-ACCESS  read-write
        STATUS  current
        DESCRIPTION
        "Set the output ports to enabled or disabled.
           1 = enabled
           2 = disabled

        Note: Byte 1 = port 1, byte 20 = port 20.
        "
    ::= { setSineoEntry 5 }

    setSineoSquelch OBJECT-TYPE
        SYNTAX  OCTET STRING (SIZE(20))
        MAX-ACCESS  read-write
        STATUS  current
        DESCRIPTION
            "Set PQL threshold to turn port off.
            If the system PQL is below the PWL threshold the port is turned off (i.e. squelched).   
            
            Note: Byte 1 = port 1, byte 20 = port 20.
            The PQL value of each byte defined as follows:
            0 = disabled
            1-16 = Provision PQL value
            "
    ::= { setSineoEntry 6 }


    -- ******************************************
    -- 64+8+4 (JAPANESE) CC OUTPUT MODULE
    -- ******************************************

    setJccoTable OBJECT-TYPE
    SYNTAX  SEQUENCE OF SetJccoEntry
    MAX-ACCESS  not-accessible
    STATUS  current
    DESCRIPTION
        "A list of JCC output status and settings.
        "
    ::= { setupJccOut 2 }

    setJccoEntry OBJECT-TYPE
    SYNTAX  SetJccoEntry
    MAX-ACCESS  not-accessible
    STATUS  current
    DESCRIPTION
    "Set JCC output attributes.
    "
    INDEX   { setJccoChassis, setJccoSlot}
    ::= { setJccoTable 1 }

    SetJccoEntry ::=
        SEQUENCE {
            setJccoChassis
                INTEGER,    
            setJccoSlot
                INTEGER,    
            setJccoBypass
                OnValue,    
            setJcco400Hz
                OnValue,    
            setJccoEnable
                OCTET STRING,   
            setJccoComp
                OCTET STRING    
        }

    setJccoChassis OBJECT-TYPE
        SYNTAX  INTEGER (1..5)
        MAX-ACCESS  not-accessible
        STATUS  current
        DESCRIPTION
        "Identifies which chassis is being addressed. 
        This chassis number and slot number uniquely identify each JCC Output entry.
        "
    ::= { setJccoEntry 1 }

    setJccoSlot OBJECT-TYPE
        SYNTAX  INTEGER (1..20)
        MAX-ACCESS  not-accessible
        STATUS  current
        DESCRIPTION
        "Identifies which slot is being addressed. 
        This chassis number and slot number uniquely identify each JCC Output entry.
        "
    ::= { setJccoEntry 2 }

    setJccoBypass OBJECT-TYPE
        SYNTAX  OnValue
        MAX-ACCESS  read-write
        STATUS  current
        DESCRIPTION
        "Set Clock C, or bypass mode, to enable or disable.
        "
    ::= { setJccoEntry 3 }

    setJcco400Hz OBJECT-TYPE
        SYNTAX  OnValue
        MAX-ACCESS  read-write
        STATUS  current
        DESCRIPTION
            "Set the 400Hz BPV removal. 
            A setting OFF removes this 400Hz component, and a setting ON  includes it.
            "
    ::= { setJccoEntry 4 }

    setJccoEnable OBJECT-TYPE
        SYNTAX  OCTET STRING (SIZE(20))
        MAX-ACCESS  read-write
        STATUS  current
        DESCRIPTION
        "Set the JCC output ports to enabled or disabled.
           1 = enabled
           2 = disabled

        Note: Byte 1 = port 1, byte 20 = port 20.
        "
    ::= { setJccoEntry 5 }


    setJccoComp OBJECT-TYPE
        SYNTAX  OCTET STRING (SIZE(20))
        MAX-ACCESS  read-write
        STATUS  current
        DESCRIPTION
        "The array represents the output phase compensation
        for all ports on an output module.

        Note: Byte 1 = port 1, byte 20 = port 20.
        The specifed byte value is 1 thru 8. 
        1 = no delay, 8 = highest delay.

        The equivalent cable length:
        1 = 2200 ft,
        2 = 1925 ft,
        3 = 1650 ft, 
        4 = 1375 ft,
        5 = 1100 ft,
        6 = 825 ft,
        7 = 550 ft,
        8 = 275 ft.
        "
    ::= { setJccoEntry 6 }


    -- ******************************************
    -- PACKETIME NTP MODULE SETUP GROUP
    -- ******************************************

    setPtNtpTable OBJECT-TYPE
    SYNTAX  SEQUENCE OF SetPtNtpEntry
    MAX-ACCESS  not-accessible
    STATUS  current
    DESCRIPTION
        "A list of PackeTime NTP status and settings.
        "
    ::= { setupPtNtp 1 }


    setPtNtpEntry OBJECT-TYPE
    SYNTAX  SetPtNtpEntry
    MAX-ACCESS  not-accessible
    STATUS  current
    DESCRIPTION
    "PackeTime NTP settings and attributes.
    "
    INDEX   { setPtNtpChassis, setPtNtpSlot}
    ::= { setPtNtpTable 1 }

    SetPtNtpEntry ::=
        SEQUENCE {
            setPtNtpChassis
                INTEGER,    
            setPtNtpSlot
                INTEGER,    
            setPtNtpCommit
                INTEGER,    
            setPtNtpProbe
                EnaValue,   
            setPtNtpBond
                EnaValue,   
            setPtNtpNTPd
                EnaValue,   
            setPtNtpTodsrcPrefer
                INTEGER,    
            setPtNtpTodsrcPriority
                INTEGER,    
            setPtNtpWeight
                INTEGER,    
            setPtNtpCompensation
                INTEGER,    
            setPtNtpPeerTimeout
                INTEGER,    
            setPtNtpPeerPrefer
                INTEGER,
            setPtNtpBypass
                OnValue,
            setPtNtpModActive
                YesValue,   
            setPtNtpPAActive
                YesValue,   
            setPtNtpPBActive
                YesValue    
        }

    setPtNtpChassis OBJECT-TYPE
        SYNTAX  INTEGER (1..5)
        MAX-ACCESS  not-accessible
        STATUS  current
        DESCRIPTION
        "Identifies which chassis is being addressed. 
        This chassis number and slot number uniquely identify each entry.
          "
    ::= { setPtNtpEntry 1 }

    setPtNtpSlot OBJECT-TYPE
        SYNTAX  INTEGER (1..20)
        MAX-ACCESS  not-accessible
        STATUS  current
        DESCRIPTION
        "Identifies which slot is being addressed. 
        This chassis number and slot number uniquely identify each entry.
          "
    ::= { setPtNtpEntry 2 }

    setPtNtpCommit OBJECT-TYPE
        SYNTAX  INTEGER 
                {
                    yes(1)
                }
        MAX-ACCESS  read-write
        STATUS  current
        DESCRIPTION
        "Commit all provisioned parameters, this action makes the parameters active. 
        This command will also store the parameters to non-volatile memory.

        Note: This field only has meaning for a writing (1).
        "
    ::= { setPtNtpEntry 3 }

    setPtNtpProbe OBJECT-TYPE
        SYNTAX  EnaValue
        MAX-ACCESS  read-write
        STATUS  current
        DESCRIPTION
        "Set the PackeTime Maintenance Port state; Enable or Disable.

        This node is obsolete, The setting is NOP.         
        "
    ::= { setPtNtpEntry 4 }


    setPtNtpBond OBJECT-TYPE
        SYNTAX  EnaValue
        MAX-ACCESS  read-write
        STATUS  current
        DESCRIPTION
        "Set Service port bonding state.
        1 = Enabled  
        2 = Disabled
        "
    ::= { setPtNtpEntry 5 }

    setPtNtpNTPd OBJECT-TYPE
        SYNTAX  EnaValue
        MAX-ACCESS  read-write
        STATUS  current
        DESCRIPTION
        "Set the NTP daemon state.
        1 = Enabled  
        2 = Disabled
        "
    ::= { setPtNtpEntry 6 }

    setPtNtpTodsrcPrefer OBJECT-TYPE
        SYNTAX  INTEGER
                {
                    todsrc(1),
                    peer(2)
                }
        MAX-ACCESS  read-write
        STATUS  current
        DESCRIPTION
        "Set the module's preferred time-source to be either TODSRC (1) or PEER (2). 
        TOD Source, either the TODSRC (GPS) or a NTP Peer if operating in Client mode
        "
    ::= { setPtNtpEntry 7 }

    setPtNtpTodsrcPriority OBJECT-TYPE
        SYNTAX  INTEGER (0..8)
        MAX-ACCESS  read-write
        STATUS  current
        DESCRIPTION
        "Set the Todsrc priority.
        The priority is the for the specified module as the TOD Source, 
        default is 0, range can be 0 through 8. Value 1 is the highest, 
        and 8 is the lowest. If the value is zero, the specified module 
        cannot be TOD Source.
        "
    ::= { setPtNtpEntry 8 }

    setPtNtpWeight OBJECT-TYPE
        SYNTAX  INTEGER (-1..100)
        MAX-ACCESS  read-write
        STATUS  current
        DESCRIPTION
        "Set the load distribution between portA/B in percent.
        For example, 70 means port-A get 70% of total bandwidth, 
        port-B gets remaining 30%. If port-A reaches 70% of total 
        bandwidth but port-B has no traffic, the 30% of bandwidth 
        will be wasted, port-A cannot use it. To allow either port 
        to use all the bandwidth, portAWeight  can be set to -1, 
        indicating no limit between port-A and port-B (either port-A 
        or port-B can get all the bandwidth, based on first come 
        first serve). Thus the range of this parameter -1 to 100. 
        For bonding mode, this parameter must be forced to -1, 
        so the active port can use 100% of the bandwidth. 
        For non-bonding mode, user can set any value between -1 to 100.
        "
    ::= { setPtNtpEntry 9 }

    setPtNtpCompensation OBJECT-TYPE
        SYNTAX  INTEGER (0..250)
        MAX-ACCESS  read-write
        STATUS  current
        DESCRIPTION
        "Set the Antenna cable delay compensation 
        in the case of GPS ToD Source(s) or the delay induced by the cable(s) used to connect 
        expansion shelves where the PackeTime ToD Source(s) is located in relationship to the Main shelf. 
        The time offset shall have a 100nS resolution, thus the Delay value shall be multiplied 
        by 100nS to provide 1PPS compensation. 
        Valid user compensation values range is 0 thru 250 for a total compensation range of 0 to 25000nS (25uS). 
        "
    ::= { setPtNtpEntry 10 }

    setPtNtpPeerTimeout OBJECT-TYPE
        SYNTAX  INTEGER (60..10000)
        MAX-ACCESS  read-write
        STATUS  current
        DESCRIPTION
        "Set the Peer Availability Timeout 
        The timer shall have a user settable range from 60 minutes to 10000 minutes, 
        with a default value of 1440 minutes
        "
    ::= { setPtNtpEntry 11 }

    setPtNtpPeerPrefer OBJECT-TYPE
        SYNTAX  INTEGER (0..8)
        MAX-ACCESS  read-write
        STATUS  current
        DESCRIPTION
        "Set the preferred peer from the peer list.
        The valid value is 0-8. The value zero means, there is no prefer. 
        This value has meaning, only when the specified peer is in the peer list.
        "
    ::= { setPtNtpEntry 12 }

    setPtNtpBypass OBJECT-TYPE
        SYNTAX  OnValue
        MAX-ACCESS  read-write
        STATUS  current
        DESCRIPTION
        "Set the clock C state, or bypass clock, to enabled or disabled.
        "
    ::= { setPtNtpEntry 13 }

    setPtNtpModActive OBJECT-TYPE
        SYNTAX  YesValue
        MAX-ACCESS  read-write
        STATUS  current
        DESCRIPTION
        "Set the specified module in the redundant pair to be Active. 
        Note1: This command only applies when the module in the redundant pair.
        Note2: This field only has meaning for a writing (1).
        Note3: Don't apply COMMIT after this command.
        "
    ::= { setPtNtpEntry 14 }

    setPtNtpPAActive OBJECT-TYPE
        SYNTAX  YesValue
        MAX-ACCESS  read-write
        STATUS  current
        DESCRIPTION
        "Set Port A is being manually selected as the active port. 
        Note1: This command only applies when the bonding mode is enabled and both ports are in network and Ethernet link up.
        Note2: This field only has meaning for a writing (1).
        Note3: Don't apply COMMIT after this command.
        "
    ::= { setPtNtpEntry 15 }

    setPtNtpPBActive OBJECT-TYPE
        SYNTAX  YesValue
        MAX-ACCESS  read-write
        STATUS  current
        DESCRIPTION
        "Set Port B is being manually selected as the active port. 
        Note1: This command only applies when the bonding mode is enabled and both ports are in network and Ethernet link up.
        Note2: This field only has meaning for a writing (1).
        Note3: Don't apply COMMIT after this command.
        "
    ::= { setPtNtpEntry 16 }

    -- ******************************************
    -- PACKETIME NTP MODULE PORT SETUP GROUP
    -- ******************************************

    setPtNtpPortTable OBJECT-TYPE
    SYNTAX  SEQUENCE OF SetPtNtpPortEntry
    MAX-ACCESS  not-accessible
    STATUS  current
    DESCRIPTION
          "PackeTime NTP ethernet port information.
          "
    ::= { setupPtNtp 2 }


    setPtNtpPortEntry OBJECT-TYPE
    SYNTAX  SetPtNtpPortEntry
    MAX-ACCESS  not-accessible
    STATUS  current
    DESCRIPTION
    "PackeTime NTP ethernet port state and settings information.
    setPtNtpPortChassis
        Identifies which chassis is being addressed. 
    setPtNtpPortSlot
        Identifies which slot is being addressed. 
    setPtNtpPortNum
        Identifies which port is being addressed. 
    setPtNtpPortAddr
        Set the port IP address         
    setPtNtpPortMask
        Set the port network mask           
    setPtNtpPortGate
        Set the port gateway address            
    "
    INDEX   { setPtNtpPortChassis, setPtNtpPortSlot, setPtNtpPortNum}
    ::= { setPtNtpPortTable 1 }

    SetPtNtpPortEntry ::=
        SEQUENCE {
            setPtNtpPortChassis
                INTEGER,    
            setPtNtpPortSlot
                INTEGER,    
            setPtNtpPortNum
                INTEGER,    
            setPtNtpPortAddr
                IpAddress,  
            setPtNtpPortMask
                IpAddress,  
            setPtNtpPortGate
                IpAddress   
        }

    setPtNtpPortChassis OBJECT-TYPE
        SYNTAX  INTEGER (1..5)
        MAX-ACCESS  not-accessible
        STATUS  current
        DESCRIPTION
        "Identifies which chassis is being addressed. 
        This chassis, slot, and port number uniquely identify each entry.
        "
    ::= { setPtNtpPortEntry 1 }

    setPtNtpPortSlot OBJECT-TYPE
        SYNTAX  INTEGER (1..20)
        MAX-ACCESS  not-accessible
        STATUS  current
        DESCRIPTION
        "Identifies which slot is being addressed. 
        This chassis, slot, and port number uniquely identify each entry.
        "
    ::= { setPtNtpPortEntry 2 }

    setPtNtpPortNum OBJECT-TYPE
        SYNTAX  INTEGER (1..3)
        MAX-ACCESS  not-accessible
        STATUS  current
        DESCRIPTION
        "Identifies which port is being addressed. 
        This chassis, slot, and port number uniquely identify each entry.

        PTNTP ethernet interface number. 
        1 = Service Port A 
        2 = Service Port B 
        3 = Maintenance Port
        "
    ::= { setPtNtpPortEntry 3 }

    setPtNtpPortAddr OBJECT-TYPE
        SYNTAX  IpAddress
        MAX-ACCESS  read-write
        STATUS  current
        DESCRIPTION
        "Set the port IP address            
        "
    ::= { setPtNtpPortEntry 4 }

    setPtNtpPortMask OBJECT-TYPE
        SYNTAX  IpAddress
        MAX-ACCESS  read-write
        STATUS  current
        DESCRIPTION
        "Set the port network mask          
        "
    ::= { setPtNtpPortEntry 5 }

    setPtNtpPortGate OBJECT-TYPE
        SYNTAX  IpAddress
        MAX-ACCESS  read-write
        STATUS  current
        DESCRIPTION
        "Set the port gateway address           
        "
    ::= { setPtNtpPortEntry 6 }


    -- ******************************************
    -- PACKETIME NTP MODULE PEER SETUP GROUP
    -- EXTERNAL NTP SERVER
    -- ******************************************

    setPtNtpPeerTable OBJECT-TYPE
    SYNTAX  SEQUENCE OF SetPtNtpPeerEntry
    MAX-ACCESS  not-accessible
    STATUS  current
    DESCRIPTION
    "List of PackeTime NTP Peer entries. 
    Entries are indexed by the values of setPtNtpPeerChassis, setPtNtpPeerSlot  and setPtNtpPortNum.
    "
    ::= { setupPtNtp 3 }

    setPtNtpPeerEntry OBJECT-TYPE
    SYNTAX  SetPtNtpPeerEntry
    MAX-ACCESS  not-accessible
    STATUS  current
    DESCRIPTION
    "Set PackeTime NTP peer state and settings.
    setPtNtpPeerChassis
        Identifies which chassis is being addressed. 
    setPtNtpPeerSlot
        Identifies which slot is being addressed. 
    setPtNtpPeerNum
        Identifies which ntp peer is being addressed. 
    setPtNtpPeerAddr
        Set Peer IP address in peer table.
    setPtNtpPeerPmin
        Set the minimum request rate in seconds for CLIENT mode. 
    setPtNtpPeerPmax
        Set the maximum request rate in seconds for CLIENT mode. 
    setPtNtpPeerKeyId
        Set keyId to be used to lookup authentication key, 
    "
    INDEX   { setPtNtpPeerChassis, setPtNtpPeerSlot, setPtNtpPeerNum}
    ::= { setPtNtpPeerTable 1 }

    SetPtNtpPeerEntry ::=
        SEQUENCE {
            setPtNtpPeerChassis
                INTEGER,    
            setPtNtpPeerSlot
                INTEGER,    
            setPtNtpPeerNum
                INTEGER,    
            setPtNtpPeerAddr
                IpAddress,  
            setPtNtpPeerPmin
                INTEGER,    
            setPtNtpPeerPmax
                INTEGER,    
            setPtNtpPeerKeyId
                INTEGER 
        }

    setPtNtpPeerChassis OBJECT-TYPE
        SYNTAX  INTEGER (1..5)
        MAX-ACCESS  not-accessible
        STATUS  current
        DESCRIPTION
        "Identifies which chassis is being addressed. 
        This chassis, slot, and peer number uniquely identify each entry.
        "
    ::= { setPtNtpPeerEntry 1 }

    setPtNtpPeerSlot OBJECT-TYPE
        SYNTAX  INTEGER (1..20)
        MAX-ACCESS  not-accessible
        STATUS  current
        DESCRIPTION
        "Identifies which slot is being addressed. 
        This chassis, slot, and peer number uniquely identify each entry.
        "
    ::= { setPtNtpPeerEntry 2 }

    setPtNtpPeerNum OBJECT-TYPE
        SYNTAX  INTEGER (1..8)
        MAX-ACCESS  not-accessible
        STATUS  current
        DESCRIPTION
        "Identifies which ntp peer is being addressed. 
        This chassis, slot, and peer number uniquely identify each entry.
        "
    ::= { setPtNtpPeerEntry 3 }

    setPtNtpPeerAddr OBJECT-TYPE
        SYNTAX  IpAddress
        MAX-ACCESS  read-write
        STATUS  current
        DESCRIPTION
        "Set Peer IP address in peer table.
        Write zero IP address will delete this IP address from peer table.
        "
    ::= { setPtNtpPeerEntry 4 }

    setPtNtpPeerPmin OBJECT-TYPE
        SYNTAX  INTEGER (16|32|64|128|256|512|1024)
        MAX-ACCESS  read-write
        STATUS  current
        DESCRIPTION
        "Set the minimum request rate in seconds for CLIENT mode, 
        the default is 16, the range is 16, 32, 64, 128, 256, 512, and 1024.
        "
    ::= { setPtNtpPeerEntry 5 }

    setPtNtpPeerPmax OBJECT-TYPE
        SYNTAX  INTEGER (16|32|64|128|256|512|1024)
        MAX-ACCESS  read-write
        STATUS  current
        DESCRIPTION
        "Set the maximum request rate in seconds for CLIENT mode, 
        the default is 64, the range is 16, 32, 64, 128, 256, 512, and 1024.
        "
    ::= { setPtNtpPeerEntry 6 }

    setPtNtpPeerKeyId OBJECT-TYPE
        SYNTAX  INTEGER (0..65534)
        MAX-ACCESS  read-write
        STATUS  current
        DESCRIPTION
        "Set keyId to be used to lookup authentication key, 
        the default is 0 (no authentication), the range is 0 through 65534
        "
    ::= { setPtNtpPeerEntry 7 }

    -- ******************************************
    -- PACKETIME NTP MODULE AUTH SETUP GROUP
    -- ******************************************

    setPtNtpAuthTable OBJECT-TYPE
    SYNTAX  SEQUENCE OF SetPtNtpAuthEntry
    MAX-ACCESS  not-accessible
    STATUS  current
    DESCRIPTION
    "A list of PackeTime NTP authentication entries. 
    The number of entries are given by the values of setPtNtpAuthChassis, setPtNtpAuthSlot and setPtNtpAuthNum.
    "
    ::= { setupPtNtp 4 }

    setPtNtpAuthEntry OBJECT-TYPE
    SYNTAX  SetPtNtpAuthEntry
    MAX-ACCESS  not-accessible
    STATUS  current
    DESCRIPTION
    "Set PackeTime NTP authentication state and settings.
    PackeTime NTP authentication attributes.
    setPtNtpAuthChassis
        Identifies which chassis is being addressed. 
    setPtNtpAuthSlot
        Identifies which slot is being addressed. 
    setPtNtpAuthNum
        Identifies which authentication key is being addressed. 
    setPtNtpAuthKeyId
        Set the authentication key ID, 
    setPtNtpAuthKeyValue
        Set the NTP authentication key used to create the MD5 hash associated with the keyid. 
    "
    INDEX   { setPtNtpAuthChassis, setPtNtpAuthSlot, setPtNtpAuthNum}
    ::= { setPtNtpAuthTable 1 }

    SetPtNtpAuthEntry ::=
        SEQUENCE {
            setPtNtpAuthChassis
                INTEGER,    
            setPtNtpAuthSlot
                INTEGER,    
            setPtNtpAuthNum
                INTEGER,    
            setPtNtpAuthKeyId
                INTEGER,    
            setPtNtpAuthKeyValue
                DisplayString   
        }

    setPtNtpAuthChassis OBJECT-TYPE
        SYNTAX  INTEGER (1..5)
        MAX-ACCESS  not-accessible
        STATUS  current
        DESCRIPTION
        "Identifies which chassis is being addressed. 
        This chassis, slot, and authentication key number uniquely identify each entry.
        "
    ::= { setPtNtpAuthEntry 1 }

    setPtNtpAuthSlot OBJECT-TYPE
        SYNTAX  INTEGER (1..20)
        MAX-ACCESS  not-accessible
        STATUS  current
        DESCRIPTION
        "Identifies which slot is being addressed. 
        This chassis, slot, and authentication key number uniquely identify each entry.
        "
    ::= { setPtNtpAuthEntry 2 }

    setPtNtpAuthNum OBJECT-TYPE
        SYNTAX  INTEGER (1..16)
        MAX-ACCESS  not-accessible
        STATUS  current
        DESCRIPTION
        "Identifies which authentication key is being addressed. 
        This chassis, slot, and authentication key number uniquely identify each entry.
        "
    ::= { setPtNtpAuthEntry 3 }

    setPtNtpAuthKeyId OBJECT-TYPE
        SYNTAX  INTEGER (0..65534)
        MAX-ACCESS  read-write
        STATUS  current
        DESCRIPTION
        "Set KeyId is the authentication key ID, 
        default is 0 (no authentication), range 0 to 65534.
        Note: If this value is zero, no authentication is used.
        "
    ::= { setPtNtpAuthEntry 4 }

    setPtNtpAuthKeyValue OBJECT-TYPE
        SYNTAX  DisplayString (SIZE (0|8..32))
        MAX-ACCESS  read-write
        STATUS  current
        DESCRIPTION
        "Set the key is the NTP authentication key used to create the MD5 hash associated with the keyid. 
        The key is a comprised of up to 32 ASCII characters, a minimum of 8 characters is required.
        Note: the key value will not display and it is always displayed as null string.
        "
    ::= { setPtNtpAuthEntry 5 }

    -- ******************************************
    -- PACKETIME NTP MODULE ROUTE SETUP GROUP
    -- ******************************************

    setPtNtpRouteTable OBJECT-TYPE
    SYNTAX  SEQUENCE OF SetPtNtpRouteEntry
    MAX-ACCESS  not-accessible
    STATUS  current
    DESCRIPTION
    "A list of PackeTime NTP route table entries. 

    Static routing describes a system that does not implement adaptive routing. In these systems routes through a data 
    network are described by fixed paths (statically). These routes are usually entered into the host by the system 
    administrator.        
    "
    ::= { setupPtNtp 5 }

    setPtNtpRouteEntry OBJECT-TYPE
    SYNTAX  SetPtNtpRouteEntry
    MAX-ACCESS  not-accessible
    STATUS  current
    DESCRIPTION
    "A PackeTime NTP route attributes and settings.
    setPtNtpRouteChassis
        Identifies which chassis is being addressed. 
    setPtNtpRouteSlot
        Identifies which slot is being addressed. 
    setPtNtpRouteNum
        Identifies which route number (index) is being addressed. 
    setPtNtpRouteAddr
        Set the route destination network or destination host.          
    setPtNtpRouteMask
        Set the netmask for the destination network.  
    setPtNtpRouteGate
        Set the gateway ip for the destination network.  
    setPtNtpRouteIface
        Set the module's network interface number.
    "
    INDEX   { setPtNtpRouteChassis, setPtNtpRouteSlot, setPtNtpRouteNum}
    ::= { setPtNtpRouteTable 1 }

    SetPtNtpRouteEntry ::=
        SEQUENCE {
            setPtNtpRouteChassis
                INTEGER,    
            setPtNtpRouteSlot
                INTEGER,    
            setPtNtpRouteNum
                INTEGER,    
            setPtNtpRouteAddr
                IpAddress,  
            setPtNtpRouteMask
                IpAddress,  
            setPtNtpRouteGate
                IpAddress,  
            setPtNtpRouteIface
                INTEGER 
        }

    setPtNtpRouteChassis OBJECT-TYPE
        SYNTAX  INTEGER (1..5)
        MAX-ACCESS  not-accessible
        STATUS  current
        DESCRIPTION
        "Identifies which chassis is being addressed. 
        This chassis, slot, and route number (index) uniquely identify each entry.
        "
    ::= { setPtNtpRouteEntry 1 }

    setPtNtpRouteSlot OBJECT-TYPE
        SYNTAX  INTEGER (1..20)
        MAX-ACCESS  not-accessible
        STATUS  current
        DESCRIPTION
        "Identifies which slot is being addressed. 
        This chassis, slot, and route number (index) uniquely identify each entry.
        "
    ::= { setPtNtpRouteEntry 2 }

    setPtNtpRouteNum OBJECT-TYPE
        SYNTAX  INTEGER (1..6)
        MAX-ACCESS  not-accessible
        STATUS  current
        DESCRIPTION
        "Identifies which route number is being addressed. 
        This chassis, slot, and route number (index) uniquely identify each entry.
        "
    ::= { setPtNtpRouteEntry 3 }

    setPtNtpRouteAddr OBJECT-TYPE
        SYNTAX  IpAddress
        MAX-ACCESS  read-write
        STATUS  current
        DESCRIPTION
        "Set the route destination network or destination host.         
        Write a new Route IP address will put this new IP into table.
        Write zero IP address will delete this IP address from table.
        "
    ::= { setPtNtpRouteEntry 4 }

    setPtNtpRouteMask OBJECT-TYPE
        SYNTAX  IpAddress
        MAX-ACCESS  read-write
        STATUS  current
        DESCRIPTION
        "Set the netmask for the destination network;  
        '255.255.255.255' for a host destination and 
        '0.0.0.0' for the default route
        "
    ::= { setPtNtpRouteEntry 5 }

    setPtNtpRouteGate OBJECT-TYPE
        SYNTAX  IpAddress
        MAX-ACCESS  read-write
        STATUS  current
        DESCRIPTION
        "Set the gateway for the destination network.
        "
    ::= { setPtNtpRouteEntry 6 }

    setPtNtpRouteIface OBJECT-TYPE
        SYNTAX  INTEGER (1..3)
        MAX-ACCESS  read-write
        STATUS  current
        DESCRIPTION
        "Set the module's network interface number:
        1 = Service Port A 
        2 = Service Port B 
        3 = Bond0 (bonding of PortA and Port B) 
        "
    ::= { setPtNtpRouteEntry 7 }

    -- ******************************************
    -- PACKETIME NTP MODULE VLAN SETUP GROUP
    -- ******************************************

    setPtNtpVlanTable OBJECT-TYPE
    SYNTAX  SEQUENCE OF SetPtNtpVlanEntry
    MAX-ACCESS  not-accessible
    STATUS  current
    DESCRIPTION
    "List of PackeTime NTP vlan attributes.
    The Virtural Local Area Network is implemented per IEEE 802.1Q.
    "
    ::= { setupPtNtp 6 }


    setPtNtpVlanEntry OBJECT-TYPE
    SYNTAX  SetPtNtpVlanEntry
    MAX-ACCESS  not-accessible
    STATUS  current
    DESCRIPTION
    "A PackeTime NTP vlan attributes and settings:
    setPtNtpVlanChassis
        Identifies which chassis is being addressed. 
    setPtNtpVlanSlot
        Identifies which slot is being addressed. 
    setPtNtpVlan
        Set the VLAN state.
    setPtNtpVlanPAId
        Set the VLAN ID for Service Port A.
    setPtNtpVlanPAPriority
        Set the VLAN priority for Service Port A.
    setPtNtpVlanPBId
        Set the VLAN ID for Service Port B.
    setPtNtpVlanPBPriority
        Set the VLAN priority for Service Port B.
    setPtNtpVlanBondId
        Set the VLAN ID for Bonding of Service Ports of A and B 
    setPtNtpVlanBondPriority
        Set the VLAN priority for Bonding of Service Ports of A and B 
    "
INDEX   { setPtNtpVlanChassis, setPtNtpVlanSlot}
    ::= { setPtNtpVlanTable 1 }

    SetPtNtpVlanEntry ::=
        SEQUENCE {
            setPtNtpVlanChassis
                INTEGER,    
            setPtNtpVlanSlot
                INTEGER,    
            setPtNtpVlan
                EnaValue,   
            setPtNtpVlanPAId
                INTEGER,    
            setPtNtpVlanPAPriority
                INTEGER,    
            setPtNtpVlanPBId
                INTEGER,    
            setPtNtpVlanPBPriority
                INTEGER,
            setPtNtpVlanBondId
                INTEGER,    
            setPtNtpVlanBondPriority
                INTEGER 
        }

    setPtNtpVlanChassis OBJECT-TYPE
        SYNTAX  INTEGER (1..5)
        MAX-ACCESS  not-accessible
        STATUS  current
        DESCRIPTION
        "Identifies which chassis is being addressed. 
        This chassis and slot number uniquely identify each entry.
        "
    ::= { setPtNtpVlanEntry 1 }

    setPtNtpVlanSlot OBJECT-TYPE
        SYNTAX  INTEGER (1..20)
        MAX-ACCESS  not-accessible
        STATUS  current
        DESCRIPTION
        "Identifies which slot is being addressed. 
        This chassis and slot number uniquely identify each entry.
        "
    ::= { setPtNtpVlanEntry 2 }

    setPtNtpVlan OBJECT-TYPE
        SYNTAX  EnaValue
        MAX-ACCESS  read-write
        STATUS  current
        DESCRIPTION
        "Set the VLAN state.
        1 = Enabled  
        2 = Disabled
        "
    ::= { setPtNtpVlanEntry 3 }

    setPtNtpVlanPAId OBJECT-TYPE
        SYNTAX  INTEGER (0..4094)
        MAX-ACCESS  read-write
        STATUS  current
        DESCRIPTION
        "Set the VLAN ID for Service Port A, [0 - 4094]

        Note: The value has no meaning, only when the VLAN is enabled
        "
    ::= { setPtNtpVlanEntry 4 }

    setPtNtpVlanPAPriority OBJECT-TYPE
        SYNTAX  INTEGER (0..7)
        MAX-ACCESS  read-write
        STATUS  current
        DESCRIPTION
        "Set the VLAN Priority for Service Port A, [0 - 7]
        Note: The value has no meaning, only when the VLAN is enabled
        "
    ::= { setPtNtpVlanEntry 5 }

    setPtNtpVlanPBId OBJECT-TYPE
        SYNTAX  INTEGER (0..4094)
        MAX-ACCESS  read-write
        STATUS  current
        DESCRIPTION
        "Set the VLAN ID for Service Port B, [0 - 4094]
        Note: The value has no meaning, only when the VLAN is enabled
        "
    ::= { setPtNtpVlanEntry 6 }


    setPtNtpVlanPBPriority OBJECT-TYPE
        SYNTAX  INTEGER (0..7)
        MAX-ACCESS  read-write
        STATUS  current
        DESCRIPTION
        "Set the VLAN Priority for Service Port B, [0 - 7]
        Note: The value has no meaning, only when the VLAN is enabled
        "
    ::= { setPtNtpVlanEntry 7 }

    setPtNtpVlanBondId OBJECT-TYPE
        SYNTAX  INTEGER (0..4094)
        MAX-ACCESS  read-write
        STATUS  current
        DESCRIPTION
        "Set the VLAN ID for Bonding of Service Ports of A and B, [0 - 4094]
        Note: The value has no meaning, only when the VLAN is enabled
        "
    ::= { setPtNtpVlanEntry 8 }


    setPtNtpVlanBondPriority OBJECT-TYPE
        SYNTAX  INTEGER (0..7)
        MAX-ACCESS  read-write
        STATUS  current
        DESCRIPTION
        "Set the VLAN Priority for Bonding of Service Ports of A and B, [0 - 7]
        Note: The value has no meaning, only when the VLAN is enabled
        "
    ::= { setPtNtpVlanEntry 9 }

    -- **************************************************************
    -- **************************************************************
    -- SSU2000 GENERAL INFORMATION GROUP
    -- **************************************************************
    -- **************************************************************

    infoTable OBJECT-TYPE
    SYNTAX  SEQUENCE OF GiEntry
    MAX-ACCESS  not-accessible
    STATUS  current
    DESCRIPTION
          "A list of general information entries."
    ::= { general 1 }


    giEntry OBJECT-TYPE
    SYNTAX  GiEntry
    MAX-ACCESS  not-accessible
    STATUS  current
    DESCRIPTION
    "Set global module attributes.
    "
    INDEX   { giChassis, giSlot }
    ::= { infoTable 1 }

 
    GiEntry ::=
        SEQUENCE {
            giChassis
                INTEGER,    
            giSlot
                INTEGER,    
            giSystime
                Counter32,
            giElevation
                INTEGER,
            giSetup
                INTEGER,
            giRestart
                YesValue
        }

    giChassis OBJECT-TYPE
        SYNTAX  INTEGER (1..5)
        MAX-ACCESS  not-accessible
        STATUS  current
        DESCRIPTION
        "Identifies which chassis is being addressed. 
        This chassis number and slot number uniquely identify each inventory entry.
        "
    ::= { giEntry 1 }

    giSlot OBJECT-TYPE
        SYNTAX  INTEGER (1..20)
        MAX-ACCESS  not-accessible
        STATUS  current
        DESCRIPTION
        "Identifies which slot is being addressed. 
        This chassis number and slot number uniquely identify each inventory entry.
        "
    ::= { giEntry 2 }

    giSystime OBJECT-TYPE
        SYNTAX  Counter32
        MAX-ACCESS  read-only
        STATUS  current
        DESCRIPTION
        "Reports length of time (in seconds) a specified module has been operational since last reboot.
        Only apply to the CPU-based module. zero means Not Applicable.
        "
    ::= { giEntry 3 }

    giElevation OBJECT-TYPE
        SYNTAX  INTEGER (0 | 60..500000)
        MAX-ACCESS  read-write
        STATUS  current
        DESCRIPTION
        "The module alarm elevation time (in seconds).  
        Each module in the system can be set for  elevation time from 60 seconds to 500,000 seconds. 
        A setting of 0 (zero) means no elevation for the alarm.
        For example, when an alarm has been at MINOR level ontinuously for elevtime seconds, then it is elevated to the next level (MAJOR).

        Note: 0 = disabled.
        "
    ::= { giEntry 4 }


    giSetup OBJECT-TYPE
        SYNTAX  INTEGER
                {
                    factory(1),
                    user(2),
                    save(3)
                }
        MAX-ACCESS  read-write
        STATUS  current
        DESCRIPTION
        "Saves or restores the configuration of the specified module. 

        FACTORY - restores the module configuration to factory defaults.
        SAVE - will save the current configuration as User.
        USER - will restore the saved User configuration.

        Note: This field only has meaning for a write operation.
        Only apply to the CPU-based module.
        "
    ::= { giEntry 5 }


    giRestart OBJECT-TYPE
        SYNTAX  YesValue
        MAX-ACCESS  read-write
        STATUS  current
        DESCRIPTION
        "Restarts a module.
        Writing a '1' to this variable restarts (reboots) the module.

        Note: This field only has meaning for a write operation.
        Only apply to the CPU-based module.
        "
    ::= { giEntry 6 }



    -- **************************************************************
    -- **************************************************************
    -- SSU2000 MODULE EVENT GROUP
    -- **************************************************************
    -- **************************************************************

    -- ******************************************
    -- SCALAR METHODS
    -- ******************************************

    evCount OBJECT-TYPE
        SYNTAX  INTEGER (1..1000)
        MAX-ACCESS  read-write 
        STATUS  current
        DESCRIPTION
        "Reports total number of events to display. 
	    The number represents total number of events
	    we want to display. Its value ranges between 
	    1 and 1000.
        "
    ::= { event 1 }

    evType OBJECT-TYPE
        SYNTAX  INTEGER
                {
                    alarm(1),
                    report(2),
                    all(3)
                }
        MAX-ACCESS  read-write 
        STATUS  current
        DESCRIPTION
        "Reports which event type we want to display (functions as a display filter). 
        Set these values to the desired type you want to display:
        ALARM - for alarm type
        REPORT -  for event type
        ALL - for all (alarm and event) type.
        "
    ::= { event 2 }


    -- ******************************************
    -- EVENT TABLE
    -- ******************************************

    eventTable OBJECT-TYPE
    SYNTAX  SEQUENCE OF EvEntry
    MAX-ACCESS  not-accessible
    STATUS  current
    DESCRIPTION
    "Report of system event entries. 
    The number of entries is given by the value of evNumber. 
    The total entries are up to 1000."
    ::= { event 3 }


    evEntry OBJECT-TYPE
    SYNTAX  EvEntry
    MAX-ACCESS  not-accessible
    STATUS  current
    DESCRIPTION
    "An event entry containing objects of each event."
    INDEX   { evIndex }
    ::= { eventTable 1 }

 
    EvEntry ::=
        SEQUENCE {
            evIndex
                INTEGER,    
            evT
                OCTET STRING
        }

    evIndex OBJECT-TYPE
        SYNTAX  INTEGER (1..1000)
        MAX-ACCESS  not-accessible
        STATUS  current
        DESCRIPTION
        "A unique value for each event. 
        This value range from 1 to 1000."
    ::= { evEntry 1 }


    evT OBJECT-TYPE
        SYNTAX  OCTET STRING (SIZE(36..116))
        MAX-ACCESS  read-only
        STATUS  current
        DESCRIPTION
        "A OCTET STRING containing information about the event.

        The string is in the TLV format, and contains
        following information:
        INTEGER - event id
        INTEGER - module hex code
        DateAndTime - timestamp
        INTEGER - chassis number
        INTEGER - slot number
        INTEGER - port number
        INTEGER - alarm code
        INTEGER - notification code
        INTEGER - Elevated
        DisplayString - ascii string description of the event

        event id:
            INTEGER (0..255)

        Alarm Code:
            minor(1),
            major(2),
            critical(3),
            ignore(4),
            report(5),

        Notification Code:
            minor(1),
            major(2),
            critical(3),
            ignore(4),
            report(5),
            clear(6)

        Elevated:
            Yes(1),
            No(2)
        "
    ::= { evEntry 2 }



    -- **************************************************************
    -- **************************************************************
    -- SSU2000 ALARM GROUP
    -- **************************************************************
    -- **************************************************************

    -- **************************************************************
    -- ALARM STATUS TABLE
    -- **************************************************************

    alarmTable OBJECT-TYPE
    SYNTAX  SEQUENCE OF AlmEntry
    MAX-ACCESS  not-accessible
    STATUS  current
    DESCRIPTION
    "A list of alarm entries. 
    "
    ::= { alarm 1 }

    almEntry OBJECT-TYPE
    SYNTAX  AlmEntry
    MAX-ACCESS  not-accessible
    STATUS  current
    DESCRIPTION
    "Alarm entry attributes.
    "
    INDEX   { almChassis, almSlot, almPort, almIndex }
    ::= { alarmTable 1 }

    AlmEntry ::=
        SEQUENCE {
            almChassis
                INTEGER,    
            almSlot
                INTEGER,    
            almPort
                INTEGER,    
            almIndex
                INTEGER,
            almId
                INTEGER,
            almName
                DisplayString,
            almLevel
                INTEGER,
            almElevate
                YesValue,
            almStatus
                DisplayString
        }

    almChassis OBJECT-TYPE
        SYNTAX  INTEGER (1..5)
        MAX-ACCESS  not-accessible
        STATUS  current
        DESCRIPTION
        "Identifies which chassis is being addressed. 
        This chassis number, slot, and port number uniquely identify each inventory entry.
        "
    ::= { almEntry 1 }

    almSlot OBJECT-TYPE
        SYNTAX  INTEGER (1..20)
        MAX-ACCESS  not-accessible
        STATUS  current
        DESCRIPTION
        "Identifies which slot is being addressed. 
        This chassis number, slot, and port number uniquely identify each inventory entry.
        "
    ::= { almEntry 2 }


    almPort OBJECT-TYPE
        SYNTAX  INTEGER (1..3)
        MAX-ACCESS  not-accessible
        STATUS  current
        DESCRIPTION
        "Identifies which port is being addressed. 
        This chassis number, slot, and port number uniquely identify each inventory entry.
        "
    ::= { almEntry 3 }

    almIndex OBJECT-TYPE
        SYNTAX  INTEGER (1..32)
        MAX-ACCESS  not-accessible
        STATUS  current
        DESCRIPTION
        "Reports the alarm index value.

        Note: The alarm id is allowed for number zero; therefore,
        the OID for this index is alarm id plus 1 to avoid the zero number for OID. 
        "
    ::= { almEntry 4 }

    almId OBJECT-TYPE
        SYNTAX  INTEGER (0..31)
        MAX-ACCESS  read-only
        STATUS  current
        DESCRIPTION
        "Reports the alarm id.

        Note: This is the actual alarm id range 0 thru 31. 
        "
    ::= { almEntry 5 }

    almName OBJECT-TYPE
        SYNTAX  DisplayString (SIZE (0..20))
        MAX-ACCESS  read-only 
        STATUS  current
        DESCRIPTION
        "Reports the text string to describe this alarm.
        "
    ::= { almEntry 6 }

    almLevel OBJECT-TYPE
        SYNTAX  INTEGER
                {
                    minor(1),
                    major(2),
                    critical(3),
                    ignore(4),
                    report(5),
                    clear(6)
                }
        MAX-ACCESS  read-only
        STATUS  current
        DESCRIPTION
        "Reports current state of alarm indications on the units. 
        minor(1),
        major(2),
        critical(3),
        ignore(4),
        report(5),
        clear(6)
        "
    ::= { almEntry 7 }


    almElevate OBJECT-TYPE
        SYNTAX  YesValue
        MAX-ACCESS  read-only
        STATUS  current
        DESCRIPTION
        "Report alarm elevation state

        1 = alarm elevated
        2 = alarm not elevated
        "
    ::= { almEntry 8 }

    almStatus OBJECT-TYPE
        SYNTAX  DisplayString (SIZE (0..20))
        MAX-ACCESS  read-only 
        STATUS  current
        DESCRIPTION
        "Reports the text string to describe this alarm status condition.
        "
    ::= { almEntry 9 }


    -- **************************************************************
    -- ALARM SET GROUP
    -- **************************************************************

    -- ******************************************
    -- SCALAR METHODS
    -- ******************************************

    --
    -- MODULE ALARM SETTING 
    -- IT SHOULD BE ONE MODULE, MULTIPLE MODULE IS NOT ALLOWED

    setAlmLoc OBJECT-TYPE
        SYNTAX  DisplayString (SIZE (0..10))
        MAX-ACCESS  read-write 
        STATUS  current
        DESCRIPTION
        "Set the module slot location.
          It should be one module, multiple module is not allowed
          where
          x is the chassis number: the range is 1 to 5,
          A is the constant letter 'A', and is chassis/slot sepearator.
          y is the slot number. range is [1 to 20].

          For example: 1A3-1 for module located in chassis 1 and slot 3, port 1.

          Note: The slot location must be physically installed in the unit.
          "
    ::= { alarm 2 }


    -- ******************************************
    -- ALARM SETTING TABLE
    -- ******************************************

    setAlmTable OBJECT-TYPE
    SYNTAX  SEQUENCE OF SalEntry
    MAX-ACCESS  not-accessible
    STATUS  current
    DESCRIPTION
      "A list of alarm entries.
      "
    ::= { alarm 3 }

    salEntry OBJECT-TYPE
    SYNTAX  SalEntry
    MAX-ACCESS  not-accessible
    STATUS  current
    DESCRIPTION
    "Set alarm attributes.
    "
    INDEX   { salChassis, salSlot, salPort, salIndex }
    ::= { setAlmTable 1 }


    SalEntry ::=
        SEQUENCE {
            salChassis
                INTEGER,    
            salSlot
                INTEGER,    
            salPort
                INTEGER,    
            salIndex
                INTEGER,
            salId
                INTEGER,
            salName
                DisplayString,
            salSet
                YesValue,
            salElevate
                YesValue,
            salLevel
                INTEGER,
            salDelay
                INTEGER
        }

    salChassis OBJECT-TYPE
        SYNTAX  INTEGER (1..5)
        MAX-ACCESS  not-accessible
        STATUS  current
        DESCRIPTION
        "Identifies which chassis is being addressed. 
        This chassis number, slot, and port number uniquely identify each inventory entry.
        "
    ::= { salEntry 1 }

    salSlot OBJECT-TYPE
        SYNTAX  INTEGER (1..20)
        MAX-ACCESS  not-accessible
        STATUS  current
        DESCRIPTION
        "Identifies which slot is being addressed. 
        This chassis number, slot, and port number uniquely identify each inventory entry.
        "
    ::= { salEntry 2 }


    salPort OBJECT-TYPE
        SYNTAX  INTEGER (1..3)
        MAX-ACCESS  not-accessible
        STATUS  current
        DESCRIPTION
        "Identifies which port is being addressed. 
        This chassis number, slot, and port number uniquely identify each inventory entry.
        "
    ::= { salEntry 3 }

    salIndex OBJECT-TYPE
        SYNTAX  INTEGER (1..32)
        MAX-ACCESS  not-accessible
        STATUS  current
        DESCRIPTION
        "Index value for the alarm.

        Note: The alarm id is allowed for number zero; 
        therefore, the OID for this index is alarm id plus 1 to avoid the zero number for OID. 
        "
    ::= { salEntry 4 }

    salId OBJECT-TYPE
        SYNTAX  INTEGER (0..31)
        MAX-ACCESS  read-only
        STATUS  current
        DESCRIPTION
        "ID value for the alarm.

        Note: This is the actual alarm id range 0 thru 31. 
        "
    ::= { salEntry 5 }

    salName OBJECT-TYPE
        SYNTAX  DisplayString (SIZE (0..20))
        MAX-ACCESS  read-only 
        STATUS  current
        DESCRIPTION
        "Name/Description for the alarm.
        "
    ::= { salEntry 6 }

    salSet OBJECT-TYPE
        SYNTAX  YesValue
        MAX-ACCESS  read-only
        STATUS  current
        DESCRIPTION
        "Alarm state for the alarm:

        1 = alarm set
        2 = no alarm 
        "
    ::= { salEntry 7 }

    salElevate OBJECT-TYPE
        SYNTAX  YesValue
        MAX-ACCESS  read-only
        STATUS  current
        DESCRIPTION
        "Alarm elevation status:

        1 = alarm elevated
        2 = alarm not elevated
        "
    ::= { salEntry 8 }

    salLevel OBJECT-TYPE
        SYNTAX  INTEGER
                {
                    minor(1),
                    major(2),
                    critical(3),
                    ignore(4),
                    report(5)
                }
        MAX-ACCESS  read-write
        STATUS  current
        DESCRIPTION
        "Sets alarm severe level are:
        MINOR - sets alarm level to MINOR
        MAJOR - set alarm level to MAJOR
        CRITICAL - sets alarm level to CRITICAL
        IGNORE - ignore any alarm indication
        REPORT - report only any alarm indication
        "
    ::= { salEntry 9 }

    salDelay OBJECT-TYPE
        SYNTAX  INTEGER (-1 | 0..86400)
        MAX-ACCESS  read-write
        STATUS  current
        DESCRIPTION
        "Sets the length of time in seconds an alarm must be active before generating an alarm.

        Note: 
        0 = user selected immediate indication
        -1 (when read) = forced immediate indication (i.e. not user selectable)
        "
    ::= { salEntry 10 }


    -- **************************************************************
    -- **************************************************************
    -- SSU2000 REF GROUP
    -- **************************************************************
    -- **************************************************************

    refClk OBJECT-TYPE
        SYNTAX  INTEGER
                {
                    clka(1),
                    clkb(2),
                    none(3)
                }
        MAX-ACCESS  read-write 
        STATUS  current
        DESCRIPTION
        "Report/Set which clk is currently selected. 
        clka(1),
        clkb(2),
        none(3)

        Note: When read, it shows which clock is currently selected. 
        When write, only clka or clkb are valid.
        "
    ::= { ref 1 }

    refInp OBJECT-TYPE
        SYNTAX  DisplayString (SIZE (0..10))
        MAX-ACCESS  read-write
        STATUS  current
        DESCRIPTION
        "Report/Set the input reference port.
        The format is defined as xAy-z.
        where
        x is the chassis number: in this case is 1,
        A is the constant letter 'A', and is chassis/slot sepearator.
        y is the slot number: (range is 3 to 11)
        - is the constant letter '-', and is slot/port sepearator
        z is the port number (1 to 3).

        For example: 1A3-1 means this input port located at chassis 1, slot 3, and port 1.
        The NULL string means there is no input reference.
        "
    ::= { ref 2 }

    refBypass OBJECT-TYPE
        SYNTAX  DisplayString (SIZE (0..10))
        MAX-ACCESS  read-only
        STATUS  current
        DESCRIPTION
        "Report/Set input port designated as the input bypass clock.

        The format is defined as xAy-z.
        where
        x is the chassis number: in this case is 1,
        A is the constant letter 'A', and is chassis/slot sepearator.
        y is the slot number: (range is 3 to 11)
        - is the constant letter '-', and is slot/port sepearator
        z is the port number (1 to 3).

        For example: 1A3-1 means this input port located at chassis 1, slot 3, and port 1.
        The NULL string means there is no bypass clock.

        Note: In the SSU2000, the input module always resides in the main chassis (i.e. 'x' is one).
        "
    ::= { ref 3 }

    refClkSwitch OBJECT-TYPE
        SYNTAX  INTEGER
                {
                    ar(1),
                    off(2)
                }
        MAX-ACCESS  read-write 
        STATUS  current
        DESCRIPTION
            "Report/Set Clock auto-return (AR) mode.
            ar(1),
            off(2)
            The AR option changes the current clock selection mode to revertive operation.
            "
    ::= { ref 4 }

    refInpSwitch OBJECT-TYPE
        SYNTAX  INTEGER
                {
                    ar(1),
                    as(2),
                    off(3)
                }
        MAX-ACCESS  read-write
        STATUS  current
        DESCRIPTION
        "Report/Set input switch mode. 
        The InpSwitch settings are:

        AR = Auto Return (revertive)
        AS = Auto Switch (but not revertive)
        OFF = No auto switching
        "
    ::= { ref 5 }

    refInpSelection OBJECT-TYPE
        SYNTAX  INTEGER
                {
                    priority(1),
                    pql(2)
                }
        MAX-ACCESS  read-write
        STATUS  current
        DESCRIPTION
        "Report/Set input selection mode. 
        The input reference selection can be PRIORITY/ PQL.

        PRIORITY - the user assigned priority number is used to
                  pick the best input port as an input reference.
        PQL - the input Priority Quality Level (PQL) is used to 
                  select which is the best input port reference.
        "
::= { ref 6 }

    refClkTodsrc OBJECT-TYPE
        SYNTAX  DisplayString (SIZE (0..10))
        MAX-ACCESS  read-write
        STATUS  current
        DESCRIPTION
        "Report/Set TOD Source. 
        The value can be any TOD source candidate (GPS or PackeTime) indicates the TODSRC of the selected clock.

        The text string of the todsrc reference port.
        The format is defined as xAy.
        where
        x is the chassis number: in this case is 1,
        A is the constant letter 'A', and is chassis/slot sepearator.
        y is the slot number: (range is 3 to 11)

        For example: 1A3 means this reference located at chassis 1, slot 3.
        The NULL string means there is no reference.
        "
    ::= { ref 7 }

    -- **************************************************************
    -- **************************************************************
    -- SSU2000 PHASE GROUP
    -- **************************************************************
    -- **************************************************************


    -- **************************************************************
    -- CURRENT PHASE TABLE
    -- **************************************************************

    phaseTable OBJECT-TYPE
    SYNTAX  SEQUENCE OF PhEntry
    MAX-ACCESS  not-accessible
    STATUS  current
    DESCRIPTION
      "A list of phase data entries. 
      "
    ::= { phase 1 }


    phEntry OBJECT-TYPE
    SYNTAX  PhEntry
    MAX-ACCESS  not-accessible
    STATUS  current
    DESCRIPTION
        "Phase data entry attributes.
        "
    INDEX   { phChassis, phSlot, phPort }
    ::= { phaseTable 1 }


    PhEntry ::=
        SEQUENCE {
            phChassis
                INTEGER,    
            phSlot
                INTEGER,    
            phPort
                INTEGER,    
            phA
                OCTET STRING,
            phB
                OCTET STRING,
            ph100A
                OCTET STRING,
            ph100B
                OCTET STRING,
            ph1000A
                OCTET STRING,
            ph1000B
                OCTET STRING,
            ph10000A
                OCTET STRING,
            ph10000B
                OCTET STRING
        }

    phChassis OBJECT-TYPE
        SYNTAX  INTEGER (1..1)
        MAX-ACCESS  not-accessible
        STATUS  current
        DESCRIPTION
        "Identifies which chassis is being addressed. 
        This chassis number, slot, and port number uniquely identify each inventory entry.
        "
    ::= { phEntry 1 }

    phSlot OBJECT-TYPE
        SYNTAX  INTEGER (1..20)
        MAX-ACCESS  not-accessible
        STATUS  current
        DESCRIPTION
        "Identifies which slot is being addressed. 
        This chassis number, slot, and port number uniquely identify each inventory entry.
        "
    ::= { phEntry 2 }

    phPort OBJECT-TYPE
        SYNTAX  INTEGER (1..3)
        MAX-ACCESS  not-accessible
        STATUS  current
        DESCRIPTION
        "Identifies which port is being addressed. 
        This chassis number, slot, and port number uniquely identify each inventory entry.
        "
    ::= { phEntry 3 }

    phA OBJECT-TYPE
        SYNTAX OCTET STRING (SIZE(16))
        MAX-ACCESS  read-only
        STATUS  current
        DESCRIPTION
        "Current 1-second phase value in nanoseconds on clock A.
        The 1,999,999,999 is designated for invalid phase value.

        The string is in the TLV format, and contains following information:
        DateAndTime - timestamp
        INTEGER - phase value
        "
    ::= { phEntry 4 }

    phB OBJECT-TYPE
        SYNTAX OCTET STRING (SIZE(16))
        MAX-ACCESS  read-only
        STATUS  current
        DESCRIPTION
        "Current 1-second phase value in nanoseconds on clock B.
        The 1,999,999,999 is designated for invalid phase value.

        The string is in the TLV format, and contains following information:
        DateAndTime - timestamp
        INTEGER - phase value
        "
    ::= { phEntry 5 }


    ph100A OBJECT-TYPE
        SYNTAX OCTET STRING (SIZE(16))
        MAX-ACCESS  read-only
        STATUS  current
        DESCRIPTION
        "Current 100-second phase value in nanoseconds on clock A.
        The 1,999,999,999 is designated for invalid phase value.

        The string is in the TLV format, and contains following information:
        DateAndTime - timestamp
        INTEGER - phase value
        "
    ::= { phEntry 6 }

    ph100B OBJECT-TYPE
        SYNTAX OCTET STRING (SIZE(16))
        MAX-ACCESS  read-only
        STATUS  current
        DESCRIPTION
        "Current 100-second phase value in nanoseconds on clock B.
        The 1,999,999,999 is designated for invalid phase value.

        The string is in the TLV format, and contains following information:
        DateAndTime - timestamp
        INTEGER - phase value
        "
    ::= { phEntry 7 }

    ph1000A OBJECT-TYPE
        SYNTAX OCTET STRING (SIZE(16))
        MAX-ACCESS  read-only
        STATUS  current
        DESCRIPTION
        "Current 1000-second phase value in nanoseconds on clock A.
        The 1,999,999,999 is designated for invalid phase value.

        The string is in the TLV format, and contains following information:
        DateAndTime - timestamp
        INTEGER - phase value
        "
    ::= { phEntry 8 }

    ph1000B OBJECT-TYPE
        SYNTAX OCTET STRING (SIZE(16))
        MAX-ACCESS  read-only
        STATUS  current
        DESCRIPTION
        "Current 1000-second phase value in nanoseconds on clock B.
        The 1,999,999,999 is designated for invalid phase value.

        The string is in the TLV format, and contains following information:
        DateAndTime - timestamp
        INTEGER - phase value
        "
    ::= { phEntry 9 }


    ph10000A OBJECT-TYPE
        SYNTAX OCTET STRING (SIZE(16))
        MAX-ACCESS  read-only
        STATUS  current
        DESCRIPTION
        "Current 10000-second phase value in nanoseconds on clock A.
        The 1,999,999,999 is designated for invalid phase value.

        The string is in the TLV format, and contains following information:
        DateAndTime - timestamp
        INTEGER - phase value
        "
    ::= { phEntry 10 }

    ph10000B OBJECT-TYPE
        SYNTAX OCTET STRING (SIZE(16))
        MAX-ACCESS  read-only
        STATUS  current
        DESCRIPTION
        "Current 10000-second phase value in nanoseconds on clock B.
        The 1,999,999,999 is designated for invalid phase value.

        The string is in the TLV format, and contains following information:
        DateAndTime - timestamp
        INTEGER - phase value
        "
    ::= { phEntry 11 }


    -- **************************************************************
    -- PHASE HISTORY GROUP
    -- **************************************************************

    -- ******************************************
    -- SCALAR METHODS  (PHASE HISTORY)
    -- ******************************************

    phHisInpLoc OBJECT-TYPE
        SYNTAX  DisplayString (SIZE (0..10))
        MAX-ACCESS  read-write 
        STATUS  current
        DESCRIPTION
        "Select input port.
        The format is defined as xAy-z.
        where
        x is the chassis number: in this case is 1,
        A is the constant letter 'A', and is chassis/slot sepearator.
        y is the slot number: (range is 3 to 11)
        - is the constant letter '-', and is slot/port sepearator
        z is the port number (1 to 3).

        For example: 1A3-1 means this input port located at chassis 1, slot 3, and port 1

        Note: the user must specify valid input port address.
        The valid port must be physically installed in the system.

        Note: In the SSU2000, the input is located at main chassis, the 'x' number is always one. 
        "
    ::= { phase 2 }

    phHisTimeAvg OBJECT-TYPE
        SYNTAX  INTEGER 
                {
                    t100   (100),  --- 100 second time interval
                    t1000  (1000), --- 1000 second time interval
                    t10000 (10000) --- 10000 second time interval
                }
        MAX-ACCESS  read-write 
        STATUS  current
        DESCRIPTION
        "Reports time (seconds) interval of phase value.  
        t1 (4000 second time interval),
        t100 (1000 second time interval),
        t1000  (1000 second time interval),
        t10000 (10000 second time interval)

        Note: T1 data is only available for ports configured for this function, maximum of 5 ports.
        "
    ::= { phase 3 }

    phHisClk OBJECT-TYPE
        SYNTAX  INTEGER  
                {
                    clka (1), 
                    clkb  (2) 
                }
        MAX-ACCESS  read-write 
        STATUS  current
        DESCRIPTION
            "Reports which clock is used as the reference in the phase measurement.
            "
    ::= { phase 4 }

    phHisCnt OBJECT-TYPE
        SYNTAX  INTEGER (1..7000) 
        MAX-ACCESS  read-write 
        STATUS  current
        DESCRIPTION
        "Count of phase measurement history requested from the phase history buffer.
        The maximum phase history in buffer are:
        T100 = 7000,
        T1000 = 700,
        T10000 = 70,

        Default value = 10.
        "
    ::= { phase 5 }


    -- ******************************************
    -- PHASE HISTORY TABLE
    -- ******************************************

    phHisTable OBJECT-TYPE
    SYNTAX  SEQUENCE OF PhHisEntry
    MAX-ACCESS  not-accessible
    STATUS  current
    DESCRIPTION
      "A list of phase history entries. The number of entries is
      given by the value of phHisCnt. The total entries 
      are up to 7000.

      Note: this table is based upon the following values:
      phHisInpLoc  - the location of the input port 
      phHisTimeAvg - the time (seconds) interval of phase value
      phHisCnt     - total amount of phase history to return.
      "
    ::= { phase 6 }



    phHisEntry OBJECT-TYPE
    SYNTAX  PhHisEntry
    MAX-ACCESS  not-accessible
    STATUS  current
    DESCRIPTION
       "A phase entry attributes:
       phHisChassis
           Identifies which chassis is being addressed. 
       phHisSlot
           Identifies which slot is being addressed. 
       phHisPort
           Identifies which port is being addressed. 
       phHisIndex
           Count/ID value for each phase. 
       phHisV
           Phase value in nanoseconds defined in phHisTimeAvg.
    "
    INDEX   { phHisChassis, phHisSlot, phHisPort, phHisIndex }
    ::= { phHisTable 1 }

    PhHisEntry ::=
        SEQUENCE {
            phHisChassis
                INTEGER,    
            phHisSlot
                INTEGER,    
            phHisPort
                INTEGER,    
            phHisIndex
                INTEGER,    
            phHisV
                OCTET STRING
        }


    phHisChassis OBJECT-TYPE
        SYNTAX  INTEGER (1..1)
        MAX-ACCESS  not-accessible
        STATUS  current
        DESCRIPTION
        "Identifies which chassis is being addressed. 
        This chassis number, slot, and port number uniquely identify each inventory entry.
        "
    ::= { phHisEntry 1 }

    phHisSlot OBJECT-TYPE
        SYNTAX  INTEGER (1..20)
        MAX-ACCESS  not-accessible
        STATUS  current
        DESCRIPTION
        "Identifies which slot is being addressed. 
        This chassis number, slot, and port number uniquely identify each inventory entry.
        "
    ::= { phHisEntry 2 }

    phHisPort OBJECT-TYPE
        SYNTAX  INTEGER (1..3)
        MAX-ACCESS  not-accessible
        STATUS  current
        DESCRIPTION
        "Identifies which port is being addressed. 
        This chassis number, slot, and port number uniquely identify each inventory entry.
        "
    ::= { phHisEntry 3 }

    phHisIndex OBJECT-TYPE
        SYNTAX  INTEGER (1..7000)
        MAX-ACCESS  not-accessible
        STATUS  current
        DESCRIPTION
        "Count/ID value for each phase. 
        Valid range : 1 - 7000.
        "
    ::= { phHisEntry 4 }


    phHisV OBJECT-TYPE
        SYNTAX OCTET STRING (SIZE(16))
        MAX-ACCESS  read-only
        STATUS  current
        DESCRIPTION
        "Phase value in nanoseconds defined in phHisTimeAvg.

        The 1,999,999,999 is designated for invalid phase value.

        The string is in the TLV format, and containsfollowing information:
        DateAndTime - timestamp
        INTEGER - phase value
        "
    ::= { phHisEntry 5 }


    -- **************************************************************
    -- **************************************************************
    -- SSU2000 MTIE GROUP
    -- **************************************************************
    -- **************************************************************

    -- **************************************************************
    -- CURRENT MTIE GROUP
    -- **************************************************************

    -- ******************************************
    -- SCALAR METHODS
    -- ******************************************

    mtInpLoc OBJECT-TYPE
        SYNTAX  DisplayString (SIZE (3..10))
        MAX-ACCESS  read-write 
        STATUS  current
        DESCRIPTION
        "Select input port.
        The format is defined as xAy-z.
        where
        x is the chassis number: in this case is 1,
        A is the constant letter 'A', and is chassis/slot sepearator.
        y is the slot number: (range is 3 to 11)
        - is the constant letter '-', and is slot/port sepearator
        z is the port number (1 to 3).

        For example: 1A3-1 means this input port located at chassis 1, slot 3, and port 1.
        For example: 1A3 means this input port located at chassis 1, slot 3, with all port specified.
        "
        ::= { mtie 1 }


    mtFrTime OBJECT-TYPE
        SYNTAX  DateAndTime
        MAX-ACCESS  read-write
        STATUS  current
        DESCRIPTION
        "Select starting time to measure the MTIE from. 

        Note: the default time is defined as last 24 hours from current time. 
        The default start-time is the current time minus 24 hours, and the default stop-time is the current time.
        " 
::= { mtie 2 }

    mtToTime OBJECT-TYPE
        SYNTAX  DateAndTime
        MAX-ACCESS  read-write
        STATUS  current
        DESCRIPTION
        "Select the stop-time to measure the MTIE.
        If the 'year' field of DateAndTime is specified as zero,  the default time is used.

        The default mtToTime is the current time.
        "
    ::= { mtie 3 }


    -- ******************************************
    -- CURRENT MTIE TABLE
    -- ******************************************

    mtTable OBJECT-TYPE
    SYNTAX  SEQUENCE OF MtEntry
    MAX-ACCESS  not-accessible
    STATUS  current
    DESCRIPTION
    "Report the MTIE measurement.
    "
    ::= { mtie 5 }

    mtEntry OBJECT-TYPE
    SYNTAX  MtEntry
    MAX-ACCESS  not-accessible
    STATUS  current
    DESCRIPTION
        "A mtie record attributes:
        mtChassis
            Identifies which chassis is being addressed. 
        mtSlot
            Identifies which slot is being addressed. 
        mtPort
            Identifies which port is being addressed. 
        mtA
            MTIE record versus clock A.
        mtB
            MTIE record versus clock B.
        "
    INDEX   { mtChassis, mtSlot, mtPort }
    ::= { mtTable 1 }

    MtEntry ::=
        SEQUENCE {
            mtChassis
                INTEGER,    
            mtSlot
                INTEGER,    
            mtPort
                INTEGER,
            mtA
                OCTET STRING,
            mtB
                OCTET STRING
        }


    mtChassis OBJECT-TYPE
        SYNTAX  INTEGER (1..1)
        MAX-ACCESS  not-accessible
        STATUS  current
        DESCRIPTION
        "Identifies which chassis is being addressed. 
        This chassis number, slot, and port number uniquely identify each inventory entry.
        "
    ::= { mtEntry 1 }

    mtSlot OBJECT-TYPE
        SYNTAX  INTEGER (1..20)
        MAX-ACCESS  not-accessible
        STATUS  current
        DESCRIPTION
        "Identifies which slot is being addressed. 
        This chassis number, slot, and port number uniquely identify each inventory entry.
        "
    ::= { mtEntry 2 }

    mtPort OBJECT-TYPE
        SYNTAX  INTEGER (1..3)
        MAX-ACCESS  not-accessible
        STATUS  current
        DESCRIPTION
        "Identifies which port is being addressed. 
        This chassis number, slot, and port number uniquely identify each inventory entry.
        "
    ::= { mtEntry 3 }

    mtA OBJECT-TYPE
        SYNTAX OCTET STRING (SIZE(76))
        MAX-ACCESS  read-only
        STATUS  current
        DESCRIPTION
        "MTIE record versus clock A.

        The MTIE record attributes:
        INTEGER - entry valid ?, 1=valid, 2=invalid 
        DateAndTime - the staring timestamp
        DateAndTime - the ending timestamp
        INTEGER - which clock, 1=clka, 2=clkb
        INTEGER - 0.05 second measurement value
        INTEGER - 0.1 second measurement value
        INTEGER - 1 second measurement value
        INTEGER - 10 second measurement value
        INTEGER - 100 second measurement value
        INTEGER - 1000 second measurement value
        INTEGER - 10000 second measurement value
        INTEGER - 100000 second measurement value
		note: if a non-deterministic value is used in this field, a 
		mtie value will be displayed as -1 (i.e. invalid value).
        "
    ::= { mtEntry 4 }

    mtB OBJECT-TYPE
        SYNTAX OCTET STRING (SIZE(76))
        MAX-ACCESS  read-only
        STATUS  current
        DESCRIPTION
        "MTIE record versus clock B.

        The MTIE record attributes:
        INTEGER - entry valid ?, 1=valid, 2=invalid 
        DateAndTime - the staring timestamp
        DateAndTime - the ending timestamp
        INTEGER - which clock, 1=clka, 2=clkb
        INTEGER - 0.05 second measurement value
        INTEGER - 0.1 second measurement value
        INTEGER - 1 second measurement value
        INTEGER - 10 second measurement value
        INTEGER - 100 second measurement value
        INTEGER - 1000 second measurement value
        INTEGER - 10000 second measurement value
        INTEGER - 100000 second measurement value
		note: if a non-deterministic value is used in this field, a 
		mtie value will be displayed as -1 (i.e. invalid value).
        "
    ::= { mtEntry 5 }


    -- **************************************************************
    -- MTIE HISTORY GROUP
    -- **************************************************************

    -- ******************************************
    -- SCALAR METHODS
    -- ******************************************

    mtHisInpLoc OBJECT-TYPE
        SYNTAX  DisplayString (SIZE (0..10))
        MAX-ACCESS  read-write 
        STATUS  current
        DESCRIPTION
        "Select the input port.
        The format is defined as xAy-z.
        where
        x is the chassis number: in this case is 1,
        A is the constant letter 'A', and is chassis/slot sepearator.
        y is the slot number: (range is 3 to 11)
        - is the constant letter '-', and is slot/port sepearator
        z is the port number (1 to 3).

        For example: 1A3-1 means this input port located at chassis 1, slot 3, and port 1.

        Note: the user must specify valid input port address.
        The valid port is single port and must be physically installed in the system.  
        Multiple ports are not valid.
        "
    ::= { mtie 6 }

    mtHisClk OBJECT-TYPE
        SYNTAX  INTEGER  
                {
                    clka (1), 
                    clkb  (2) 
                }
        MAX-ACCESS  read-write 
        STATUS  current
        DESCRIPTION
        "Clock reference used for reporting of MTIE History.
        "
    ::= { mtie 7 }

    mtHisCnt OBJECT-TYPE
        SYNTAX  INTEGER (1..100) 
        MAX-ACCESS  read-write 
        STATUS  current
        DESCRIPTION
            "Number of days of MTIE History to report.
            The range = 1 - 100. 
            Default value for this field = 1.
            "
    ::= { mtie 8 }


    -- ******************************************
    -- MTIE HISTORY TABLE
    -- ******************************************

    mtHisTable OBJECT-TYPE
    SYNTAX  SEQUENCE OF MtHisEntry
    MAX-ACCESS  not-accessible
    STATUS  current
    DESCRIPTION
    "A list of mtie history entries. 

    Note: this table is based upon the following values:
    mtHisInpLoc - the location of the input port 
    mtHisCnt - total number of mtie hostory want to query.
    "
    ::= { mtie 9 }


    mtHisEntry OBJECT-TYPE
    SYNTAX  MtHisEntry
    MAX-ACCESS  not-accessible
    STATUS  current
    DESCRIPTION
        "MTIE 24-hours history attributes.
        mtHisChassis
            Identifies which chassis is being addressed. 
        mtHisSlot
            Identifies which slot is being addressed. 
        mtHisPort
            Identifies which port is being addressed. 
        mtHisIndex
            Index for the MTIE record. 
        mtHisV
            MTIE record versus selected clock.
        "
    INDEX   { mtHisChassis, mtHisSlot, mtHisPort, mtHisIndex }
    ::= { mtHisTable 1 }


    MtHisEntry ::=
        SEQUENCE {
            mtHisChassis
                INTEGER,    
            mtHisSlot
                INTEGER,    
            mtHisPort
                INTEGER,    
            mtHisIndex
                INTEGER,    
            mtHisV
            	OCTET STRING
        }

    mtHisChassis OBJECT-TYPE
        SYNTAX  INTEGER (1..1)
        MAX-ACCESS  not-accessible
        STATUS  current
        DESCRIPTION
        "Identifies which chassis is being addressed. 
        This chassis number, slot, and port number uniquely identify each inventory entry.
        "
    ::= { mtHisEntry 1 }

    mtHisSlot OBJECT-TYPE
        SYNTAX  INTEGER (1..20)
        MAX-ACCESS  not-accessible
        STATUS  current
        DESCRIPTION
        "Identifies which slot is being addressed. 
        This chassis number, slot, and port number uniquely identify each inventory entry.
        "
    ::= { mtHisEntry 2 }

    mtHisPort OBJECT-TYPE
        SYNTAX  INTEGER (1..3)
        MAX-ACCESS  not-accessible
        STATUS  current
        DESCRIPTION
        "Identifies which port is being addressed. 
        This chassis number, slot, and port number uniquely identify each inventory entry.
        "
    ::= { mtHisEntry 3 }

    mtHisIndex OBJECT-TYPE
        SYNTAX  INTEGER (1..100)
        MAX-ACCESS  not-accessible
        STATUS  current
        DESCRIPTION
        "Index for the MTIE record. 
        Valid range = 1 - 100.
        "
    ::= { mtHisEntry 4 }


    mtHisV OBJECT-TYPE
        SYNTAX OCTET STRING (SIZE(76))
        MAX-ACCESS  read-only
        STATUS  current
        DESCRIPTION
        "MTIE record versus selected clock.

        The MTIE record attributes:
        INTEGER - entry valid ?, 1=valid, 2=invalid 
        DateAndTime - the staring timestamp
        DateAndTime - the ending timestamp
        INTEGER - which clock, 1=clka, 2=clkb
        INTEGER - 0.05 second measurement value
        INTEGER - 0.1 second measurement value
        INTEGER - 1 second measurement value
        INTEGER - 10 second measurement value
        INTEGER - 100 second measurement value
        INTEGER - 1000 second measurement value
        INTEGER - 10000 second measurement value
        INTEGER - 100000 second measurement value
		note: if a non-deterministic value is used in this field, a 
		mtie value will be displayed as -1 (i.e. invalid value).
        "
    ::= { mtHisEntry 5 }





    -- **************************************************************
    -- **************************************************************
    -- SSU2000 TDEV GROUP
    -- **************************************************************
    -- **************************************************************

    -- **************************************************************
    -- CURRENT TDEV GROUP
    -- **************************************************************

    -- ******************************************
    -- SCALAR METHODS
    -- ******************************************

    tdInpLoc OBJECT-TYPE
        SYNTAX  DisplayString (SIZE (3..10))
        MAX-ACCESS  read-write 
        STATUS  current
        DESCRIPTION
        "Select input port.
        The format is defined as xAy-z.
        where
        x is the chassis number: in this case is 1,
        A is the constant letter 'A', and is chassis/slot sepearator.
        y is the slot number: (range is 3 to 11)
        - is the constant letter '-', and is slot/port sepearator
        z is the port number (1 to 3).

        For example: 1A3-1 means this input port located at chassis 1, slot 3, and port 1.
        For example: 1A3 means this input port located at hassis 1, slot 3, with all port specified.
        "
    ::= { tdev 1 }

    tdFrTime OBJECT-TYPE
        SYNTAX  DateAndTime
        MAX-ACCESS  read-write
        STATUS  current
        DESCRIPTION
        "Select starting time to measure the TDEV from. 

        Note: the default time is defined as last 24 hours from current time. 
        The default start-time is the current time minus 24 hours, and the default stop-time is the current time.
        " 
    ::= { tdev 2 }

    tdToTime OBJECT-TYPE
        SYNTAX  DateAndTime
        MAX-ACCESS  read-write
        STATUS  current
        DESCRIPTION
        "Select stop time to measure the TDEV from. 

        Note: the default time is the current time. 
        " 
    ::= { tdev 3 }


    -- ******************************************
    -- CURRENT TDEV TABLE 
    -- ******************************************

    tdTable OBJECT-TYPE
    SYNTAX  SEQUENCE OF TdEntry
    MAX-ACCESS  not-accessible
    STATUS  current
    DESCRIPTION
    "Report the TDEV measurement.
    "
    ::= { tdev 5 }

    tdEntry OBJECT-TYPE
    SYNTAX  TdEntry
    MAX-ACCESS  not-accessible
    STATUS  current
    DESCRIPTION
        "A mtie record attributes:
        tdChassis
            Identifies which chassis is being addressed. 
        tdSlot
            Identifies which slot is being addressed. 
        tdPort
            Identifies which port is being addressed. 
        tdA
            TDEV record versus clock A.
        tdB
            TDEV record versus clock B.
        "
    INDEX   { tdChassis, tdSlot, tdPort }
    ::= { tdTable 1 }

    TdEntry ::=
        SEQUENCE {
            tdChassis
                INTEGER,    
            tdSlot
                INTEGER,    
            tdPort
                INTEGER,
            tdA
                OCTET STRING,
            tdB
                OCTET STRING
        }

    tdChassis OBJECT-TYPE
        SYNTAX  INTEGER (1..1)
        MAX-ACCESS  not-accessible
        STATUS  current
        DESCRIPTION
        "Identifies which chassis is being addressed. 
        This chassis number, slot, and port number uniquely identify each inventory entry.
        "
    ::= { tdEntry 1 }

    tdSlot OBJECT-TYPE
        SYNTAX  INTEGER (1..20)
        MAX-ACCESS  not-accessible
        STATUS  current
        DESCRIPTION
        "Identifies which port is being addressed. 
        This chassis number, slot, and port number uniquely identify each inventory entry.
        "
    ::= { tdEntry 2 }

    tdPort OBJECT-TYPE
        SYNTAX  INTEGER (1..3)
        MAX-ACCESS  not-accessible
        STATUS  current
        DESCRIPTION
        "Identifies which port is being addressed. 
        This chassis number, slot, and port number uniquely identify each inventory entry.
        "
    ::= { tdEntry 3 }


    tdA OBJECT-TYPE
        SYNTAX OCTET STRING (SIZE(124))
        MAX-ACCESS  read-only
        STATUS  current
        DESCRIPTION
        "TDEV record versus clock A:

        TDEV record attributes:
        INTEGER - entry valid ?, 1=valid, 2=invalid 
        DateAndTime - the staring timestamp
        DateAndTime - the ending timestamp
        INTEGER - which clock, 1=clka, 2=clkb
        INTEGER - 0.1 second measurement value
        INTEGER - 0.3 second measurement value
        INTEGER - 0.6 second measurement value
        INTEGER - 1 second measurement value
        INTEGER - 3 second measurement value
        INTEGER - 6 second measurement value
        INTEGER - 10 second measurement value
        INTEGER - 30 second measurement value
        INTEGER - 60 second measurement value
        INTEGER - 100 second measurement value
        INTEGER - 300 second measurement value
        INTEGER - 600 second measurement value
        INTEGER - 1000 second measurement value
        INTEGER - 3000 second measurement value
        INTEGER - 6000 second measurement value
        INTEGER - 10000 second measurement value

        Note: The value are for the time period, the value provided are multpled by 100 times, 
        to avoid floating number representaion.
        "
    ::= { tdEntry 4 }

    tdB OBJECT-TYPE
        SYNTAX OCTET STRING (SIZE(124))
        MAX-ACCESS  read-only
        STATUS  current
        DESCRIPTION
        "TDEV record versus clock B:

        TDEV record attributes:
        INTEGER - entry valid ?, 1=valid, 2=invalid 
        DateAndTime - the staring timestamp
        DateAndTime - the ending timestamp
        INTEGER - which clock, 1=clka, 2=clkb
        INTEGER - 0.1 second measurement value
        INTEGER - 0.3 second measurement value
        INTEGER - 0.6 second measurement value
        INTEGER - 1 second measurement value
        INTEGER - 3 second measurement value
        INTEGER - 6 second measurement value
        INTEGER - 10 second measurement value
        INTEGER - 30 second measurement value
        INTEGER - 60 second measurement value
        INTEGER - 100 second measurement value
        INTEGER - 300 second measurement value
        INTEGER - 600 second measurement value
        INTEGER - 1000 second measurement value
        INTEGER - 3000 second measurement value
        INTEGER - 6000 second measurement value
        INTEGER - 10000 second measurement value

        Note: The value are for the time period, the value provided are multpled by 100 times, 
        to avoid floating number representaion.
        "
    ::= { tdEntry 5 }


    -- **************************************************************
    -- TDEV HISTORY GROUP
    -- **************************************************************

    -- ******************************************
    -- SCALAR METHODS
    -- ******************************************

    tdHisInpLoc OBJECT-TYPE
        SYNTAX  DisplayString (SIZE (0..10))
        MAX-ACCESS  read-write 
        STATUS  current
        DESCRIPTION
        "Selected input port.

        The format is defined as xAy-z.
        where
        x is the chassis number: in this case is 1,
        A is the constant letter 'A', and is chassis/slot sepearator.
        y is the slot number: (range is 3 to 11)
        - is the constant letter '-', and is slot/port sepearator
        z is the port number (1 to 3).

        For example: 1A3-1 means this input port located at chassis 1, slot 3, and port 1

        Note: the user must specify valid input port address.
        The valid port is single port and must be physically installed in the system.  
        Multiple ports are not valid.
        "
    ::= { tdev 6 }

    tdHisClk OBJECT-TYPE
        SYNTAX  INTEGER  
                {
                    clka (1), 
                    clkb (2) 
                }
        MAX-ACCESS  read-write 
        STATUS  current
        DESCRIPTION
        "Report/Set which clock is used to make the TDEV measurement.
        "
    ::= { tdev 7 }

    tdHisCnt OBJECT-TYPE
        SYNTAX  INTEGER (1..100) 
        MAX-ACCESS  read-write 
        STATUS  current
        DESCRIPTION
        "Report/Set the number of days of TDEV History to report.
        The range = 1 - 100. 
        Default value for this field = 1.
        "
    ::= { tdev 8 }


    -- ******************************************
    -- TDEV HISTORY TABLE
    -- ******************************************

    tdHisTable OBJECT-TYPE
    SYNTAX  SEQUENCE OF TdHisEntry
    MAX-ACCESS  not-accessible
    STATUS  current
    DESCRIPTION
    "A list of tdev history entries. 

    Note: this table is based upon the following values:
    tdHisInpLoc - the location of the input port 
    tdHisCnt - total number of tdev hostory want to query.
    "
    ::= { tdev 9 }


    tdHisEntry OBJECT-TYPE
    SYNTAX  TdHisEntry
    MAX-ACCESS  not-accessible
    STATUS  current
    DESCRIPTION
        "TDEV 24-hours history attributes.
        tdHisChassis
            Identifies which chassis is being addressed. 
        tdHisSlot
            Identifies which slot is being addressed. 
        tdHisPort
            Identifies which port is being addressed. 
        tdHisIndex
            Index for the TDEV record. 
        tdHisV
            TDEV record versus selected clock.
        "
    INDEX   { tdHisChassis, tdHisSlot, tdHisPort, tdHisIndex }
    ::= { tdHisTable 1 }


    TdHisEntry ::=
        SEQUENCE {
            tdHisChassis
                INTEGER,    
            tdHisSlot
                INTEGER,    
            tdHisPort
                INTEGER,    
            tdHisIndex
                INTEGER,    
            tdHisV
                OCTET STRING
        }

    tdHisChassis OBJECT-TYPE
        SYNTAX  INTEGER (1..1)
        MAX-ACCESS  not-accessible
        STATUS  current
        DESCRIPTION
        "Identifies which chassis is being addressed. 
        This chassis number, slot, and port number uniquely identify each inventory entry.
        "
    ::= { tdHisEntry 1 }

    tdHisSlot OBJECT-TYPE
        SYNTAX  INTEGER (1..20)
        MAX-ACCESS  not-accessible
        STATUS  current
        DESCRIPTION
        "Identifies which slot is being addressed. 
        This chassis number, slot, and port number uniquely identify each inventory entry.
        "
    ::= { tdHisEntry 2 }

    tdHisPort OBJECT-TYPE
        SYNTAX  INTEGER (1..3)
        MAX-ACCESS  not-accessible
        STATUS  current
        DESCRIPTION
        "Identifies which port is being addressed. 
        This chassis number, slot, and port number uniquely identify each inventory entry.
        "
    ::= { tdHisEntry 3 }

    tdHisIndex OBJECT-TYPE
        SYNTAX  INTEGER (1..100)
        MAX-ACCESS  not-accessible
        STATUS  current
        DESCRIPTION
        "Index value for the TDEV history record. 
        Valid range = 1 - 100.
        "
    ::= { tdHisEntry 4 }


    tdHisV OBJECT-TYPE
        SYNTAX OCTET STRING (SIZE(124))
        MAX-ACCESS  read-only
        STATUS  current
        DESCRIPTION
        "TDEV record versus selected clock.

        The TDEV record attributes:
        INTEGER - entry valid ?, 1=valid, 2=invalid 
        DateAndTime - the staring timestamp
        DateAndTime - the ending timestamp
        INTEGER - which clock, 1=clka, 2=clkb
        INTEGER - 0.1 second measurement value
        INTEGER - 0.3 second measurement value
        INTEGER - 0.6 second measurement value
        INTEGER - 1 second measurement value
        INTEGER - 3 second measurement value
        INTEGER - 6 second measurement value
        INTEGER - 10 second measurement value
        INTEGER - 30 second measurement value
        INTEGER - 60 second measurement value
        INTEGER - 100 second measurement value
        INTEGER - 300 second measurement value
        INTEGER - 600 second measurement value
        INTEGER - 1000 second measurement value
        INTEGER - 3000 second measurement value
        INTEGER - 6000 second measurement value
        INTEGER - 10000 second measurement value
        
        Note: The value are for the time period, the value provided are multpled by 100 times, 
        to avoid floating number representaion.
        "
    ::= { tdHisEntry 5 }



    -- **************************************************************
    -- **************************************************************
    -- SSU2000 FREQ GROUP
    -- **************************************************************
    -- **************************************************************

    freqTable OBJECT-TYPE
    SYNTAX  SEQUENCE OF FqEntry
    MAX-ACCESS  not-accessible
    STATUS  current
    DESCRIPTION
        "A list of frequency entries for each input port.
        "
    ::= { freq 1 }


    fqEntry OBJECT-TYPE
    SYNTAX  FqEntry
    MAX-ACCESS  not-accessible
    STATUS  current
    DESCRIPTION
        "Frequency entry attributes:
        fqChassis
                INTEGER,    
        fqSlot
                INTEGER,    
        fqPort
                INTEGER,    
        fqA
                OCTET STRING,
        fqB
        "
    INDEX   { fqChassis, fqSlot, fqPort }
    ::= { freqTable 1 }


    FqEntry ::=
        SEQUENCE {
            fqChassis
                INTEGER,    
            fqSlot
                INTEGER,    
            fqPort
                INTEGER,    
            fqA
                OCTET STRING,
            fqB
                OCTET STRING
        }

    fqChassis OBJECT-TYPE
        SYNTAX  INTEGER (1..1)
        MAX-ACCESS  not-accessible
        STATUS  current
        DESCRIPTION
        "Identifies which chassis is being addressed. 
        This chassis number, slot, and port number uniquely identify each inventory entry.
        "
    ::= { fqEntry 1 }

    fqSlot OBJECT-TYPE
        SYNTAX  INTEGER (1..20)
        MAX-ACCESS  not-accessible
        STATUS  current
        DESCRIPTION
        "Identifies which slot is being addressed. 
        This chassis number, slot, and port number uniquely identify each inventory entry.
        "
    ::= { fqEntry 2 }

    fqPort OBJECT-TYPE
        SYNTAX  INTEGER (1..3)
        MAX-ACCESS  not-accessible
        STATUS  current
        DESCRIPTION
        "Identifies which port is being addressed. 
        This chassis number, slot, and port number uniquely identify each inventory entry.
        "
    ::= { fqEntry 3 }


    fqA OBJECT-TYPE
        SYNTAX OCTET STRING (SIZE(16))
        MAX-ACCESS  read-only
        STATUS  current
        DESCRIPTION
        "Current frequency measurement versus clock A.
        The 1,999,999,999 is designated for invalid frequency value.

        DateAndTime - timestamp
        INTEGER - frequency value
        "
    ::= { fqEntry 4 }

    fqB OBJECT-TYPE
        SYNTAX OCTET STRING (SIZE(16))
        MAX-ACCESS  read-only
        STATUS  current
        DESCRIPTION
        "Current frequency measurement versus clock B.
        The 1,999,999,999 is designated for invalid frequency value.

        DateAndTime - timestamp
        INTEGER - frequency value
        "
    ::= { fqEntry 5 }


    -- **************************************************************
    -- **************************************************************
    -- SSU2000 NTP GROUP
    -- **************************************************************
    -- **************************************************************


    -- ******************************************
    -- SCALAR METHODS
    -- ******************************************

    ntpMode OBJECT-TYPE
        SYNTAX  INTEGER
                {
                    server(1),
                    client(2),
                    local(3)
                }
        MAX-ACCESS  read-only 
        STATUS  current
        DESCRIPTION
        "Current NTP mode in the system.

        SERVER - The system has a GPS module installed and has UTC time.

        CLIENT - The system has a valid Client peer entry in the NTP Table, 
                 and is synced with its associated Server. 

        LOCAL - The sytem is running its own clock and has its own time. 
        "
    ::= { ntp 1 }

    ntpSysPeer OBJECT-TYPE
        SYNTAX  IpAddress
        MAX-ACCESS  read-only 
        STATUS  current
        DESCRIPTION
        "This is the system peer IP address.
        "
    ::= { ntp 2 }

    ntpSysPeerOffset OBJECT-TYPE
        SYNTAX  DisplayString (SIZE (0..32))
        MAX-ACCESS  read-only 
        STATUS  current
        DESCRIPTION
        "This is the system peer offset.
        "
    ::= { ntp 3 }


    -- **************************************************************
    -- **************************************************************
    -- SSU2000 NTP PEER STATUS TABLE
    -- **************************************************************
    -- **************************************************************

    peerStaTable OBJECT-TYPE
    SYNTAX  SEQUENCE OF PeerStaEntry
    MAX-ACCESS  not-accessible
    STATUS  current
    DESCRIPTION
          "This is the peer statistics table."
    ::= { ntp 4 }

    peerStaEntry OBJECT-TYPE
    SYNTAX  PeerStaEntry
    MAX-ACCESS  not-accessible
    STATUS  current
    DESCRIPTION
          "A peer statistics attributes:
            peerStaIndex
                Reports index for each peer statistics table. 
            peerStaAddress
                Reports the peer IP address.
            peerStaHomeMode
                Reports the peer NTP mode.
            peerStaParentMode   
                Reports the parent NTP mode.
            peerStaLeap 
                Reports leap indicator state.  
            peerStaStratum  
                Reports peer stratum level. 
            peerStaPrecision    
                Reports peer precision. 
            peerStaDelay    
                Reports peer delay. 
            peerStaDispersion   
                Reports peer dispersion. 
            peerStaOffset   
                Reports peer offset. 
            peerStaSentCnt  
                Reports peer sent counter.
            peerStaProcessCnt   
                Reports peer process counter.
            peerStaSanity   
                Reports status of peer sanity.
          "
    INDEX   { peerStaIndex }
    ::= { peerStaTable 1 }


    PeerStaEntry ::=
        SEQUENCE {
            peerStaIndex
                INTEGER,
            peerStaAddress
                IpAddress,
            peerStaHomeMode
                INTEGER,
            peerStaParentMode   
                INTEGER,
            peerStaLeap 
                INTEGER,
            peerStaStratum  
                INTEGER,
            peerStaPrecision    
                INTEGER,
            peerStaDelay    
                DisplayString,
            peerStaDispersion   
                DisplayString,
            peerStaOffset   
                DisplayString,
            peerStaSentCnt  
                Counter32,
            peerStaProcessCnt   
                Counter32,
            peerStaSanity   
                YesValue
        }

    peerStaIndex OBJECT-TYPE
        SYNTAX  INTEGER (1..8)
        MAX-ACCESS  not-accessible
        STATUS  current
        DESCRIPTION
        "Reports index for each peer statistics table. 
        This value ranges from 1 to 8."
    ::= { peerStaEntry 1 }

    peerStaAddress OBJECT-TYPE
        SYNTAX  IpAddress
        MAX-ACCESS  read-only 
        STATUS  current
        DESCRIPTION
            "Reports the peer IP address.
            "
    ::= { peerStaEntry 2 }

    peerStaHomeMode OBJECT-TYPE
        SYNTAX  INTEGER
                {
                    unspect(0),
                    active(1),
                    passive(2),
                    client(3),
                    server(4),
                    broadcast(5),
                    control(6),
                    private(7),
                    bclient(8)
                }
        MAX-ACCESS  read-only 
        STATUS  current
        DESCRIPTION
            "Reports the peer NTP mode.
                    unspect(0),
                    active(1),
                    passive(2),
                    client(3),
                    server(4),
                    broadcast(5),
                    control(6),
                    private(7),
                    bclient(8)
            "
    ::= { peerStaEntry 3 }

    peerStaParentMode OBJECT-TYPE
        SYNTAX  INTEGER
                {
                    unspect(0),
                    active(1),
                    passive(2),
                    client(3),
                    server(4),
                    broadcast(5),
                    control(6),
                    private(7),
                    bclient(8)
                }
        MAX-ACCESS  read-only 
        STATUS  current
        DESCRIPTION
            "Reports the peer parent NTP mode.
                    unspect(0),
                    active(1),
                    passive(2),
                    client(3),
                    server(4),
                    broadcast(5),
                    control(6),
                    private(7),
                    bclient(8)
            "
    ::= { peerStaEntry 4 }

    peerStaLeap OBJECT-TYPE
        SYNTAX  INTEGER
                {
                    nowarning(0),
                    addsec(1),
                    delsec(2),
                    notinsync(3)
                }
        MAX-ACCESS  read-only 
        STATUS  current
        DESCRIPTION
        "Reports leap indicator state.  
            Valid values are:
            0 = sync'd, no warning
            1 = 1 second will be added
            2 = 1 second will be subtracted
            3 = not sync'd
        "
    ::= { peerStaEntry 5 }


    peerStaStratum OBJECT-TYPE
        SYNTAX  INTEGER (0 | 1..16)
        MAX-ACCESS  read-only 
        STATUS  current
        DESCRIPTION
        "Reports peer stratum level. 
        If zero, it is invalid.
        "
    ::= { peerStaEntry 6 }

    peerStaPrecision OBJECT-TYPE
        SYNTAX  INTEGER (-1000..1000)
        MAX-ACCESS  read-only 
        STATUS  current
        DESCRIPTION
        "Reports peer precision.
        "
    ::= { peerStaEntry 7 }

    peerStaDelay OBJECT-TYPE
        SYNTAX  DisplayString (SIZE (0..32))
        MAX-ACCESS  read-only 
        STATUS  current
        DESCRIPTION
        "Reports peer delay.
        "
    ::= { peerStaEntry 8 }

    peerStaDispersion OBJECT-TYPE
        SYNTAX  DisplayString (SIZE (0..32))
        MAX-ACCESS  read-only 
        STATUS  current
        DESCRIPTION
        "Reports peer dispersion.
        "
    ::= { peerStaEntry 9 }

    peerStaOffset OBJECT-TYPE
        SYNTAX  DisplayString (SIZE (0..32))
        MAX-ACCESS  read-only 
        STATUS  current
        DESCRIPTION
        "Reports peer offset.
        "
    ::= { peerStaEntry 10 }

    peerStaSentCnt OBJECT-TYPE
        SYNTAX  Counter32
        MAX-ACCESS  read-only 
        STATUS  current
        DESCRIPTION
        "Reports peer sent counter.
        "
    ::= { peerStaEntry 11 }

    peerStaProcessCnt OBJECT-TYPE
        SYNTAX  Counter32
        MAX-ACCESS  read-only 
        STATUS  current
        DESCRIPTION
        "Reports peer process counter.
        "
    ::= { peerStaEntry 12 }

    peerStaSanity OBJECT-TYPE
        SYNTAX  YesValue
        MAX-ACCESS  read-only 
        STATUS  current
        DESCRIPTION
        "Reports status of peer sanity:
            1 = passed
            2 = rejected
        "
    ::= { peerStaEntry 13 }


    -- **************************************************************
    -- **************************************************************
    -- SSU2000 NTP IP TABLE
    -- **************************************************************
    -- **************************************************************

    ntpTable OBJECT-TYPE
    SYNTAX  SEQUENCE OF NtpEntry
    MAX-ACCESS  not-accessible
    STATUS  current
    DESCRIPTION
          "This table provides the NTP peer statistics.
          "
    ::= { ntp 5 }


    ntpEntry OBJECT-TYPE
    SYNTAX  NtpEntry
    MAX-ACCESS  not-accessible
    STATUS  current
    DESCRIPTION
          "NTP peer attributes.
          ntpIndex
             Index for each NTP peer entry. 
          ntpPeer
             Reports NTP peer IP address.
          ntpPeerType
             Report NTP peer mode.
          ntpBrdTimer
             Report NTP broadcast timer
         "
    INDEX   { ntpIndex }
    ::= { ntpTable 1 }


    NtpEntry ::=
        SEQUENCE {
            ntpIndex
                INTEGER,    
            ntpPeer
                IpAddress,  
            ntpPeerType
                INTEGER,    
            ntpBrdTimer
                INTEGER
        }

    ntpIndex OBJECT-TYPE
        SYNTAX  INTEGER (1..3)
        MAX-ACCESS  not-accessible
        STATUS  current
        DESCRIPTION
        "Index for each NTP peer entry. 
        This value ranges from 1 to 3."
    ::= { ntpEntry 1 }


    ntpPeer OBJECT-TYPE
        SYNTAX  IpAddress
        MAX-ACCESS  read-only 
        STATUS  current
        DESCRIPTION
        "Reports NTP peer IP address.
        If the ip address is zero for this entry, the whole entry has no meaning.
        "
    ::= { ntpEntry 2 }

    ntpPeerType OBJECT-TYPE
        SYNTAX  INTEGER
                {
                    client (1),
                    broadcast (2),
                    bclient (3)
                }
        MAX-ACCESS  read-only 
        STATUS  current
        DESCRIPTION
        "Report NTP peer mode.

        CLIENT    - The IP for NTP server in client mode.
        BROADCAST - The subnet mask for broadcasting mode.
        BCLIENT   - The IP for NTP server in broadcast client mode.
        "
    ::= { ntpEntry 3 }


    ntpBrdTimer OBJECT-TYPE
        SYNTAX  INTEGER
                {
                    notuse(0),
                    t32 (32),
                    t64 (64),
                    t128 (128),
                    t256 (256),
                    t512 (512),
                    t1024 (1024)
                }
        MAX-ACCESS  read-only 
        STATUS  current
        DESCRIPTION
        "Report NTP broadcast timer in
        notuse(0),
        t32 (32),
        t64 (64),
        t128 (128),
        t256 (256),
        t512 (512),
        t1024 (1024)
        "
    ::= { ntpEntry 4 }


    -- ******************************************
    -- NTP SCALAR METHODS 
    -- ******************************************

    ntpAddClient OBJECT-TYPE
        SYNTAX  IpAddress
        MAX-ACCESS  read-write 
        STATUS  current
        DESCRIPTION
            "Set NTP peers to enable client mode.

            This field has meaning only during 'write' operations.
            "
    ::= { ntp 6 }

    ntpAddBrd OBJECT-TYPE
        SYNTAX  IpAddress
        MAX-ACCESS  read-write 
        STATUS  current
        DESCRIPTION
        "Set NTP servers to enable broadcast mode.

        This field has meaning only during 'write' operations.
        "
    ::= { ntp 7 }

    ntpAddBclient OBJECT-TYPE
        SYNTAX  IpAddress
        MAX-ACCESS  read-write 
        STATUS  current
        DESCRIPTION
        "Set NTP peers to enable broadcast client mode.

        This field has meaning only during 'write' operations.
        "
    ::= { ntp 8 }



    ntpDelPeer OBJECT-TYPE
        SYNTAX  IpAddress
        MAX-ACCESS  read-write 
        STATUS  current
        DESCRIPTION
        "Delete NTP servers from the peer table.

        This field has meaning only during 'write' operations.
        "
    ::= { ntp 9 }


    ntpClr OBJECT-TYPE
        SYNTAX  INTEGER
                {
                    clr (1)
                }
        MAX-ACCESS  read-write 
        STATUS  current
        DESCRIPTION
        "Clear all the NTP peer addresses in the unit.

        This field has meaning only during 'write' operations.
        "
    ::= { ntp 10 }


    ntpBTimer OBJECT-TYPE
        SYNTAX  INTEGER
                {
                    t32 (32),
                    t64 (64),
                    t128 (128),
                    t256 (256),
                    t512 (512),
                    t1024 (1024)
                }
        MAX-ACCESS  read-write 
        STATUS  current
        DESCRIPTION
        "Reports/Set the broadcast timer 
        t32 (32),
        t64 (64),
        t128 (128),
        t256 (256),
        t512 (512),
        t1024 (1024)
        "
    ::= { ntp 11 }

    ntpPrefer OBJECT-TYPE
        SYNTAX  INTEGER
                {
                    gps (1),
                    client (2)
                }
        MAX-ACCESS  read-write 
        STATUS  current
        DESCRIPTION
        "Report/Set the SSU time-of-day source from GPS or NTP Client.
        "
    ::= { ntp 12 }


    -- **************************************************************
    -- **************************************************************
    -- SSU2000 TIME
    -- **************************************************************
    -- **************************************************************

    -- TOP LEVEL
    tmCurTime OBJECT-TYPE
        SYNTAX  DateAndTime
        MAX-ACCESS  read-write 
        STATUS  current
        DESCRIPTION
        "Reports the current system time.

        Note: user can change the system time only when the system is in LOCAL mode. 
        If the system is SERVER or NTP CLIENT, changing system time is not allowed.
        "
    ::= { time 1 }

    tmLocalOffset OBJECT-TYPE
        SYNTAX  TLocalTimeOffset
        MAX-ACCESS  read-write 
        STATUS  current
        DESCRIPTION
        "Report/Set local time offset.

        Note: This allow the users to set a local time offset.
        The local time offset limits are (+/-)13 hours. 
        This is primarily used in systems with GPS or NTP time-of-day references. 
        where users' prefer system time to be set to local time.
        "
::= { time 2 }


    -- **************************************************************
    -- **************************************************************
    -- SSU2000 PQL TABLE GROUP
    -- **************************************************************
    -- **************************************************************

    -- ******************************************
    -- The DS1 PQL Table
    -- ******************************************

    pqlDs1Table OBJECT-TYPE
    SYNTAX  SEQUENCE OF PqlDs1Entry
    MAX-ACCESS  not-accessible
    STATUS  current
    DESCRIPTION
          "A list of PQL entries. 
          The total entries are 16."
    ::= { pqlTable 1 }

    pqlDs1Entry OBJECT-TYPE
    SYNTAX  PqlDs1Entry
    MAX-ACCESS  not-accessible
    STATUS  current
    DESCRIPTION
          "A PQL entry containing objects of each PQL."
    INDEX   { pqlDs1Index }
    ::= { pqlDs1Table 1 }

    PqlDs1Entry ::=
        SEQUENCE {
            pqlDs1Index
                INTEGER,    
            pqlDs1Ssm
                TSsm,
            pqlDs1Descr
                DisplayString
        }

    pqlDs1Index OBJECT-TYPE
        SYNTAX  INTEGER (1..16)
        MAX-ACCESS  not-accessible
        STATUS  current
        DESCRIPTION
        "A unique value for each PQL table. 
        This value ranges from 1 to 16."
    ::= { pqlDs1Entry 1 }


    pqlDs1Ssm OBJECT-TYPE
        SYNTAX  TSsm
        MAX-ACCESS  read-write
        STATUS  current
        DESCRIPTION
        "This DS1 Sync Status Message (SSM) value for that Priority Quality Level (PQL) entry. 

        Note: If value of this entry is 0xff, the entry is not used.
        This is the 8-bit value. If the 8th bit is set, this SSM value is not telcom standard.
        Use caution when modifying as system characteristics will be altered.
        "
    ::= { pqlDs1Entry 2 }


    pqlDs1Descr OBJECT-TYPE
        SYNTAX  DisplayString (SIZE (0..14))
        MAX-ACCESS  read-write
        STATUS  current
        DESCRIPTION
        "Report description for the DS1 Priority Quality Level (PQL) entry."
    ::= { pqlDs1Entry 3 }



    -- ******************************************
    -- The E1 PQL Table
    -- ******************************************

    pqlE1Table OBJECT-TYPE
    SYNTAX  SEQUENCE OF PqlE1Entry
    MAX-ACCESS  not-accessible
    STATUS  current
    DESCRIPTION
          "A list of PQL entries. 
          The total entries are 16."
    ::= { pqlTable 2 }

    pqlE1Entry OBJECT-TYPE
    SYNTAX  PqlE1Entry
    MAX-ACCESS  not-accessible
    STATUS  current
    DESCRIPTION
          "A PQL entry attributes.
            pqlE1Index
               Index value for each PQL table. 
            pqlE1Ssm
               Report/Set the E1 Sync Status Message (SSM) value for that Priority Quality Level (PQL) entry. 
            pqlE1Descr
               Report/Set description for the E1 Priority Quality Level (PQL) entry.
          "
    INDEX   { pqlE1Index }
    ::= { pqlE1Table 1 }

    PqlE1Entry ::=
        SEQUENCE {
            pqlE1Index
                INTEGER,    
            pqlE1Ssm
                TSsm,
            pqlE1Descr
                DisplayString
        }

    pqlE1Index OBJECT-TYPE
        SYNTAX  INTEGER (1..16)
        MAX-ACCESS  not-accessible
        STATUS  current
        DESCRIPTION
              "Index value for each PQL table. 
              This value ranges from 1 to 16."
    ::= { pqlE1Entry 1 }


    pqlE1Ssm OBJECT-TYPE
        SYNTAX  TSsm
        MAX-ACCESS  read-write
        STATUS  current
        DESCRIPTION
        "Report/Set the E1 Sync Status Message (SSM) value for that Priority Quality Level (PQL) entry. 

        Note: If value of this entry is 0xff, this entry is not used.
        This is the 8-bits value. If the 8th bit is set, this SSM value is not telcom standard.
        Use caution when modifying as system characteristics will be altered.
        "
    ::= { pqlE1Entry 2 }

    pqlE1Descr OBJECT-TYPE
        SYNTAX  DisplayString (SIZE (0..14))
        MAX-ACCESS  read-write
        STATUS  current
        DESCRIPTION
        "Report/Set description for the E1 Priority Quality Level (PQL) entry."
    ::= { pqlE1Entry 3 }



    -- ******************************************
    -- Reset PQL Table
    -- ******************************************

    pqlReset OBJECT-TYPE
        SYNTAX  INTEGER
                {
                    factory(1)
                }
        MAX-ACCESS  read-write 
        STATUS  current
        DESCRIPTION
        "Set DS1/E1 Priority Quality Level(PQL) tables into factory defaults. 

        Note: It only has meaning for 'write' operations.
        "
    ::= { pqlTable 3 }


    -- **************************************************************
    -- **************************************************************
    -- SSU2000 IONAME TABLE GROUP
    -- **************************************************************
    -- **************************************************************

    ionameTable OBJECT-TYPE
    SYNTAX  SEQUENCE OF IonEntry
    MAX-ACCESS  not-accessible
    STATUS  current
    DESCRIPTION
          "A list of input/output name entries.
          " 
    ::= { ioname 1 }


    ionEntry OBJECT-TYPE
    SYNTAX  IonEntry
    MAX-ACCESS  not-accessible
    STATUS  current
    DESCRIPTION
          "An io name entry attributes.
            ionChassis
               Identifies which chassis is being addressed. 
            ionSlot
               Identifies which slot is being addressed. 
            ionPort
               Identifies which port is being addressed. 
            ionName
               Report/Set port ioname field.
          "
    INDEX   { ionChassis, ionSlot, ionPort }
    ::= { ionameTable 1 }

    IonEntry ::=
        SEQUENCE {
            ionChassis
                INTEGER,    
            ionSlot
                INTEGER,    
            ionPort
                INTEGER,
            ionName
                DisplayString
    }
                    
    ionChassis OBJECT-TYPE
        SYNTAX  INTEGER (1..5)
        MAX-ACCESS  not-accessible
        STATUS  current
        DESCRIPTION
        "Identifies which chassis is being addressed. 
        This chassis number, slot, and port number uniquely identify each inventory entry.
        "
    ::= { ionEntry 1 }

    ionSlot OBJECT-TYPE
        SYNTAX  INTEGER (1..20)
        MAX-ACCESS  not-accessible
        STATUS  current
        DESCRIPTION
        "Identifies which slot is being addressed. 
        This chassis number, slot, and port number uniquely identify each inventory entry.
        "
    ::= { ionEntry 2 }


    ionPort OBJECT-TYPE
        SYNTAX  INTEGER (1..20)
        MAX-ACCESS  not-accessible
        STATUS  current
        DESCRIPTION
        "Identifies which port is being addressed. 
        This chassis number, slot, and port number uniquely identify each inventory entry.
        "
    ::= { ionEntry 3 }

    ionName OBJECT-TYPE
        SYNTAX  DisplayString (SIZE (0..20))
        MAX-ACCESS  read-write 
        STATUS  current
        DESCRIPTION
          "Report/Set port ioname field.
          If the name is a null string (zero length), this i/o name s cleared from the port.
          "
    ::= { ionEntry 4 }


    -- ******************************************
    -- IONAME SCALAR METHODS
    -- ******************************************

    ionameLoc OBJECT-TYPE
        SYNTAX  DisplayString (SIZE (3..20))
        MAX-ACCESS  read-write 
        STATUS  current
        DESCRIPTION
        "The text string of the input/output port.
        The format is defined as xAy-z or xAy-z&&z (if specified the range of ports)
        where
        x is the chassis number: in this case is 1,
        A is the constant letter 'A', and is chassis/slot sepearator.
        y is the slot number: (range is 3 to 11)
        - is the constant letter '-', and is slot/port sepearator
        z is the port number (1 to 3, if input) or 
            (1 to 20, if output port).
        && is the two constant letters '&&', and is port range sepearator
        z is the ending port number (1 to 3, if input) or 
            (1 to 20, if output port).

        For example: 
        1A3-1 means this port located at chassis 1, slot 3, and port 1.
        2A5-2&&5 means this ports located at chassis 2, slot 5, and ports 2 thru 5.

        Note: the user must specify valid port address.
        The valid port must be physically installed in the system.
        "
    ::= { ioname 2 }


    ionameSet OBJECT-TYPE
        SYNTAX  DisplayString (SIZE (0..20))
        MAX-ACCESS  read-write 
        STATUS  current
        DESCRIPTION
        "Report/Set name associated input/output ports.

        If the name is a null string, this i/o name is cleared from the ports.

        Note: You must specify the i/o port range first, and then provide the i/o name.
        "
    ::= { ioname 3 }



    -- **************************************************************
    -- **************************************************************
    -- SSU2000 COMMUNICATION PORT (SUCH AS RS232) GROUP
    -- **************************************************************
    -- **************************************************************

    -- **************************************************************
    -- SSU2000 RS232
    -- **************************************************************

    com232Table OBJECT-TYPE
    SYNTAX  SEQUENCE OF ComEntry
    MAX-ACCESS  not-accessible
    STATUS  current
    DESCRIPTION
          "A list of RS232 port entries. The total entries are 3."
    ::= { comm 1 }


    comEntry OBJECT-TYPE
    SYNTAX  ComEntry
    MAX-ACCESS  not-accessible
    STATUS  current
    DESCRIPTION
        "An RS232 communication entry attributes.
            comIndex
               Index for each communication table. 
            comMode
               Set the specified RS232 port command parser to ICS or  TL1.
            comEcho
                Enable/disable echo on the specified RS232 port.
            comEol
                Set the specified RS232 port End Of Line (EOL) terminator.
            comBaud
                Set the specified RS232 port baud rate.
		"
    INDEX   { comIndex }
    ::= { com232Table 1 }

    ComEntry ::=
        SEQUENCE {
            comIndex
                INTEGER,    
            comMode
                INTEGER,
            comEcho
                OnValue,
            comEol
                INTEGER,
            comBaud
                INTEGER
        }


    comIndex OBJECT-TYPE
        SYNTAX  INTEGER (1..3)
        MAX-ACCESS  not-accessible
        STATUS  current
        DESCRIPTION
              "Index for each communication table. 
              This value ranges from 1 to 3."
    ::= { comEntry 1 }


    comMode OBJECT-TYPE
        SYNTAX  INTEGER
                {
                    ics(1),
                    tl1(2)
                }
        MAX-ACCESS  read-write
        STATUS  current
        DESCRIPTION
            "Set the specified RS232 port command parser to ICS or TL1.
            "
    ::= { comEntry 2 }

    comEcho OBJECT-TYPE
        SYNTAX  OnValue
        MAX-ACCESS  read-write
        STATUS  current
        DESCRIPTION
            "Enable/disable echo on the specified RS232 port.

            Note: This only affects the ICS command mode. 
            "
    ::= { comEntry 3 }

    comEol OBJECT-TYPE
        SYNTAX  INTEGER
                {
                    cr (1),
                    lf (2),
                    crlf (3)
                }

        MAX-ACCESS  read-write
        STATUS  current
        DESCRIPTION
            "Set the specified RS232 port End Of Line (EOL) terminator.
                    cr (1),
                    lf (2),
                    crlf (3)
            "
    ::= { comEntry 4 }

    comBaud OBJECT-TYPE
        SYNTAX  INTEGER
                {
                    baud1200 (1200),
                    baud2400 (2400),
                    baud4800 (4800),
                    baud9600 (9600),
                    baud19200 (19200)
                }

        MAX-ACCESS  read-write
        STATUS  current
        DESCRIPTION
            "Set the specified RS232 port baud rate.
            Valid baud rates are: 
                    baud1200 (1200),
                    baud2400 (2400),
                    baud4800 (4800),
                    baud9600 (9600),
                    baud19200 (19200)
            "
    ::= { comEntry 5 }


    -- **************************************************************
    -- SSU2000 COMMUNICATION (INCLUDE TELNET AND ETHERNET TL1)
    -- **************************************************************

    comParmTable OBJECT-TYPE
    SYNTAX  SEQUENCE OF ComParmEntry
    MAX-ACCESS  not-accessible
    STATUS  current
    DESCRIPTION
          "A list of communication port setting entries (such as timeout). 
          The total entries are 5."
    ::= { comm 2 }


    comParmEntry OBJECT-TYPE
    SYNTAX  ComParmEntry
    MAX-ACCESS  not-accessible
    STATUS  current
    DESCRIPTION
          "Communication setting entry for each logical port.
            comParmIndex
                Index for each communication parameter table. 
            comType
                Specify the communication port.
            comTimeout
                Report/Set communication port session timeout (in seconds).
          "
    INDEX   { comParmIndex }
    ::= { comParmTable 1 }


    ComParmEntry ::=
        SEQUENCE {
            comParmIndex
                INTEGER,    
            comType
                INTEGER,
            comTimeout
                INTEGER
        }


    comParmIndex OBJECT-TYPE
        SYNTAX  INTEGER (1..5)
        MAX-ACCESS  not-accessible
        STATUS  current
        DESCRIPTION
              "Index for each communication parameter table. 
              This value ranges from 1 to 5."
    ::= { comParmEntry 1 }


    comType OBJECT-TYPE
        SYNTAX  INTEGER
                {
                    local (1),
                    coma (2),
                    comb (3),
                    telnet (4),
                    etl1 (5)      -- Ethernet TL1
                }
        MAX-ACCESS  read-only
        STATUS  current
        DESCRIPTION
        "Specify the communication port.
        Valid values are:
            1 = local (RS232)
            2 = com A (RS232)
            3 = com B (RS232)
            4 = telnet
            5 = telnet TL1 port
        "
    ::= { comParmEntry 2 }

    comTimeout OBJECT-TYPE
        SYNTAX  INTEGER (0| 5..43200)
        MAX-ACCESS  read-write
        STATUS  current
        DESCRIPTION
        "Report/Set communication port session timeout (in seconds).

        Note: 0 = NEVER timeout.
        "
    ::= { comParmEntry 3 }



    -- ******************************************
    -- COM SCALER METHODS
    -- ******************************************

    comLogoff OBJECT-TYPE
        SYNTAX  INTEGER
                {
                    local (1),
                    coma (2),
                    comb (3),
                    telneta (4),
                    telnetb (5),
                    telnetc (6),
                    telnetd (7),
                    etl1a (8),
                    etl1b (9),
                    etl1c (10),
                    etl1d (11)
                }
                
        MAX-ACCESS  read-write 
        STATUS  current
        DESCRIPTION
        "Logoff user on another logical communication port.

        The valid communication port are: 
                    local (1),
                    coma (2),
                    comb (3),
                    telneta (4),
                    telnetb (5),
                    telnetc (6),
                    telnetd (7),
                    etl1a (8),
                    etl1b (9),
                    etl1c (10),
                    etl1d (11)

        Note: This field only has meaning for 'write' operations.
        "
::= { comm 3 }



    -- **************************************************************
    -- **************************************************************
    -- SSU2000 SNMPv2 MANAGER TABLE GROUP
    -- **************************************************************
    -- **************************************************************

    snmpv2manTable OBJECT-TYPE
    SYNTAX  SEQUENCE OF Snmpv2manEntry
    MAX-ACCESS  not-accessible
    STATUS  current
    DESCRIPTION
    "Reports the SNMPv2 manager(s) IP address.
    "
    ::= { snmpman 1 }

    snmpv2manEntry OBJECT-TYPE
    SYNTAX  Snmpv2manEntry
    MAX-ACCESS  not-accessible
    STATUS  current
    DESCRIPTION
          "SNMPv2 manager table attributes.
            snmpv2manIndex
                Index for each SNMPv2 manager table entry. 
            snmpv2manIp
                Set the snmpv2 manager IP address.
          "
    INDEX   { snmpv2manIndex }
    ::= { snmpv2manTable 1 }

    Snmpv2manEntry ::=
        SEQUENCE {
            snmpv2manIndex
                INTEGER,    
            snmpv2manIp
                IpAddress   
        }

    snmpv2manIndex OBJECT-TYPE
        SYNTAX  INTEGER (1..4)
        MAX-ACCESS  not-accessible
        STATUS  current
        DESCRIPTION
        "Index for each SNMPv2 manager table entry. 
        This value range from 1 to 4."
    ::= { snmpv2manEntry 1 }

    snmpv2manIp OBJECT-TYPE
        SYNTAX  IpAddress
        MAX-ACCESS  read-write 
        STATUS  current
        DESCRIPTION
        "Set the snmpv2 manager IP address.
        Write a new IP address will put this new IP into table.
        Write zero IP address will delete this IP address from table.
        Note: The above only apply to SNMPv2. 
        "
    ::= { snmpv2manEntry 2 }


    -- ******************************************
    -- SNMP SCALAR METHODS
    -- ******************************************

    snmpmanInit OBJECT-TYPE
        SYNTAX  INTEGER
                {
                    initv2 (1),     -- initialize the SNMPv2 manager table
                    initv3 (2)      -- initialize the SNMPv3 manager table
                }
                
        MAX-ACCESS  read-write 
        STATUS  current
        DESCRIPTION
        "Initializes the SNMP Manager Table to null IP addresses.
        Note: This field only has meaning when 'write' operations
        "
    ::= { snmpman 2 }


    snmpmanTrap OBJECT-TYPE
        SYNTAX  INTEGER
                {
                    alarm(1),
                    all(2)
                }
        MAX-ACCESS  read-write 
        STATUS  current
        DESCRIPTION
        "Set the SNMP trap filter to SNMP Manager.
        The trap filter can be set to be 'alarm' only or all traps.

        1 = alarm
        2 = all

        If 'alarm' trap, only events with ID less than 32 (i.e. alarms) 
        will be sent to the SNMP Manager. All other traps will be filtered 
        out. The purpose of this command is to reduce the traffic, if 
        desired.
        "
    ::= { snmpman 3 }


    snmpNotification OBJECT-TYPE
        SYNTAX  INTEGER
                {
                    v2 (1), -- traps in v2 form, address from v2 manager table
                    v3 (2), -- traps in v3 form, address from v2 manager table
                    all(3)  -- traps in v2/v3, address from v2/v3 table accordingly
                }
                
        MAX-ACCESS  read-write 
        STATUS  current
        DESCRIPTION
        "Set SNMPv3 traps format to use.
             v2 (1), -- traps in v2 form, address from v2 manager table
             v3 (2), -- traps in v3 form, address from v2 manager table
             all(3)  -- traps in v2/v3, address from v2/v3 table accordingly
        It can V2, V3, or both forms. Each v2/v3 traps sent out are viaits own manager table accordingly.
        Note: The above only apply to SNMPv3 load. 
        "
    ::= { snmpman 4 }

    snmpEnable OBJECT-TYPE
        SYNTAX  INTEGER
                {
                    v2enable(1),    -- activate SNMPv2
                    v2disable(2)    -- deactivate SNMPv2
                }
                
        MAX-ACCESS  read-write 
        STATUS  current
        DESCRIPTION
        "Activate/deactivate SNMPv2.
        Note: The above only apply to SNMPv3 load. 
        "
    ::= { snmpman 5 }


    -- **************************************************************
    -- SSU2000 SNMPv2 User TABLE GROUP
    -- **************************************************************

    snmpv2userTable OBJECT-TYPE
    SYNTAX  SEQUENCE OF Snmpv2userEntry
    MAX-ACCESS  not-accessible
    STATUS  current
    DESCRIPTION
    "SNMPv2 User Table.
    "
    ::= { snmpman 6 }

    snmpv2userEntry OBJECT-TYPE
    SYNTAX  Snmpv2userEntry
    MAX-ACCESS  not-accessible
    STATUS  current
    DESCRIPTION
    "SNMPv2 user table entry attributes.
            snmpv2userIndex
              Index for each SNMPv2 user table entry. 
            snmpv2user
             Reports SNMPv2 user 
    "
    INDEX   { snmpv2userIndex }
    ::= { snmpv2userTable 1 }

    Snmpv2userEntry ::=
        SEQUENCE {
            snmpv2userIndex
                INTEGER,    
            snmpv2user
                DisplayString   
        }

    snmpv2userIndex OBJECT-TYPE
        SYNTAX  INTEGER (1..6)
        MAX-ACCESS  not-accessible
        STATUS  current
        DESCRIPTION
              "Index for each SNMPv2 user entry. 
              "
    ::= { snmpv2userEntry 1 }

    snmpv2user OBJECT-TYPE
        SYNTAX  DisplayString (SIZE (0..20))
        MAX-ACCESS  read-only 
        STATUS  current
        DESCRIPTION
            "Reports SNMPv2 user entry
            It is the read community string of an SNMPv2 user
            "
    ::= { snmpv2userEntry 2 }


    -- **************************************************************
    -- SSU2000 SNMPv3 User TABLE GROUP
    -- **************************************************************

    snmpv3userTable OBJECT-TYPE
    SYNTAX  SEQUENCE OF Snmpv3userEntry
    MAX-ACCESS  not-accessible
    STATUS  current
    DESCRIPTION
          "SNMPv3 User Table.
          "
    ::= { snmpman 7 }

    snmpv3userEntry OBJECT-TYPE
    SYNTAX  Snmpv3userEntry
    MAX-ACCESS  not-accessible
    STATUS  current
    DESCRIPTION
    "SNMPv3 user table entry attributes.
            snmpv3userIndex
              Index for each SNMPv3 user table entry. 
            snmpv3user
             Reports SNMPv3 user 
    "
    INDEX   { snmpv3userIndex }
    ::= { snmpv3userTable 1 }

    Snmpv3userEntry ::=
        SEQUENCE {
            snmpv3userIndex
                INTEGER,    
            snmpv3user
                DisplayString   
        }

    snmpv3userIndex OBJECT-TYPE
        SYNTAX  INTEGER (1..6)
        MAX-ACCESS  not-accessible
        STATUS  current
        DESCRIPTION
              "Index for each SNMPv3 user table entry. 
              "
    ::= { snmpv3userEntry 1 }

    snmpv3user OBJECT-TYPE
        SYNTAX  DisplayString (SIZE (0..20))
        MAX-ACCESS  read-only 
        STATUS  current
        DESCRIPTION
            "Reports SNMPv3 user
            "
    ::= { snmpv3userEntry 2 }


    -- **************************************************************
    -- SSU2000 SNMPv3 MANAGER TABLE GROUP
    -- **************************************************************

    snmpv3manTable OBJECT-TYPE
    SYNTAX  SEQUENCE OF Snmpv3manEntry
    MAX-ACCESS  not-accessible
    STATUS  current
    DESCRIPTION
          "Reports SNMPv3 manager IP address.
          "
    ::= { snmpman 8 }

    snmpv3manEntry OBJECT-TYPE
    SYNTAX  Snmpv3manEntry
    MAX-ACCESS  not-accessible
    STATUS  current
    DESCRIPTION
          "SNMPv3 manager entry attributes.
            snmpv3manIndex
               Index for each SNMPv3 manager entry. 
            snmpv3manIp
               Report/Set snmpv3 manager IP address.
            snmpv3manUser
               Report/Set the SNMPv3 user
          "
    INDEX   { snmpv3manIndex }
    ::= { snmpv3manTable 1 }

    Snmpv3manEntry ::=
        SEQUENCE {
            snmpv3manIndex
                INTEGER,    
            snmpv3manIp
                IpAddress,  
            snmpv3manUser
                DisplayString   
        }

    snmpv3manIndex OBJECT-TYPE
        SYNTAX  INTEGER (1..4)
        MAX-ACCESS  not-accessible
        STATUS  current
        DESCRIPTION
              "Index for each SNMPv3 manager entry. 
              This value range from 1 to 4."
    ::= { snmpv3manEntry 1 }

    snmpv3manIp OBJECT-TYPE
        SYNTAX  IpAddress
        MAX-ACCESS  read-write 
        STATUS  current
        DESCRIPTION
        "Report/Set snmpv3 manager IP address.

        Note: No action shall be taken at this time. 
        Action shall be taken when the next field 'snmpv3manUser'is written. 
        The above only apply to SNMPv3. 
        "
    ::= { snmpv3manEntry 2 }

    snmpv3manUser OBJECT-TYPE
        SYNTAX  DisplayString (SIZE (0..20))
        MAX-ACCESS  read-write 
        STATUS  current
        DESCRIPTION
        "Report/Set the SNMPv3 user

        Note1: All user names are uppercase except the built-in user. 
        Write username will put this user along with ip into table.
        Writing a null string will delete this entry from table.
        Any previouly written IP has no meaning (i.e. the writing the null 
        string of username shall trigger the delete action of that entry from table.
        Note2: There is no modify action. User need to delete an entry and then add an new entry.
        Note3: The above only apply to SNMPv3. 
        "
    ::= { snmpv3manEntry 3 }


    -- **************************************************************
    -- **************************************************************
    -- SSU2000 SYSTEM TABLE GROUP
    -- **************************************************************
    -- **************************************************************

    sysPbo OBJECT-TYPE
        SYNTAX  INTEGER
                {
                    event(1),
                    report(2),
                    none(3),
                    disable(4)
                }
        MAX-ACCESS  read-write
        STATUS  current
        DESCRIPTION
        "The input port Phase Built-Out ode (PBO). 
        1 = EVENT   : PBO enabled, PBO sent out, and stored 
                      in the event buffer.
        2 = REPORT  : PBO enabled, PBO sent out, but not stored 
                      in the event buffer.
        3 = NONE    : PBO enabled, but PBO event not sent out.
        4 = DISABLE : PBO disabled.

        Note: This is a system-wide command. 
        When the user writes this field, it will affect all DS1/E1 input modules in the system.
        "
    ::= { sys 1 }

    sysResetClk OBJECT-TYPE
        SYNTAX  INTEGER
                {
                    clka(1),
                    clkb(2)
                }
        MAX-ACCESS  read-write
        STATUS  current
        DESCRIPTION
        "Reset the specified clock.
        Restarts clock without maintaining current servo control values. 
        "
    ::= { sys 2 }


    -- **************************************************************
    -- SSU2000 KEEPALIVE TABLE
    -- **************************************************************

    sysKeepAliveTable OBJECT-TYPE
    SYNTAX  SEQUENCE OF SysAliveEntry
    MAX-ACCESS  not-accessible
    STATUS  current
    DESCRIPTION
      "Set system 'keep alive' mode 
      where a trap is generated automatically on a period specified by the customer
      This is intended to verify the upstream support that the SSU2000 and the associated communication path is functional"
    ::= { sys 3 }


    sysAliveEntry OBJECT-TYPE
    SYNTAX  SysAliveEntry
    MAX-ACCESS  not-accessible
    STATUS  current
    DESCRIPTION
    "System 'keepalive' attributes for TL1 or SNMP.
            sysAliveIndex
                Index value for each 'keepalive' table. 
            sysAliveType
                Keep Alive session type:
            sysAliveTime
                Keep alive message interval.  
    "
    INDEX   { sysAliveIndex }
    ::= { sysKeepAliveTable 1 }


    SysAliveEntry ::=
        SEQUENCE {
            sysAliveIndex
                INTEGER,    
            sysAliveType
                INTEGER,
            sysAliveTime
                INTEGER
        }

    sysAliveIndex OBJECT-TYPE
        SYNTAX  INTEGER (1..2)
        MAX-ACCESS  not-accessible
        STATUS  current
        DESCRIPTION
        "Index value for each 'keepalive' table. 
        This range of the value is from 1 to 2."
    ::= { sysAliveEntry 1 }


    sysAliveType OBJECT-TYPE
        SYNTAX  INTEGER
                {
                    tl1(1),
                    snmp(2)
                }
        MAX-ACCESS  read-only
        STATUS  current
        DESCRIPTION
        "Keep Alive session type:
        1 = TL1 session 
        2 = SNMP session
        "
    ::= { sysAliveEntry 2 }


    sysAliveTime OBJECT-TYPE
        SYNTAX  INTEGER (0..60)
        MAX-ACCESS  read-write
        STATUS  current
        DESCRIPTION
        "Keep alive message interval.  
        Valid range = 1 - 60 (minutes).
        0 = disabled (default)
        "
    ::= { sysAliveEntry 3 }


    -- **************************************************************
    -- Unit Operating Mode
    -- **************************************************************

    sysOpmode OBJECT-TYPE
        SYNTAX  INTEGER
                {
                    normal(1),      -- Non-Subtending
                    subtending(2),  -- Domestic Subtending
                    japanese(3)     -- Japanese Subtending
                }
        MAX-ACCESS  read-write
        STATUS  current
        DESCRIPTION
            "Set the operational mode in the SSU-2000. 
            normal(1), -- Non-Subtending
            subtending(2), -- Domestic Subtending
            japanese(3)  -- Japanese Subtending
            "
    ::= { sys 4 }


    -- **************************************************************
    -- TL1 format
    -- **************************************************************

    sysTl1Format OBJECT-TYPE
        SYNTAX  INTEGER
                {
                    gr831(1),
                    gr833(2)
                }
        MAX-ACCESS  read-write
        STATUS  current
        DESCRIPTION
        "Set the TL1 format in the SSU-2000.
        Allows the system to generate GR-831 compliant or GR-833 compliant autonomous events. 
        All SSU-2000 TL1 sessions will generate either GR-831 or GR-833 autonomous events.  
        Refer to TL1 Specification 12613127-001-2 for event formats 
        "
    ::= { sys 5 }

    -- **************************************************************
    -- LOGIN/ LOGOUT EVENT 
    -- **************************************************************

    sysEvtLogin OBJECT-TYPE
        SYNTAX  INTEGER
                {
                    disable(1), -- not store login and logout in the event log
                    enable(2)   -- store login and logout in the event log
                }
        MAX-ACCESS  read-write
        STATUS  current
        DESCRIPTION
        "Set LOGIN and LOGOUT events from being stored in the event log.

        disable(1), -- not store login and logout in the event log
        enable(2)   -- store login and logout in the event log
        "
    ::= { sys 6 }

    -- **************************************************************
    -- Alarm Cut Off (ACO) 
    -- **************************************************************

    sysAco OBJECT-TYPE
        SYNTAX  INTEGER
                {
                    active(1),  -- ACO active
                    inactive(2) -- ACO inactive
                }
        MAX-ACCESS  read-write
        STATUS  current
        DESCRIPTION
            "Set ACO when writing with active.
            It has NOP when write with inactive.
            When read, it returns the current state of ACO.
            "
    ::= { sys 7 }


    -- **************************************************************
    -- **************************************************************
    -- SSU2000 USERS TABLE GROUP
    -- **************************************************************
    -- **************************************************************

    userTable OBJECT-TYPE
    SYNTAX  SEQUENCE OF UserEntry
    MAX-ACCESS  not-accessible
    STATUS  current
    DESCRIPTION
        "Report valid user names and their associated user access level.
        This user list is used for connecting the ICS and TL1 command parser via RS232 or Ethernet port (telnet or TL1 port).
        Note: the password is not reported.
        "
    ::= { users 1 }

    userEntry OBJECT-TYPE
    SYNTAX  UserEntry
    MAX-ACCESS  not-accessible
    STATUS  current
    DESCRIPTION
          "User table attributes:
           userIndex
               Index for each user entry. 
           userlevel
               Reports user access level.
           username
               Reports user name.
          "
    INDEX   { userIndex }
    ::= { userTable 1 }


    UserEntry ::=
        SEQUENCE {
            userIndex
                INTEGER,
            userlevel
                INTEGER,
            username
                DisplayString
        }

    userIndex OBJECT-TYPE
        SYNTAX  INTEGER (1..25)
        MAX-ACCESS  not-accessible
        STATUS  current
        DESCRIPTION
              "Reports index for each user entry. 
              This value ranges from 1 to 25.
              "
    ::= { userEntry 1 }


    userlevel OBJECT-TYPE
        SYNTAX  INTEGER (1..4)
        MAX-ACCESS  read-only
        STATUS  current
        DESCRIPTION
        "Reports user access level.
        The user level:
        (1) USER - Read Only - can retrieve status information only.
        (2) TECHNICIAN - Read and limited set ability for fault isolating and installation setup of the unit.
        (3) SUPERVISORY - For configuration modifications.
        (4) ADMINISTRATOR - Setup or change user access.
        "
    ::= { userEntry 2 }


    username OBJECT-TYPE
        SYNTAX  DisplayString (SIZE (1..10))
        MAX-ACCESS  read-only
        STATUS  current
        DESCRIPTION
            "Reports user name."
    ::= { userEntry 3 }



    -- **************************************************************
    -- **************************************************************
    -- SSU2000 WHO TABLE GROUP
    -- **************************************************************
    -- **************************************************************

    whoTable OBJECT-TYPE
    SYNTAX  SEQUENCE OF WhoEntry
    MAX-ACCESS  not-accessible
    STATUS  current
    DESCRIPTION
    "Reports which users are logged into all active communication ports (RS232, TL1, or telnet). 
    It displays the username and the communication port.
    "
    ::= { who 1 }

    whoEntry OBJECT-TYPE
    SYNTAX  WhoEntry
    MAX-ACCESS  not-accessible
    STATUS  current
    DESCRIPTION
          "Report 'who' table attributes.
            whoIndex
                Report index of the 'who' entry. 
            whoPort
                Report logical communication port.
            whoName
                Report user name.
          "
    INDEX   { whoIndex }
    ::= { whoTable 1 }

    WhoEntry ::=
        SEQUENCE {
            whoIndex
                INTEGER,    
            whoPort
                INTEGER,
            whoName
                DisplayString
        }

    whoIndex OBJECT-TYPE
        SYNTAX  INTEGER (1..12)
        MAX-ACCESS  not-accessible
        STATUS  current
        DESCRIPTION
              "Report index of the 'who' entry. 
              This value ranges from 1 to 11."
    ::= { whoEntry 1 }

    whoPort OBJECT-TYPE
        SYNTAX  INTEGER
                {
                    local(1),
                    coma(2),
                    comb(3),
                    telneta(4),
                    telnetb(5),
                    telnetc(6),
                    telnetd(7),
                    etl1a(8),
                    etl1b(9),
                    etl1c(10),
                    etl1d(11)
                }
        MAX-ACCESS  read-only
        STATUS  current
        DESCRIPTION
            "Report logical communication port.
            local(1), -- serial local (craft) port
            coma(2), -- serial port A
            comb(3), -- serial port B
            telneta(4), -- telnet session A
            telnetb(5), -- telnet session B
            telnetc(6), -- telnet session C
            telnetd(7), -- telnet session D
            etl1a(8), -- TL1 session A
            etl1b(9), -- TL1 session B
            etl1c(10), -- TL1 session C
            etl1d(11) -- TL1 session D
            "
    ::= { whoEntry 2 }


    whoName OBJECT-TYPE
        SYNTAX  DisplayString (SIZE (1..10))
        MAX-ACCESS  read-only
        STATUS  current
        DESCRIPTION
            "Report user name."
    ::= { whoEntry 3 }


    -- **************************************************************
    -- **************************************************************
    -- SSU2000 NTPQ GROUP
    -- **************************************************************
    -- **************************************************************

    -- ******************************************
    -- SCALAR METHODS
    -- ******************************************

    ntpqXeq OBJECT-TYPE
        SYNTAX  DisplayString (SIZE (0..10))
        MAX-ACCESS  read-write 
        STATUS  current
        DESCRIPTION
        "Report/Set the PackeTime Module.
        The format is defined as xAy.
        where
        x is the chassis number: in this case is 1,
        A is the constant letter 'A', and is chassis/slot sepearator.
        y is the slot number: (range is 3 to 11)

        For example: 1A6 means this PackeTime located at chassis 1, slot 6

        Note: the user must specify valid PackeTime address.
        The valid module must be physically installed in the system.
        Note: Writing operation causes the system to execute the ntpq.
        The ntpq returned value may take 2 seconds.
        "
    ::= { ntpq 1 }

    ntpqSyspeer OBJECT-TYPE
        SYNTAX  DisplayString (SIZE (0..20)) 
        MAX-ACCESS  read-only 
        STATUS  current
        DESCRIPTION
        "Report syspeer is the IP address of peer selected by server as most likely to provide best timing information.
        "
    ::= { ntpq 4 }

    ntpqSysleap OBJECT-TYPE
        SYNTAX  INTEGER (-1..2)
        MAX-ACCESS  read-only
        STATUS  current
        DESCRIPTION
        "Report system leap indicator
        The NTP server leap indicator (0, +1, -1, or NOSYNC).
        2 = NOSYNC
        "
    ::= { ntpq 5 }

    ntpqSysstratum OBJECT-TYPE
        SYNTAX  INTEGER (0..16)
        MAX-ACCESS  read-only
        STATUS  current
        DESCRIPTION
        "Report system NTP server stratum level
        "
    ::= { ntpq 6 }

    ntpqSysprecision OBJECT-TYPE
        SYNTAX  INTEGER (-100..0)
        MAX-ACCESS  read-only
        STATUS  current
        DESCRIPTION
        "Report measurement of a number of significant bits in NTP timestamp
        "
    ::= { ntpq 7 }

    ntpqRootdelay OBJECT-TYPE
        SYNTAX  DisplayString (SIZE (0..20))
        MAX-ACCESS  read-only
        STATUS  current
        DESCRIPTION
        "Report calculated root delay value to primary source
        "
    ::= { ntpq 8 }

    ntpqRootdispersion OBJECT-TYPE
        SYNTAX  DisplayString (SIZE (0..20))
        MAX-ACCESS  read-only
        STATUS  current
        DESCRIPTION
        "Report NTP system Root Dispersion (max error relative to the primary 
        reference source at the root of the synchronization subnet, in seconds)
        "
    ::= { ntpq 9 }

    ntpqSysoffset OBJECT-TYPE
        SYNTAX  DisplayString (SIZE (0..20))
        MAX-ACCESS  read-only
        STATUS  current
        DESCRIPTION
        "Report clients calculated time offset value for the specified server
        "
    ::= { ntpq 10 }

    ntpqReftime OBJECT-TYPE
        SYNTAX  DisplayString (SIZE (0..60))
        MAX-ACCESS  read-only
        STATUS  current
        DESCRIPTION
        "Report local reference time
        "
    ::= { ntpq 11 }

    -- ******************************************
    -- NTPQ TABLE
    -- ******************************************

    ntpqTable OBJECT-TYPE
    SYNTAX  SEQUENCE OF NtpqEntry
    MAX-ACCESS  not-accessible
    STATUS  current
    DESCRIPTION
    "PackeTime NTPQ entries.
    "
    ::= { ntpq 3 }

    ntpqEntry OBJECT-TYPE
    SYNTAX  NtpqEntry
    MAX-ACCESS  not-accessible
    STATUS  current
    DESCRIPTION
    "Report NTPQ attributes.
            ntpqChassis
               Identifies which chassis is being addressed. 
            ntpqSlot
               Identifies which slot is being addressed. 
            ntpqIndex
               Identifies which index is being addressed. 
            ntpqValid
               Reports validity of entry.
            ntpqPeer
               Reports address of NTP peer
            ntpqRefid
               Reports NTP peer reference ID
            ntpqStratum
               Reports NTP peer stratum level
            ntpqPoll
               Reports NTP peer poll interval
            ntpqReach
               Reports NTP peer reachability
            ntpqDelay
               Reports NTP peer delay
            ntpqOffset
               Reports NTP peer offset
            ntpqJitter
               Report  NTP peer jitter 
     "
    INDEX   { ntpqChassis, ntpqSlot, ntpqIndex }
    ::= { ntpqTable 1 }

    NtpqEntry ::=
        SEQUENCE {
            ntpqChassis
                INTEGER,    
            ntpqSlot
                INTEGER,    
            ntpqIndex
                INTEGER,    
            ntpqValid
                ValidValue, 
            ntpqPeer
                DisplayString,
            ntpqRefid
                DisplayString,
            ntpqStratum
                INTEGER,
            ntpqPoll
                INTEGER,
            ntpqReach
                DisplayString,
            ntpqDelay
                DisplayString,
            ntpqOffset
                DisplayString,
            ntpqJitter
                DisplayString
        }

    ntpqChassis OBJECT-TYPE
        SYNTAX  INTEGER (1..1)
        MAX-ACCESS  not-accessible
        STATUS  current
        DESCRIPTION
        "Identifies which chassis is being addressed. 
        This chassis, slot, and index number uniquely identify each entry.
        "
    ::= { ntpqEntry 1 }

    ntpqSlot OBJECT-TYPE
        SYNTAX  INTEGER (1..20)
        MAX-ACCESS  not-accessible
        STATUS  current
        DESCRIPTION
        "Identifies which slot is being addressed. 
        This chassis, slot, and index number uniquely identify each entry.
        "
    ::= { ntpqEntry 2 }

    ntpqIndex OBJECT-TYPE
        SYNTAX  INTEGER (1..9)
        MAX-ACCESS  not-accessible
        STATUS  current
        DESCRIPTION
        "Identifies which index is being addressed. 
        This chassis, slot, and index number uniquely identify each entry.
        "
    ::= { ntpqEntry 3 }

    ntpqValid OBJECT-TYPE
        SYNTAX ValidValue
        MAX-ACCESS  read-only
        STATUS  current
        DESCRIPTION
        "Reports validity of entry.
        If this entry is not valid, all info in this entry has no meaning.
        "
    ::= { ntpqEntry 4 }

    ntpqPeer OBJECT-TYPE
        SYNTAX DisplayString (SIZE (0..20))
        MAX-ACCESS  read-only
        STATUS  current
        DESCRIPTION
        "Reports address of NTP peer
        "
    ::= { ntpqEntry 5 }

    ntpqRefid OBJECT-TYPE
        SYNTAX DisplayString (SIZE (0..20))
        MAX-ACCESS  read-only
        STATUS  current
        DESCRIPTION
        "Reports NTP system Reference
        "
    ::= { ntpqEntry 6 }

    ntpqStratum OBJECT-TYPE
        SYNTAX INTEGER (0..16)
        MAX-ACCESS  read-only
        STATUS  current
        DESCRIPTION
        "Reports NTP server stratum level
        "
    ::= { ntpqEntry 7 }

    ntpqPoll OBJECT-TYPE
        SYNTAX INTEGER (0..1024)
        MAX-ACCESS  read-only
        STATUS  current
        DESCRIPTION
        "Reports NTP server poll interval
        "
    ::= { ntpqEntry 8 }

    ntpqReach OBJECT-TYPE
        SYNTAX DisplayString (SIZE (0..20))
        MAX-ACCESS  read-only
        STATUS  current
        DESCRIPTION
        "Reports NTP server reachability
        "
    ::= { ntpqEntry 9 }

    ntpqDelay OBJECT-TYPE
        SYNTAX DisplayString (SIZE (0..20))
        MAX-ACCESS  read-only
        STATUS  current
        DESCRIPTION
        "Reports calculated root delay value to primary source
        "
    ::= { ntpqEntry 10 }

    ntpqOffset OBJECT-TYPE
        SYNTAX DisplayString (SIZE (0..20))
        MAX-ACCESS  read-only
        STATUS  current
        DESCRIPTION
        "Reports client's calculated time offset value for the specified server
        "
    ::= { ntpqEntry 11 }

    ntpqJitter OBJECT-TYPE
        SYNTAX DisplayString (SIZE (0..20))
        MAX-ACCESS  read-only
        STATUS  current
        DESCRIPTION
        "Report jitter value
        "
    ::= { ntpqEntry 12 }


    -- **************************************************************
    -- **************************************************************
    -- SSU2000 STATIC ROUTE STATUS GROUP
    -- **************************************************************
    -- **************************************************************

    -- ******************************************
    -- SCALAR METHODS
    -- ******************************************

    rtXeq OBJECT-TYPE
        SYNTAX  DisplayString (SIZE (0..10))
        MAX-ACCESS  read-write 
        STATUS  current
        DESCRIPTION
        "Write access level: level 1 or above

        The text string of the PackeTime Module.
        The format is defined as xAy.
        where
        x is the chassis number: in this case is 1,
        A is the constant letter 'A', and is chassis/slot sepearator.
        y is the slot number: (range is 3 to 11)

        For example: 1A6 means this PackeTime located at 
          chassis 1, slot 6

        Note1: the user must specify valid PackeTime address.
        The valid module must be physically installed in the system.
        Note2: Writing operation causes the system to execute the route table.
        The route table returned value may take 2 seconds.
        "
    ::= { route 1 }

    -- ******************************************
    -- ROUTE TABLE
    -- ******************************************

    routeTable OBJECT-TYPE
    SYNTAX  SEQUENCE OF RouteEntry
    MAX-ACCESS  not-accessible
    STATUS  current
    DESCRIPTION
      "PackeTime route entries. 
      "
    ::= { route 3 }

    rtEntry OBJECT-TYPE
    SYNTAX  RouteEntry
    MAX-ACCESS  not-accessible
    STATUS  current
    DESCRIPTION
    "PackeTime route table attributes:
            rtChassis
                Identifies which chassis is being addressed. 
            rtSlot
                Identifies which slot is being addressed. 
            rtIndex
                Identifies which index is being addressed. 
            rtValid
                Reports validity of entry.
            rtDest
                Reports destination network/host
            rtGate
                Reports destination gateway
            rtMask
                Reports destination network mask
            rtFlags
                Reports route flags
            rtMetric
                Reports the 'distance' to the target (router hops). 
            rtRef
                Reports number of references to this route.
            rtUse
                Report number of lookups for the route.
            rtIface
                Report interface associated with this route. 
    "
    INDEX   { rtChassis, rtSlot, rtIndex }
    ::= { routeTable 1 }

    RouteEntry ::=
        SEQUENCE {
            rtChassis
                INTEGER,    
            rtSlot
                INTEGER,    
            rtIndex
                INTEGER,    
            rtValid
                ValidValue, 
            rtDest
                IpAddress,
            rtGate
                IpAddress,
            rtMask
                IpAddress,
            rtFlags
                DisplayString,
            rtMetric
                INTEGER,
            rtRef
                INTEGER,
            rtUse
                INTEGER,
            rtIface
                INTEGER
        }

    rtChassis OBJECT-TYPE
        SYNTAX  INTEGER (1..1)
        MAX-ACCESS  not-accessible
        STATUS  current
        DESCRIPTION
        "Identifies which chassis is being addressed. 
        This chassis, slot, and index number uniquely identify each entry.
        "
    ::= { rtEntry 1 }

    rtSlot OBJECT-TYPE
        SYNTAX  INTEGER (1..20)
        MAX-ACCESS  not-accessible
        STATUS  current
        DESCRIPTION
        "Identifies which slot is being addressed. 
        This chassis, slot, and index number uniquely identify each entry.
        "
    ::= { rtEntry 2 }

    rtIndex OBJECT-TYPE
        SYNTAX  INTEGER (1..20)
        MAX-ACCESS  not-accessible
        STATUS  current
        DESCRIPTION
        "Identifies which index is being addressed. 
        This chassis, slot, and index number uniquely identify each entry.
        "
    ::= { rtEntry 3 }

    rtValid OBJECT-TYPE
        SYNTAX ValidValue
        MAX-ACCESS  read-only
        STATUS  current
        DESCRIPTION
            "Reports validity of entry.
            If this entry is not valid, all info in this entry has no meaning.
            "
    ::= { rtEntry 4 }

    rtDest OBJECT-TYPE
        SYNTAX IpAddress
        MAX-ACCESS  read-only
        STATUS  current
        DESCRIPTION
            "Reports destination network/host
            or 0.0.0.0 is default.
            "
    ::= { rtEntry 5 }

    rtGate OBJECT-TYPE
        SYNTAX IpAddress
        MAX-ACCESS  read-only
        STATUS  current
        DESCRIPTION
            "Reports gateway address 
            or 0.0.0.0 if none set
            "
    ::= { rtEntry 6 }

    rtMask OBJECT-TYPE
        SYNTAX IpAddress
        MAX-ACCESS  read-only
        STATUS  current
        DESCRIPTION
            "Reports  netmask  for  the  destination  net;  
            '255.255.255.255' for a host destination and '0.0.0.0' for the default route.
            "
    ::= { rtEntry 7 }

    rtFlags OBJECT-TYPE
        SYNTAX DisplayString (SIZE (0..6))
        MAX-ACCESS  read-only
        STATUS  current
        DESCRIPTION
            " Reports route table flags 
              U (route is up)
              H (target is a host)
              G (use gateway)
              R (reinstate route for dynamic routing)
              D (dynamically installed by daemon or redirect)
              M (modified from routing daemon or redirect)
              A (installed by addrconf)
              C (cache entry)
              !  (reject route)         
            "
    ::= { rtEntry 8 }

    rtMetric OBJECT-TYPE
        SYNTAX INTEGER (0..4)
        MAX-ACCESS  read-only
        STATUS  current
        DESCRIPTION
            "Reports the 'distance' to the target (router hops). 
            "
    ::= { rtEntry 9 }

    rtRef OBJECT-TYPE
        SYNTAX INTEGER (0..4)
        MAX-ACCESS  read-only
        STATUS  current
        DESCRIPTION
            "Reports number of references to this route.
            "
    ::= { rtEntry 10 }

    rtUse OBJECT-TYPE
        SYNTAX INTEGER (0..1)
        MAX-ACCESS  read-only
        STATUS  current
        DESCRIPTION
            "Report number of lookups for the route.
            "
    ::= { rtEntry 11 }

    rtIface OBJECT-TYPE
        SYNTAX INTEGER (0..34094)
        MAX-ACCESS  read-only
        STATUS  current
        DESCRIPTION
            "Report interface associated with this route. 
              0 = eth0 (Maintenance Port)
              1 = eth1 (Service Port A)
              2 = eth2 (Service Port B)
              3 = bond0 (Service Port Bonding)
              10000-14094 = eth1.xxxx
              20000-24094 = eth2.xxxx
              30000-34094 = bond0.xxxx
              where xxxx is the VLAN ID.
            "
    ::= { rtEntry 12 }


    -- **************************************************************
    -- **************************************************************
    -- SSU2000 TRAP REQUEST GROUP
    -- **************************************************************
    -- **************************************************************

    tprTag OBJECT-TYPE
        SYNTAX  INTEGER (1..2147483647)
        MAX-ACCESS  read-write
        STATUS  current
        DESCRIPTION
            "This command is to ask the agent to resend a lost trap.
            The lost trap is specified by its trap tag number.
            The trap tag number is a 32-bit positive integer. It will 
            rollover to one, when it reaches the maximum number 
            2147483647.

            If the tag number is beyond the agent's abilities to handle,
            it will respond with an error. Otherwise, the requested trap 
            will be sent to the manager.
             
            Note: When resending a trap, the 'tpEvt' field of trap is set 
            to 2 (RE-SEND). In the normal trap, the'tpEvt' field of trap 
            is set to 1 (AUTONOMOUS).
            "
    ::= { mTrapReq 1 }



    -- **************************************************************
    -- **************************************************************
    -- SSU2000 TRAP OBJECTS
    -- **************************************************************
    -- **************************************************************

    tpTag OBJECT-TYPE
        SYNTAX  INTEGER (1..2147483647)
        MAX-ACCESS  read-only
        STATUS  current
        DESCRIPTION
        "The trap counter which increments for each trap.
        "
    ::= { mTrapObjs 1 }

    tpEvt OBJECT-TYPE
        SYNTAX  INTEGER
                {
                    autonomous(1),
                    resend(2)
                }
        MAX-ACCESS  read-only
        STATUS  current
        DESCRIPTION
        "Indication of whether trap is an autonomous event or resend by user request.
        "
    ::= { mTrapObjs 2 }

    tpId OBJECT-TYPE
        SYNTAX  INTEGER (0..255)
        MAX-ACCESS  read-only
        STATUS  current
        DESCRIPTION
            "The trap ID number."
    ::= { mTrapObjs 3 }

    tpMCode OBJECT-TYPE
        SYNTAX  TModuleCode
        MAX-ACCESS  read-only
        STATUS  current
        DESCRIPTION
            "The trap module hex code (16-bits)."
    ::= { mTrapObjs 4 }

    tpTimestamp OBJECT-TYPE
        SYNTAX  DateAndTime
        MAX-ACCESS  read-only
        STATUS  current
        DESCRIPTION
            "This DateAndTime string contains the event timestamp."
    ::= { mTrapObjs 5 }

    tpChassis OBJECT-TYPE
        SYNTAX  INTEGER (1..5)
        MAX-ACCESS  read-only
        STATUS  current
        DESCRIPTION
        "The trap chassis number.
        In SSU2000, there are some modules have to inserted in the main chassis: 
        COMM, CLOCK, INPUT, GPS modules. 
        "
    ::= { mTrapObjs 6 }

    tpSlot OBJECT-TYPE
        SYNTAX  INTEGER (1..20)
        MAX-ACCESS  read-only
        STATUS  current
        DESCRIPTION
        "The trap slot number.
        In SSU2000, there are some modules have to inserted in the fixed locations: 
        COMM - 1A2
        CLOCK - 1A1 or 1A17 (physical slot address)
        GPS - 1A3 or 1A5.
        "
    ::= { mTrapObjs 7 }

    tpPort OBJECT-TYPE
        SYNTAX  INTEGER (0..20)
        MAX-ACCESS  read-only
        STATUS  current
        DESCRIPTION
        "The trap port number.
        If value 0, it means (DON'T CARE) whole module.
        In SSU2000, most of the DS1/E1 input module alarms specify the port number (1-3). 
        The remaining modules specify the port number as either '0' or '1'.
        "
    ::= { mTrapObjs 8 }


    tpAlmCode OBJECT-TYPE
        SYNTAX  INTEGER
                {
                    minor(1),
                    major(2),
                    critical(3),
                    ignore(4),
                    report(5)
                }
        MAX-ACCESS  read-only
        STATUS  current
        DESCRIPTION
        "The trap alarm code.

        Relationship between tpAlmCode and tpNtfCode. 
        For example:
        If for the set MINOR alarm, the tpAlmCode is MINOR and the tpNtfCode is MINOR.
        If the MINIR alarm is cleared, the tpAlmCode is MINOR and the tpNtfCode is CLEAR.

        For all events:
        The tpAlmCode and tpNtfCode are REPORT.
        "
    ::= { mTrapObjs 9 }

    tpNtfCode OBJECT-TYPE
        SYNTAX  INTEGER
                {
                    minor(1),
                    major(2),
                    critical(3),
                    report(5),
                    clear(6)
                }
        MAX-ACCESS  read-only
        STATUS  current
        DESCRIPTION
        "The trap alarm notification code.

        Relationship between tpAlmCode and tpNtfCode. 
        For example for alarms:
        If for the set MINOR alarm, the tpAlmCode is MINOR and the tpNtfCode is MINOR.
        If the MINOR alarm is cleared, the tpAlmCode is MINOR and the tpNtfCode is CLEAR.

        For all events:
        The tpAlmCode and tpNtfCode are REPORT.
        "
    ::= { mTrapObjs 10 }

    tpElevated OBJECT-TYPE
        SYNTAX  INTEGER
                {
                    yes(1),
                    no(2)
                }
        MAX-ACCESS  read-only
        STATUS  current
        DESCRIPTION
            "This alarm if elevated."
    ::= { mTrapObjs 11 }

    tpDescr OBJECT-TYPE
        SYNTAX  DisplayString (SIZE (0..255))
        MAX-ACCESS  read-only
        STATUS  current
        DESCRIPTION
            "The text string description of the event.
            "
    ::= { mTrapObjs 12 }


    -- **************************************************************
    -- **************************************************************
    -- SSU2000 TRAP NOTIFICATION OBJECTS
    -- **************************************************************
    -- **************************************************************

    ssuTraps    OBJECT-IDENTITY
        STATUS  current 
        DESCRIPTION
            "The SSU2000 traps"
    ::= {mTraps 0}


    ssuEvent    NOTIFICATION-TYPE
        OBJECTS {tpTag, tpEvt, tpId, tpMCode,tpTimestamp, 
                    tpChassis, tpSlot, tpPort, 
                    tpAlmCode, tpNtfCode, tpElevated, tpDescr}
        STATUS  current 
        DESCRIPTION
        "SSU2000 trap object which specifies trap tag number, trap id number, module hex code, timestamp, chassis number, 
        slot number, port number, alarm code, alarm notification code, and the text string description.
        "
    ::= {ssuTraps 1}


    -- **************************************************************
    -- **************************************************************
    -- SSU2000 INTERFACES OBJECTS
    -- Note: Developer could use following objects to determine the 
    -- SSU2000 resources in the unit right away.
    -- **************************************************************
    -- **************************************************************

    sifNtpNumber OBJECT-TYPE
        SYNTAX  INTEGER (0..1)
        MAX-ACCESS  read-only 
        STATUS  current
        DESCRIPTION
        "0 = if no NTP resource present 
         1 = if NTP presentt 
        "
    ::= { sInterfaces 1 }

    sifSnmpv2Number OBJECT-TYPE
        SYNTAX  INTEGER (0..1)
        MAX-ACCESS  read-only 
        STATUS  current
        DESCRIPTION
        "0 = if no SNMPv2 resource present (note: it is load resource, not enable/disable)
         1 = if SNMPv2 present
        "
    ::= { sInterfaces 2 }

    sifSnmpv3Number OBJECT-TYPE
        SYNTAX  INTEGER (0..1)
        MAX-ACCESS  read-only 
        STATUS  current
        DESCRIPTION
        "0 = if no SNMPv3 resource present (note: it is load resource, not enable/disable)
         1 = if SNMPv3 present
        "
    ::= { sInterfaces 3 }

    sifClkNumber OBJECT-TYPE
        SYNTAX  INTEGER (0..2)
        MAX-ACCESS  read-only 
        STATUS  current
        DESCRIPTION
        "0 = if no Clock Module present 
         x = number of Clock Modules present 
        "
    ::= { sInterfaces 10 }

    sifGpsNumber OBJECT-TYPE
        SYNTAX  INTEGER (0..2)
        MAX-ACCESS  read-only 
        STATUS  current
        DESCRIPTION
        "0 = if no GPS Module present 
         x = number of GPS Modules present 
        "
    ::= { sInterfaces 11 }

    sifInpDs1Number OBJECT-TYPE
        SYNTAX  INTEGER (0..10)
        MAX-ACCESS  read-only 
        STATUS  current
        DESCRIPTION
        "0 = if no DS1 Input Module present 
         x = number of DS1 Input Modules present 
        "
    ::= { sInterfaces 12 }

    sifInpE1Number OBJECT-TYPE
        SYNTAX  INTEGER (0..10)
        MAX-ACCESS  read-only 
        STATUS  current
        DESCRIPTION
        "0 = if no E1 Input Module present 
         x = number of E1 Input Modules present 
        "
    ::= { sInterfaces 13 }

    sifInpCcNumber OBJECT-TYPE
        SYNTAX  INTEGER (0..10)
        MAX-ACCESS  read-only 
        STATUS  current
        DESCRIPTION
        "0 = if no ANSI CC Input Module present 
         x = number of ANSI CC Input Modules present 
        "
    ::= { sInterfaces 14 }

    sifOutDs1Number OBJECT-TYPE
        SYNTAX  INTEGER (0..100)
        MAX-ACCESS  read-only 
        STATUS  current
        DESCRIPTION
        "0 = if no DS1 Output Module present 
         x = number of DS1 Output Modules present 
        "
    ::= { sInterfaces 15 }

    sifOutE1Number OBJECT-TYPE
        SYNTAX  INTEGER (0..100)
        MAX-ACCESS  read-only 
        STATUS  current
        DESCRIPTION
        "0 = if no E1 Output Module present 
         x = number of E1 Output Modules present 
        "
    ::= { sInterfaces 16 }

    sifOut2048Number OBJECT-TYPE
        SYNTAX  INTEGER (0..100)
        MAX-ACCESS  read-only 
        STATUS  current
        DESCRIPTION
        "0 = if no 2048 Output Module present 
         x = number of 2048 Output Modules present 
        "
    ::= { sInterfaces 17 }

    sifOutCcNumber OBJECT-TYPE
        SYNTAX  INTEGER (0..100)
        MAX-ACCESS  read-only 
        STATUS  current
        DESCRIPTION
        "0 = if no ANSI CC Output Module present 
         x = number of ANSI CC Output Modules present 
        "
    ::= { sInterfaces 18 }


    sifOutE12048Number OBJECT-TYPE
        SYNTAX  INTEGER (0..100)
        MAX-ACCESS  read-only 
        STATUS  current
        DESCRIPTION
        "0 = if no E1/2048KHZ Output Module present 
         x = number of E1/2048KHZ Output Modules present 
        "
    ::= { sInterfaces 19 }

    sifOut422Number OBJECT-TYPE
        SYNTAX  INTEGER (0..100)
        MAX-ACCESS  read-only 
        STATUS  current
        DESCRIPTION
        "0 = if no RS422 Output Module present 
         x = number of RS422 Output Modules present 
        "
    ::= { sInterfaces 20 }

    sifLrmDs1Number OBJECT-TYPE
        SYNTAX  INTEGER (0..100)
        MAX-ACCESS  read-only 
        STATUS  current
        DESCRIPTION
        "0 = if no DS1 LRM Module present 
         x = number of DS1 LRM Modules present 
        "
    ::= { sInterfaces 21 }


    sifOutJsineNumber OBJECT-TYPE
        SYNTAX  INTEGER (0..100)
        MAX-ACCESS  read-only 
        STATUS  current
        DESCRIPTION
        "0 = if no Japanese Sine (J/SW) Output Module present 
         x = number of Sine (J/SW) Output Modules present 
        "
    ::= { sInterfaces 22 }

    sifInpJsineNumber OBJECT-TYPE
        SYNTAX  INTEGER (0..10)
        MAX-ACCESS  read-only 
        STATUS  current
        DESCRIPTION
        "0 = if no Japanese Sine (J/SW) Input Module present 
         x = number of Sine (J/SW) Input Modules present 
        "
    ::= { sInterfaces 23 }

    sifOutJccNumber OBJECT-TYPE
        SYNTAX  INTEGER (0..100)
        MAX-ACCESS  read-only 
        STATUS  current
        DESCRIPTION
        "0 = if no Japanese CC (J/CC) Output Module present 
         x = number of Japanese CC (J/CC) Output Modules present 
        "
    ::= { sInterfaces 24 }

    sifInpJccNumber OBJECT-TYPE
        SYNTAX  INTEGER (0..10)
        MAX-ACCESS  read-only 
        STATUS  current
        DESCRIPTION
        "0 = if no Japanese CC (J/CC) Input Module present 
         x = number of Japanese CC (J/CC) Input Modules present 
        "
    ::= { sInterfaces 25 }

    sifLrmE1Number OBJECT-TYPE
        SYNTAX  INTEGER (0..100)
        MAX-ACCESS  read-only 
        STATUS  current
        DESCRIPTION
        "0 = if no E1 LRM Module present 
         x = number of E1 LRM Modules present 
        "
    ::= { sInterfaces 26 }

    -- **************************************************************
    -- SSU2000 PACKETIME PTP MODULE STATUS GROUP
    -- **************************************************************

    staPtPtpTable OBJECT-TYPE
    SYNTAX  SEQUENCE OF StaPtPtpEntry
    MAX-ACCESS  not-accessible
    STATUS  current
    DESCRIPTION
    "List of PackeTime PTP status information.
    "
    ::= { statusPtPtp 1 }


    staPtPtpEntry OBJECT-TYPE
    SYNTAX  StaPtPtpEntry
    MAX-ACCESS  not-accessible
    STATUS  current
    DESCRIPTION
    "The entries of PackeTime PTP status attributes.
    "
    INDEX   { staPtPtpChassis, staPtPtpSlot}
    ::= { staPtPtpTable 1 }

    StaPtPtpEntry ::=
        SEQUENCE {
            staPtPtpChassis
                INTEGER,    
            staPtPtpSlot
                INTEGER,    
            staPtPtpStatus
                INTEGER,    
            staPtPtpClkSel
                INTEGER,
            staPtPtpClka
                ActiveValue,
            staPtPtpClkb
                ActiveValue,
            staPtPtpClkc
                ActiveValue,
            staPtPtpClkd
                ActiveValue,
            staPtPtpRednt
                INTEGER,
            staPtPtpModState
                INTEGER,
            staPtPtpPAState
                INTEGER,
            staPtPtpTod
                OnValue,
            staPtPtpCommit
                INTEGER
        }

    staPtPtpChassis OBJECT-TYPE
        SYNTAX  INTEGER (1..5)
        MAX-ACCESS  not-accessible
        STATUS  current
        DESCRIPTION
        "Identifies which chassis is being addressed. 
        This chassis number and slot number uniquely identify each inventory entry.
        "
    ::= { staPtPtpEntry 1 }

    staPtPtpSlot OBJECT-TYPE
        SYNTAX  INTEGER (1..20)
        MAX-ACCESS  not-accessible
        STATUS  current
        DESCRIPTION
        "Identifies which slot position is being addressed. 
        This chassis number and slot number uniquely identify each inventory entry.
        "
    ::= { staPtPtpEntry 2 }


    staPtPtpStatus OBJECT-TYPE
        SYNTAX  INTEGER
                {
                    ok(1),
                    disable(3),
                    fault(4),
                    reject(5)
                }
        MAX-ACCESS  read-only
        STATUS  current
        DESCRIPTION
        "Reports PackeTime PTP module status.
        ok(1), -- module is enabled and operating without faults
        disable(3), -- module is disabled
        fault(4), -- module is enabled and operating with fault(s)
        reject(5) -- module type between redundant modules do not agree
        "
    ::= { staPtPtpEntry 3 }

    staPtPtpClkSel OBJECT-TYPE
        SYNTAX  INTEGER
                {
                    clka(1),
                    clkb(2),
                    clkc(3),
                    clkd(4),
                    none(5)
                }
        MAX-ACCESS  read-only
        STATUS  current
        DESCRIPTION
        "Reports which clock reference is selected to generate the output reference.
        clka(1), -- Clock A is selected as the Primary clock
        clkb(2), -- Clock B is selected as the Primary clock
        clkc(3), -- Clock C is selected as the Primary clock
        clkd(4), -- Clock D is selected as the Primary clock
        none(5) -- no clock is selected
        "
    ::= { staPtPtpEntry 4 }

    staPtPtpClka OBJECT-TYPE
        SYNTAX  ActiveValue
        MAX-ACCESS  read-only
        STATUS  current
        DESCRIPTION
        "Reports that clock A is available.
        "
    ::= { staPtPtpEntry 5 }

    staPtPtpClkb OBJECT-TYPE
        SYNTAX  ActiveValue
        MAX-ACCESS  read-only
        STATUS  current
        DESCRIPTION
        "Reports that clock B is available.
        "
    ::= { staPtPtpEntry 6 }

    staPtPtpClkc OBJECT-TYPE
        SYNTAX  ActiveValue
        MAX-ACCESS  read-only
        STATUS  current
        DESCRIPTION
        "Reports that clock C is available.
        "
    ::= { staPtPtpEntry 7 }

    staPtPtpClkd OBJECT-TYPE
        SYNTAX  ActiveValue
        MAX-ACCESS  read-only
        STATUS  current
        DESCRIPTION
        "Reports that clock D is available.
        "
    ::= { staPtPtpEntry 8 }

    staPtPtpRednt OBJECT-TYPE
        SYNTAX  INTEGER (0..20)
        MAX-ACCESS  read-only
        STATUS  current
        DESCRIPTION
        "Reports the adjacent slot number if this module is the redundant pair. 
        If this module is not redundant, zero is reported.
        "
    ::= { staPtPtpEntry 9 }

    staPtPtpModState OBJECT-TYPE
        SYNTAX  INTEGER
                {
                    active(1),
                    stdby(2),
                    fault(3),
                    stdalone(4)
                }
        MAX-ACCESS  read-only
        STATUS  current
        DESCRIPTION
        "Reports the current operational mode.
        active(1), --If the module is in redundant pair and selected, it shall return active.
        stdby(2), --If the module is in redundant pair but not selected, it shall return stdby (standby).
        fault(3), --If the module disabled, it will return fault.
        stdalone(4) --If the module is not redundant pair, it shall return stdalone (standalone).
        "
    ::= { staPtPtpEntry 10 }

    staPtPtpPAState OBJECT-TYPE
        SYNTAX  INTEGER
                {
                    active(1),
                    stdby(2),
                    fault(3),
                    stdalone(4)
                }
        MAX-ACCESS  read-only
        STATUS  current
        DESCRIPTION
        "Reports the current operational mode.
        active(1), --If service ports are bonded and selected, it shall return active.
        stdby(2), --If service ports are bonded but not selected, it shall return stdby (standby).
        fault(3), --Service port is faulted.
        stdalone(4) --If service ports are not bonded , it shall return stdalone (standalone).
        "
    ::= { staPtPtpEntry 11 }

    staPtPtpTod OBJECT-TYPE
        SYNTAX  OnValue
        MAX-ACCESS  read-only
        STATUS  current
        DESCRIPTION
        "Reports if the PTP Time of Day is valid or invalid.
        "
    ::= { staPtPtpEntry 12 }

    staPtPtpCommit OBJECT-TYPE
        SYNTAX  INTEGER
                {
                    done(1),
                    prog(2)
                }
        MAX-ACCESS  read-only
        STATUS  current
        DESCRIPTION
        "Reports the Commit command status.
        1 = done
        2 = in progress
        "
    ::= { staPtPtpEntry 13 }


    -- **************************************************************
    -- SSU2000 ptpDfltDataSetTable
    -- **************************************************************

    ptpDfltDataSetTable OBJECT-TYPE
    SYNTAX  SEQUENCE OF PtpDfltDataSetEntry
    MAX-ACCESS  not-accessible
    STATUS  current
    DESCRIPTION
    "List of the PackeTime PTP Management Messages: ptpDefaultDataSet
    "
    ::= { statusPtPtp 2 }

    ptpDfltDataSetEntry OBJECT-TYPE
    SYNTAX  PtpDfltDataSetEntry
    MAX-ACCESS  not-accessible
    STATUS  current
    DESCRIPTION
    "The entries of PackeTime PTP Management Messages: ptpDefaultDataSet attributes.
    "
    INDEX   { ptpDfltDataSetChassis, ptpDfltDataSetSlot}
    ::= { ptpDfltDataSetTable 1 }

    PtpDfltDataSetEntry ::=
        SEQUENCE {
            ptpDfltDataSetChassis
                INTEGER,    
            ptpDfltDataSetSlot
                INTEGER,    
            ptpDfltDataSetClockId
                OCTET STRING,
            ptpDfltDataSetClockClass
                INTEGER,
            ptpDfltDataSetClockAccuracy
                INTEGER,
            ptpDfltDataSetTimeTraceable
                TrueValue,
            ptpDfltDataSetFreqTraceable
                TrueValue,
            ptpDfltDataSetDomainNumber
                INTEGER    
        }

    ptpDfltDataSetChassis OBJECT-TYPE
        SYNTAX  INTEGER (1..5)
        MAX-ACCESS  not-accessible
        STATUS  current
        DESCRIPTION
        "Identifies which chassis is being addressed. 
        This chassis number and slot number uniquely identify each inventory entry.
        "
    ::= { ptpDfltDataSetEntry 1 }

    ptpDfltDataSetSlot OBJECT-TYPE
        SYNTAX  INTEGER (1..20)
        MAX-ACCESS  not-accessible
        STATUS  current
        DESCRIPTION
        "Identifies which slot position is being addressed. 
        This chassis number and slot number uniquely identify each inventory entry.
        "
    ::= { ptpDfltDataSetEntry 2 }

    ptpDfltDataSetClockId OBJECT-TYPE
        SYNTAX  OCTET STRING (SIZE(8))
        MAX-ACCESS  read-only
        STATUS  current
        DESCRIPTION
        "Reports the PTP Clock Identity (64-bit value). 
        The clock id is a hexadecimal format. 
        "
    ::= { ptpDfltDataSetEntry 3 }

    ptpDfltDataSetClockClass OBJECT-TYPE
        SYNTAX  INTEGER (0..255)
        MAX-ACCESS  read-only
        STATUS  current
        DESCRIPTION
        "Reports the PTP Master Clock Class
        "
    ::= { ptpDfltDataSetEntry 4 }


    ptpDfltDataSetClockAccuracy OBJECT-TYPE
        SYNTAX  INTEGER
        	{
        	within25ns   (32),
		    within100ns  (33),
		    within250ns  (34),
		    within1000ns (35),
		    within2p5us  (36),
		    within10us   (37),
		    within25us   (38),
		    within100us  (39),
		    within250us  (40),
		    within1ms    (41),
		    within2p5ms  (42),
		    within10ms   (43),
		    within25ms   (44),
		    within100ms  (45),
		    within250ms  (46),
		    within1sec   (47),
		    within10sec  (48),
		    beyond10sec  (49),
		    unknown      (254)
        	}
        MAX-ACCESS  read-only
        STATUS  current
        DESCRIPTION
        "Reports the PTP Master Clock Accuracy
        Following is the Clock Accuracy Table
        32 = within 25   ns
        33 = within 100  ns
        34 = within 250  ns
        35 = within 1000 ns
        36 = within 2.5  us
        37 = within 10   us
        38 = within 25   us
        39 = within 100  us
        40 = within 250  us
        41 = within 1    ms 
        42 = within 2.5  ms
        43 = within 10   ms
        44 = within 25   ms
        45 = within 100  ms
        46 = within 250  ms
        47 = within 1    sec
        48 = within 10   sec
        49 = beyond 10   sec
        254 = unknown       
        "
    ::= { ptpDfltDataSetEntry 5 }

    ptpDfltDataSetTimeTraceable OBJECT-TYPE
        SYNTAX  TrueValue
        MAX-ACCESS  read-only
        STATUS  current
        DESCRIPTION
        "Reports the PTP Master Time Traceability
        1 = true, time traceable
        2 = false, time not traceable
        "
    ::= { ptpDfltDataSetEntry 6 }

    ptpDfltDataSetFreqTraceable OBJECT-TYPE
        SYNTAX  TrueValue
        MAX-ACCESS  read-only
        STATUS  current
        DESCRIPTION
        "Reports the PTP Master Frequency Traceability
        1 = true, frequency traceable
        2 = false, frequency not traceable
        "
    ::= { ptpDfltDataSetEntry 7 }


    ptpDfltDataSetDomainNumber OBJECT-TYPE
        SYNTAX  INTEGER (0..255) 
        MAX-ACCESS  read-only
        STATUS  current
        DESCRIPTION
        "Reports the PTP domain number. 
        "
    ::= { ptpDfltDataSetEntry 8 }
    

     -- **************************************************************
    -- SSU2000 ptpClockDescrTable
    -- **************************************************************

    ptpClockDescrTable OBJECT-TYPE
    SYNTAX  SEQUENCE OF PtpClockDescrEntry
    MAX-ACCESS  not-accessible
    STATUS  current
    DESCRIPTION
    "List of the PackeTime PTP Management Messages: ptpClockDescription.
    "
    ::= { statusPtPtp 3 }

    ptpClockDescrEntry OBJECT-TYPE
    SYNTAX  PtpClockDescrEntry
    MAX-ACCESS  not-accessible
    STATUS  current
    DESCRIPTION
    "Entries of the PackeTime PTP Management Messages: ptpClockDescription attributes.
    "
    INDEX   { ptpClockDescrChassis, ptpClockDescrSlot}
    ::= { ptpClockDescrTable 1 }

    PtpClockDescrEntry ::=
        SEQUENCE {
            ptpClockDescrChassis
                INTEGER,    
            ptpClockDescrSlot
                INTEGER,    
            ptpClockDescrClockType
                INTEGER,   
            ptpClockDescrProtocolAddress
                IpAddress,  
            ptpClockDescrManufacturerId
                OCTET STRING,
            ptpClockDescrProfileId
                OCTET STRING
         }

    ptpClockDescrChassis OBJECT-TYPE
        SYNTAX  INTEGER (1..5)
        MAX-ACCESS  not-accessible
        STATUS  current
        DESCRIPTION
        "Identifies which chassis is being addressed. 
        This chassis number and slot number uniquely identify each inventory entry.
        "
    ::= { ptpClockDescrEntry 1 }

    ptpClockDescrSlot OBJECT-TYPE
        SYNTAX  INTEGER (1..20)
        MAX-ACCESS  not-accessible
        STATUS  current
        DESCRIPTION
        "Identifies which slot position is being addressed. 
        This chassis number and slot number uniquely identify each inventory entry.
        "
    ::= { ptpClockDescrEntry 2 }

     ptpClockDescrClockType OBJECT-TYPE
        SYNTAX  INTEGER
        	{
        	ordinary (32768)
        	}
        MAX-ACCESS  read-only
        STATUS  current
        DESCRIPTION
        "Reports the PTP Clock Type
        The value 0x8000 meant Ordinary Clock
        "
    ::= { ptpClockDescrEntry 3 }

    ptpClockDescrProtocolAddress OBJECT-TYPE
        SYNTAX  IpAddress
        MAX-ACCESS  read-only
        STATUS  current
        DESCRIPTION
        "Reports the PTP IP Address of PTP port.            
        "
    ::= { ptpClockDescrEntry 4 }

    ptpClockDescrManufacturerId OBJECT-TYPE
        SYNTAX  OCTET STRING (SIZE(3))
        MAX-ACCESS  read-only
        STATUS  current
        DESCRIPTION
        "Reports the PTP Manufacturer Id. 
        The format is a 3 bytes array.
        The Manufacturer Id is 00 B0 AE
        "
    ::= { ptpClockDescrEntry 5 }

    ptpClockDescrProfileId OBJECT-TYPE
        SYNTAX  OCTET STRING (SIZE(6))
        MAX-ACCESS  read-only
        STATUS  current
        DESCRIPTION
        "Reports the PTP Profile ID. 
        The format is 6 bytes array.
		If Telecom-2008, the profile_id is: 00 00 00 00 00 00
		If ITU G8265.1,  the profile_id is: 00 19 A7 00 01 00	
        "
    ::= { ptpClockDescrEntry 6 }
    

      -- **************************************************************
    -- SSU2000 ptpTimeMessageTable
    -- **************************************************************

    ptpTimeMessageTable OBJECT-TYPE
    SYNTAX  SEQUENCE OF PtpTimeMessageEntry
    MAX-ACCESS  not-accessible
    STATUS  current
    DESCRIPTION
    "List of the PackeTime PTP Management Messages: ptpTimeMessage.
    "
    ::= { statusPtPtp 4 }

    ptpTimeMessageEntry OBJECT-TYPE
    SYNTAX  PtpTimeMessageEntry
    MAX-ACCESS  not-accessible
    STATUS  current
    DESCRIPTION
    "The entries of PackeTime PTP Management Messages: ptpTimeMessage attributes
    "
    INDEX   { ptpTimeMessageChassis, ptpTimeMessageSlot}
    ::= { ptpTimeMessageTable 1 }

    PtpTimeMessageEntry ::=
        SEQUENCE {
            ptpTimeMessageChassis
                INTEGER,    
            ptpTimeMessageSlot
                INTEGER,    
            ptpTimeMessageCurrentTimeSec
                OCTET STRING,
            ptpTimeMessageCurrentTimeNSec
                Counter32    
         }

    ptpTimeMessageChassis OBJECT-TYPE
        SYNTAX  INTEGER (1..5)
        MAX-ACCESS  not-accessible
        STATUS  current
        DESCRIPTION
        "Identifies which chassis is being addressed. 
        This chassis number and slot number uniquely identify each inventory entry.
        "
    ::= { ptpTimeMessageEntry 1 }

    ptpTimeMessageSlot OBJECT-TYPE
        SYNTAX  INTEGER (1..20)
        MAX-ACCESS  not-accessible
        STATUS  current
        DESCRIPTION
        "Identifies which slot position is being addressed. 
        This chassis number and slot number uniquely identify each inventory entry.
        "
    ::= { ptpTimeMessageEntry 2 }

    ptpTimeMessageCurrentTimeSec OBJECT-TYPE
        SYNTAX  OCTET STRING (SIZE(6))
        MAX-ACCESS  read-only
        STATUS  current
        DESCRIPTION
        "Reports the PTP Current Time of seconds. 
        The current is a 6-byte a hexadecimal format.
        "
    ::= { ptpTimeMessageEntry 3 }

     ptpTimeMessageCurrentTimeNSec OBJECT-TYPE
        SYNTAX  Counter32
        MAX-ACCESS  read-only
        STATUS  current
        DESCRIPTION
        "Reports the PTP fractional Current Time of nanoseconds
        "
    ::= { ptpTimeMessageEntry 4 }

      -- **************************************************************
    -- SSU2000 ptpPortDataSetTable
    -- **************************************************************

    ptpPortDataSetTable OBJECT-TYPE
    SYNTAX  SEQUENCE OF PtpPortDataSetEntry
    MAX-ACCESS  not-accessible
    STATUS  current
    DESCRIPTION
    "List of the PackeTime PTP Management Messages: ptpPortDataSet
    "
    ::= { statusPtPtp 5 }

    ptpPortDataSetEntry OBJECT-TYPE
    SYNTAX  PtpPortDataSetEntry
    MAX-ACCESS  not-accessible
    STATUS  current
    DESCRIPTION
    "The entries of PackeTime PTP Management Messages: ptpPortDataSet attributes
    "
    INDEX   { ptpPortDataSetChassis, ptpPortDataSetSlot}
    ::= { ptpPortDataSetTable 1 }

    PtpPortDataSetEntry ::=
        SEQUENCE {
            ptpPortDataSetChassis
                INTEGER,    
            ptpPortDataSetSlot
                INTEGER, 
            ptpPortDataSetClockId
            	OCTET STRING,
            ptpPortDataSetPortNumber
                INTEGER,    
            ptpPortDataSetPortState
                INTEGER    
         }

    ptpPortDataSetChassis OBJECT-TYPE
        SYNTAX  INTEGER (1..5)
        MAX-ACCESS  not-accessible
        STATUS  current
        DESCRIPTION
        "Identifies which chassis is being addressed. 
        This chassis number and slot number uniquely identify each inventory entry.
        "
    ::= { ptpPortDataSetEntry 1 }

    ptpPortDataSetSlot OBJECT-TYPE
        SYNTAX  INTEGER (1..20)
        MAX-ACCESS  not-accessible
        STATUS  current
        DESCRIPTION
        "Identifies which slot position is being addressed. 
        This chassis number and slot number uniquely identify each inventory entry.
        "
    ::= { ptpPortDataSetEntry 2 }

    ptpPortDataSetClockId OBJECT-TYPE
        SYNTAX  OCTET STRING (SIZE(8))
        MAX-ACCESS  read-only
        STATUS  current
        DESCRIPTION
        "Reports the PTP Clock Identity (64-bit value). 
        The port clock id is a hexadecimal format. 
        "
    ::= { ptpPortDataSetEntry 3 }

     ptpPortDataSetPortNumber OBJECT-TYPE
        SYNTAX  INTEGER (0..65535)
        MAX-ACCESS  read-only
        STATUS  current
        DESCRIPTION
        "Reports the PTP Port Number
        "
    ::= { ptpPortDataSetEntry 4 }

     ptpPortDataSetPortState OBJECT-TYPE
        SYNTAX  INTEGER
        	{
        	notdefined (0),
	    	initializing (1),
	    	faulty (2),
	   	disabled (3),
	    	listening (4),
	    	premaster (5),
	    	master	(6),
	    	passive	(7),
	    	uncalibrated (8),
	    	slave (9)
        	}
        MAX-ACCESS  read-only
        STATUS  current
        DESCRIPTION
        "Reports the PTP Port State
        Following is the PTP Port State Table
        	0 = notdefined 
	    	1 = initializing
	    	2 = faulty
	   	3 = disabled
	    	4 = listening
	    	5 = premaster, it is a state before becoming a Master
	    	6 = master
	    	7 = passive
	    	8 = uncalibrated 
	    	9 = slave
        "
    ::= { ptpPortDataSetEntry 5 }


    -- ******************************************
    -- PACKETIME PTP MODULE SETUP GROUP
    -- ******************************************

    setPtPtpTable OBJECT-TYPE
    SYNTAX  SEQUENCE OF SetPtPtpEntry
    MAX-ACCESS  not-accessible
    STATUS  current
    DESCRIPTION
        "A list of PackeTime PTP status and settings.
        "
    ::= { setupPtPtp 1 }

    setPtPtpEntry OBJECT-TYPE
    SYNTAX  SetPtPtpEntry
    MAX-ACCESS  not-accessible
    STATUS  current
    DESCRIPTION
    "The enties of the PackeTime PTP settings and attributes.
    "
    INDEX   { setPtPtpChassis, setPtPtpSlot}
    ::= { setPtPtpTable 1 }

    SetPtPtpEntry ::=
        SEQUENCE {
            setPtPtpChassis
                INTEGER,    
            setPtPtpSlot
                INTEGER,    
            setPtPtpCommit
                INTEGER,    
            setPtPtpService
                EnaValue,   
            setPtPtpClockId
                OCTET STRING,
            setPtPtpDomain
                INTEGER,    
            setPtPtpTimescale
                INTEGER,    
            setPtPtpSyncLimit
                INTEGER,    
            setPtPtpAnnounceLimit
                INTEGER,    
            setPtPtpDelayLimit
                INTEGER,    
            setPtPtpDscpState
                EnaValue,   
            setPtPtpDscpValue
                INTEGER,    
            setPtPtpMaxClient
                INTEGER,    
            setPtPtpPortPriority1
                INTEGER,    
            setPtPtpPortPriority2
                INTEGER,    
            setPtPtpUniLeaseDuration
                INTEGER,    
            setPtPtpUniNegotiation
                EnaValue,                               
            setPtPtpTwostep
                EnaValue,                               
            setPtPtpProfile
                INTEGER,    
            setPtPtpSsmOption
                INTEGER,    
            setPtPtpBypass
                OnValue,
            setPtPtpModActive
                YesValue,   
            setPtPtpEthRate
                INTEGER,
            setPtPtpVlan    
                EnaValue,    
            setPtPtpRmvClient    
                OCTET STRING
        }

    setPtPtpChassis OBJECT-TYPE
        SYNTAX  INTEGER (1..5)
        MAX-ACCESS  not-accessible
        STATUS  current
        DESCRIPTION
        "Identifies which chassis is being addressed. 
        This chassis number and slot number uniquely identify each entry.
          "
    ::= { setPtPtpEntry 1 }

    setPtPtpSlot OBJECT-TYPE
        SYNTAX  INTEGER (1..20)
        MAX-ACCESS  not-accessible
        STATUS  current
        DESCRIPTION
        "Identifies which slot is being addressed. 
        This chassis number and slot number uniquely identify each entry.
          "
    ::= { setPtPtpEntry 2 }

    setPtPtpCommit OBJECT-TYPE
        SYNTAX  INTEGER 
                {
                    yes(1)
                }
        MAX-ACCESS  read-write
        STATUS  current
        DESCRIPTION
        "Commit all provisioned parameters, this action makes the parameters active. 
        This command will also store the parameters to non-volatile memory.

        Note: This field only has meaning for a writing (1).
        "
    ::= { setPtPtpEntry 3 }

    setPtPtpService OBJECT-TYPE
        SYNTAX  EnaValue
        MAX-ACCESS  read-write
        STATUS  current
        DESCRIPTION
        "Set the PTP service (daemon) to enable or disable. 
        This command is applied to both modules if redundant cards installed.

        1 = Enabled  
        2 = Disabled
        "
    ::= { setPtPtpEntry 4 }

    setPtPtpClockId OBJECT-TYPE
        SYNTAX  OCTET STRING (SIZE(8))
        MAX-ACCESS  read-write
        STATUS  current
        DESCRIPTION
        "Set the clockId is the PTP Port Clock Identity (64-bit value). 
        The clockid is a hexadecimal format. 

        Note: users shall enter command COMMIT to take changes into effect      
        "
    ::= { setPtPtpEntry 5 }

    setPtPtpDomain OBJECT-TYPE
        SYNTAX  INTEGER (0..255) 
        MAX-ACCESS  read-write
        STATUS  current
        DESCRIPTION
        "Set the PTP port domain. 
        Note: users shall enter command COMMIT to take changes into effect      
        "
    ::= { setPtPtpEntry 6 }

    setPtPtpTimescale OBJECT-TYPE
        SYNTAX  INTEGER  
                {
                    ptp (1), 
                    arb (2) 
                }
        MAX-ACCESS  read-write
        STATUS  current
        DESCRIPTION
        "Set timescale to 'PTP' or 'ARB'. 
        Note: users shall enter command COMMIT to take changes into effect      
        "
    ::= { setPtPtpEntry 7 }

    setPtPtpSyncLimit OBJECT-TYPE
        SYNTAX  INTEGER (-7..7) 
        MAX-ACCESS  read-write
        STATUS  current
        DESCRIPTION
        "Set the unicast Sync message rate  (2^y). 
        The range of the rate value is {-7 to 7}. 
        For example, the configurable range is  -7, means 128 per second
        "
    ::= { setPtPtpEntry 8 }

    setPtPtpAnnounceLimit OBJECT-TYPE
        SYNTAX  INTEGER (-3..4) 
        MAX-ACCESS  read-write
        STATUS  current
        DESCRIPTION
        "Set unicast announce message rate  (2^y). 
        The range of the rate value is {-3 to 4}. 
        For example, the configurable range is  -3, means 8 per second
        "
    ::= { setPtPtpEntry 9 }

    setPtPtpDelayLimit OBJECT-TYPE
        SYNTAX  INTEGER (-7..7) 
        MAX-ACCESS  read-write
        STATUS  current
        DESCRIPTION
        "Set unicast delay resp message rate  (2^y). 
        The range of the rate value is {-7 to 7}. 
        For example, the configurable range is  -6, means 64 per second
        "
    ::= { setPtPtpEntry 10 }

    setPtPtpDscpState OBJECT-TYPE
        SYNTAX  EnaValue  
        MAX-ACCESS  read-write
        STATUS  current
        DESCRIPTION
        "Set the DSCP state to enable or disable.
        "
    ::= { setPtPtpEntry 11 }

    setPtPtpDscpValue OBJECT-TYPE
        SYNTAX  INTEGER (0..63) 
        MAX-ACCESS  read-write
        STATUS  current
        DESCRIPTION
        "Set DSCP value.
        "
    ::= { setPtPtpEntry 12 }

    setPtPtpMaxClient OBJECT-TYPE
        SYNTAX  INTEGER (64..400) 
        MAX-ACCESS  read-write
        STATUS  current
        DESCRIPTION
        "Set the PTP max clients.
        "
    ::= { setPtPtpEntry 13 }

    setPtPtpPortPriority1 OBJECT-TYPE
        SYNTAX  INTEGER (0..255) 
        MAX-ACCESS  read-write
        STATUS  current
        DESCRIPTION
        "Set the PTP Port Priority 1 {0 to 255}.
        "
    ::= { setPtPtpEntry 14 }

    setPtPtpPortPriority2 OBJECT-TYPE
        SYNTAX  INTEGER (0..255)
        MAX-ACCESS  read-write
        STATUS  current
        DESCRIPTION
        "Set the PTP Port Priority 2 {0 to 255}.
        "
    ::= { setPtPtpEntry 15 }

    setPtPtpUniLeaseDuration OBJECT-TYPE
        SYNTAX  INTEGER (10..1000) 
        MAX-ACCESS  read-write
        STATUS  current
        DESCRIPTION
        "Set the PTP Max Dynamic Unicast Lease Interval, {10 to 1000}
        "
    ::= { setPtPtpEntry 16 }

    setPtPtpUniNegotiation OBJECT-TYPE
        SYNTAX  EnaValue  
        MAX-ACCESS  read-write
        STATUS  current
        DESCRIPTION
        "Set the PTP Unicast Negotiation state: Enable or Disable
        "
    ::= { setPtPtpEntry 17 }

    setPtPtpTwostep OBJECT-TYPE
        SYNTAX  EnaValue  
        MAX-ACCESS  read-write
        STATUS  current
        DESCRIPTION
        "Set the PTP Two-Step clock state: Enable or Disable
        Note: users shall enter command COMMIT to take changes into effect      
        "
    ::= { setPtPtpEntry 18 }

    setPtPtpProfile OBJECT-TYPE
        SYNTAX  INTEGER  
                {
                    telecom2008 (1), 
                    ituG8265dot1 (4) 
                }
        MAX-ACCESS  read-write
        STATUS  current
        DESCRIPTION
        "Set PTP profile telecom_2008 or itu_g8265_1. 
        Note: users shall enter command COMMIT to take changes into effect      
        "
    ::= { setPtPtpEntry 19 }

    setPtPtpSsmOption OBJECT-TYPE
        SYNTAX  INTEGER  
                {
                    option1 (1), 
                    option2 (2) 
                }
        MAX-ACCESS  read-write
        STATUS  current
        DESCRIPTION
        "Set PTP ssm-option in Option 1 or Option 2. 
        "
    ::= { setPtPtpEntry 20 }

    setPtPtpBypass OBJECT-TYPE
        SYNTAX  OnValue
        MAX-ACCESS  read-write
        STATUS  current
        DESCRIPTION
        "Set the clock C state, or bypass clock, to enabled or disabled.
        "
    ::= { setPtPtpEntry 30 }

    setPtPtpModActive OBJECT-TYPE
        SYNTAX  YesValue
        MAX-ACCESS  read-write
        STATUS  current
        DESCRIPTION
        "Set the specified module in the redundant pair to be Active. 
        Note1: This command only applies when the module in the redundant pair.
        Note2: This field only has meaning for a writing (1).
        Note3: Don't apply COMMIT after this command.
        "
    ::= { setPtPtpEntry 31 }

    setPtPtpEthRate OBJECT-TYPE
        SYNTAX  INTEGER
                {
                    all (0), 
                    r100  (1), 
                    r1000 (2) 
                }
        MAX-ACCESS  read-write
        STATUS  current
        DESCRIPTION
        "Set the PTP port transmission rate.
        all -  means auto negotiation capable of both 100M and 1000Mbits/s rate. 
        r100 - means auto negotiation capable of only 100Mbit/s rate.
        r1000 - means auto negotiation capable of only 1000Mbit/s rate

        Note: this setting is only applied to the copper SFP, not fiber. 
        If fiber SFP installed, this setting is ignored.
        "
    ::= { setPtPtpEntry 32 }

    setPtPtpVlan OBJECT-TYPE
        SYNTAX  EnaValue
        MAX-ACCESS  read-write
        STATUS  current
        DESCRIPTION
        "Set the VLAN state.
        1 = Enabled  
        2 = Disabled

        Users must COMMIT for changes into effect.          
        "
    ::= { setPtPtpEntry 33 }

    setPtPtpRmvClient OBJECT-TYPE
        SYNTAX  OCTET STRING (SIZE(8))
        MAX-ACCESS  read-write
        STATUS  current
        DESCRIPTION
        "This is an action command and not a configuration command.
        This command remove a client from a ptp client list. 
        The clockid is a hexadecimal format. 

        Note: this field only has meansing for write action with proper clock id.
        When it read, it always returns as all zero octet string.      
        "
    ::= { setPtPtpEntry 34 }

    -- ******************************************
    -- PACKETIME PTP MODULE PORT SETUP GROUP
    -- ******************************************

    setPtpPortTable OBJECT-TYPE
    SYNTAX  SEQUENCE OF SetPtpPortEntry
    MAX-ACCESS  not-accessible
    STATUS  current
    DESCRIPTION
          "Set PackeTime PTP ethernet port information.
          "
    ::= { setupPtPtp 2 }


    setPtpPortEntry OBJECT-TYPE
    SYNTAX  SetPtpPortEntry
    MAX-ACCESS  not-accessible
    STATUS  current
    DESCRIPTION
    "PackeTime PTP ethernet port state and settings information.
    setPtPtpPortChassis
        Identifies which chassis is being addressed. 
    setPtPtpPortSlot
        Identifies which slot is being addressed. 
    setPtPtpPortNum
        Identifies which port is being addressed. 
    setPtPtpPortAddr
        Set the port IP address         
    setPtPtpPortMask
        Set the port network mask           
    setPtPtpPortGate
        Set the port gateway address            
    "
    INDEX   { setPtpPortChassis, setPtpPortSlot, setPtpPortNum}
    ::= { setPtpPortTable 1 }

    SetPtpPortEntry ::=
        SEQUENCE {
            setPtpPortChassis
                INTEGER,    
            setPtpPortSlot
                INTEGER,    
            setPtpPortNum
                INTEGER,    
            setPtpPortAddr
                IpAddress,  
            setPtpPortMask
                IpAddress,  
            setPtpPortGate
                IpAddress   
        }

    setPtpPortChassis OBJECT-TYPE
        SYNTAX  INTEGER (1..5)
        MAX-ACCESS  not-accessible
        STATUS  current
        DESCRIPTION
        "Identifies which chassis is being addressed. 
        This chassis, slot, and port number uniquely identify each entry.
        "
    ::= { setPtpPortEntry 1 }

    setPtpPortSlot OBJECT-TYPE
        SYNTAX  INTEGER (1..20)
        MAX-ACCESS  not-accessible
        STATUS  current
        DESCRIPTION
        "Identifies which slot is being addressed. 
        This chassis, slot, and port number uniquely identify each entry.
        "
    ::= { setPtpPortEntry 2 }

    setPtpPortNum OBJECT-TYPE
        SYNTAX  INTEGER (1..2)
        MAX-ACCESS  not-accessible
        STATUS  current
        DESCRIPTION
        "Identifies which port is being addressed. 
        This chassis, slot, and port number uniquely identify each entry.

        PTPTP ethernet interface number. 
        1 = Service Port A 
        2 = Maintenance Port
        "
    ::= { setPtpPortEntry 3 }

    setPtpPortAddr OBJECT-TYPE
        SYNTAX  IpAddress
        MAX-ACCESS  read-write
        STATUS  current
        DESCRIPTION
        "Set the port IP address            
        "
    ::= { setPtpPortEntry 4 }

    setPtpPortMask OBJECT-TYPE
        SYNTAX  IpAddress
        MAX-ACCESS  read-write
        STATUS  current
        DESCRIPTION
        "Set the port network mask          
        "
    ::= { setPtpPortEntry 5 }

    setPtpPortGate OBJECT-TYPE
        SYNTAX  IpAddress
        MAX-ACCESS  read-write
        STATUS  current
        DESCRIPTION
        "Set the port gateway address           
        "
    ::= { setPtpPortEntry 6 }


    -- ******************************************
    -- PACKETIME PTP VLAN GROUP
    -- ******************************************

    setPtpVlanTable OBJECT-TYPE
    SYNTAX  SEQUENCE OF SetPtpVlanEntry
    MAX-ACCESS  not-accessible
    STATUS  current
    DESCRIPTION
    "List of PackeTime PTP vlan attributes.
    The Virtural Local Area Network is implemented per IEEE 802.1Q.
        "
    ::= { setupPtPtp 3 }

    setPtpVlanEntry OBJECT-TYPE
    SYNTAX  SetPtpVlanEntry
    MAX-ACCESS  not-accessible
    STATUS  current
    DESCRIPTION
    "A PackeTime PTP vlan attributes and settings:
    setPtPtpVlanChassis
        Identifies which chassis is being addressed. 
    setPtPtpVlanSlot
        Identifies which slot is being addressed. 
    setPtpVlanIndex
        Set the VLAN index number for PTPTP.
    setPtpVlanState
        Enable or Disable of a given VLAN Entry 
    setPtpVlanAddr
        VLAN IP Address (If 0.0.0.0, and then SET, this will delete this entry)
		note: This field has to set first with a valid non-zero IP address, if you want to add a new entry
    setPtpVlanMask
        VLAN Network Mask
    setPtpVlanGate
        VLAN Gateway
    setPtpVlanId
        VLAN ID
    setPtpVlanPriority
        VLAN Priority
	Note: The module setPtPtpVlan set must be enabled, and each of the enabled entires 
	has meaning.
    "
    INDEX   { setPtpVlanChassis, setPtpVlanSlot, setPtpVlanIndex}
    ::= { setPtpVlanTable 1 }

    SetPtpVlanEntry ::=
        SEQUENCE {
            setPtpVlanChassis
                INTEGER,    
            setPtpVlanSlot
                INTEGER,    
            setPtpVlanIndex
                INTEGER,    
            setPtpVlanState
                EnaValue,   
            setPtpVlanAddr
                IpAddress,  
            setPtpVlanMask
                IpAddress,  
            setPtpVlanGate
                IpAddress,   
            setPtpVlanId
                INTEGER,    
            setPtpVlanPriority
                INTEGER    
        }

    setPtpVlanChassis OBJECT-TYPE
        SYNTAX  INTEGER (1..5)
        MAX-ACCESS  not-accessible
        STATUS  current
        DESCRIPTION
        "Identifies which chassis is being addressed. 
        This chassis and slot number uniquely identify each entry.
        "
    ::= { setPtpVlanEntry 1 }

    setPtpVlanSlot OBJECT-TYPE
        SYNTAX  INTEGER (1..20)
        MAX-ACCESS  not-accessible
        STATUS  current
        DESCRIPTION
            "Identifies which slot is being addressed. 
            This chassis and slot number uniquely identify each entry.
            "
    ::= { setPtpVlanEntry 2 }

    setPtpVlanIndex OBJECT-TYPE
        SYNTAX  INTEGER (1..4)
        MAX-ACCESS  not-accessible
        STATUS  current
        DESCRIPTION
        "Set the VLAN index number for PTP. 
        "
    ::= { setPtpVlanEntry 3 }

    setPtpVlanState OBJECT-TYPE
        SYNTAX  EnaValue
        MAX-ACCESS  read-write
        STATUS  current
        DESCRIPTION
        "Enable or Disable of a given VLAN entry 
        Note: The value has meaning, only when the VLAN is enabled
        "
    ::= { setPtpVlanEntry 4 }

    setPtpVlanAddr OBJECT-TYPE
        SYNTAX  IpAddress
        MAX-ACCESS  read-write
        STATUS  current
        DESCRIPTION
        "Ethernet VLAN Port IP Address
        Note: you must have IP address in order to add or change other fields.
        This field has to set first with a valid non-zero IP address, if you want to add a new entry         
        If the IP is 0.0.0.0, and use the SET operation, this mean delete this entry. 
        "
    ::= { setPtpVlanEntry 5 }

    setPtpVlanMask OBJECT-TYPE
        SYNTAX  IpAddress
        MAX-ACCESS  read-write
        STATUS  current
        DESCRIPTION
        "Ethernet VLAN Port Network Mask            
        "
    ::= { setPtpVlanEntry 6 }

    setPtpVlanGate OBJECT-TYPE
        SYNTAX  IpAddress
        MAX-ACCESS  read-write
        STATUS  current
        DESCRIPTION
        "Ethernet VLAN Port Gateway Address         
        "
    ::= { setPtpVlanEntry 7 }

    setPtpVlanId OBJECT-TYPE
        SYNTAX  INTEGER (2..4094)
        MAX-ACCESS  read-write
        STATUS  current
        DESCRIPTION
        "Set the VLAN ID (2..4094) for Service Port A 
        Note: The value has meaning, only when the VLAN is enabled
        "
    ::= { setPtpVlanEntry 8 }


    setPtpVlanPriority OBJECT-TYPE
        SYNTAX  INTEGER (0..7)
        MAX-ACCESS  read-write
        STATUS  current
        DESCRIPTION
        "VLAN Priority (0..7) for Service Port A 
        Note: The value has meaning, only when the VLAN is enabled
        "
    ::= { setPtpVlanEntry 9 }

    -- **************************************************************
    -- SSU2000 PACKETIME PTP GETCLIENTLIST GROUP
    -- **************************************************************

    ptpclientTable OBJECT-TYPE
    SYNTAX  SEQUENCE OF PtpclientEntry
    MAX-ACCESS  not-accessible
    STATUS  current
    DESCRIPTION
    "Reports PackeTime PTP client list entries.

    Usage: you need to specify a PTP blade address in ptpclientParmLoc, and
    then execute the command ptpclientCmdXeq first. The PTP client list will be
    saved. This ptpclientTable will display all the PTP client list contents 
    of this saved information.
      "
    ::= { ptpclient 1 }

    ptpclientEntry OBJECT-TYPE
    SYNTAX  PtpclientEntry
    MAX-ACCESS  not-accessible
    STATUS  current
    DESCRIPTION
    "Reports PackeTime PTP client list containing each PTP client status value.
    ptpclientChassis
        Identifies which chassis is being addressed. 
    ptpclientSlot
        Identifies which slot is being addressed. 
    ptpclientData
        Reports the contents of the Client data TLV:
    "
    INDEX   { ptpclientChassis, ptpclientSlot}
    ::= { ptpclientTable 1 }

    PtpclientEntry ::=
        SEQUENCE {
            ptpclientChassis
                INTEGER,    
            ptpclientSlot
                INTEGER,    
            ptpclientData
                OCTET STRING
        }

    ptpclientChassis OBJECT-TYPE
        SYNTAX  INTEGER (1..5)
        MAX-ACCESS  not-accessible
        STATUS  current
        DESCRIPTION
        "Identifies which chassis is being addressed. 
        This chassis and slot number uniquely identify each entry.
        "
    ::= { ptpclientEntry 1 }

    ptpclientSlot OBJECT-TYPE
        SYNTAX  INTEGER (1..20)
        MAX-ACCESS  not-accessible
        STATUS  current
        DESCRIPTION
        "Identifies which slot is being addressed. 
        This chassis and slot number uniquely identify each entry.
        "
    ::= { ptpclientEntry 2 }

    ptpclientData OBJECT-TYPE
        SYNTAX  OCTET STRING (SIZE(40))
        MAX-ACCESS  read-only
        STATUS  current
        DESCRIPTION
        "Reports the contents of the Client data TLV:
        INTEGER - mode, 0:dynamic, 1:static
        INTEGER - ip address
        OCTET - clock id
        INTEGER -  VLAN ID, if 0xffff, then there is no vlan
        INTEGER -  VLAN Priority
        INTEGER -  Sync Limit (signed value), if 99, the disable
        INTEGER -  Announce Limit (signed value), if 99, the disable
        INTEGER -  Delay Limit (signed value), if 99, the disable
        "
    ::= { ptpclientEntry 3 }


    -- ******************************************
    -- SCALAR METHODS  (GETCLIENTLIST)
    -- ******************************************

    ptpclientParmLoc OBJECT-TYPE
        SYNTAX  DisplayString (SIZE (0..10))
        MAX-ACCESS  read-write 
        STATUS  current
        DESCRIPTION
        "Set the ports VLAN address.
        where
        x is the chassis number: in this case is 1-5,
        A is the constant letter 'A', and is chassis/slot sepearator.
        y is the slot number: (range is 1 to 14)

        For example: 1A6 means this port located at chassis 1, slot 6

        Note: the user must specify valid PTP address.
        The valid port must be physically installed in the system.
        "
    ::= { ptpclient 2 }

    ptpclientCmdXeq OBJECT-TYPE
        SYNTAX  YesValue 
        MAX-ACCESS  read-write 
        STATUS  current
        DESCRIPTION
        "Reports the current client list in the module. 
        The max number of client is 400
        "
    ::= { ptpclient 3 }


    -- **************************************************************
    -- SSU2000 SYNCE STATUS GROUP
    -- **************************************************************

    staSynceTable OBJECT-TYPE
    SYNTAX  SEQUENCE OF StaSynceEntry
    MAX-ACCESS  not-accessible
    STATUS  current
    DESCRIPTION
    "List of SyncE status information:
	port_direction, ethernet_mode, rx_ssm, and tx_ssm  
    "
    ::= { statusSynce 1 }

    staSynceEntry OBJECT-TYPE
    SYNTAX  StaSynceEntry
    MAX-ACCESS  not-accessible
    STATUS  current
    DESCRIPTION
    "The entries of SyncE status attributes.
    "
    INDEX   { staSynceChassis, staSynceSlot}
    ::= { staSynceTable 1 }

    StaSynceEntry ::=
        SEQUENCE {
            staSynceChassis
                INTEGER,    
            staSynceSlot
                INTEGER,    
            staSyncePortDirection
                INTEGER,    
            staSynceEthernetMode
                INTEGER,    
            staSynceRxSsm
                INTEGER,    
            staSynceTxSsm
                INTEGER    
          }

    staSynceChassis OBJECT-TYPE
        SYNTAX  INTEGER (1..5)
        MAX-ACCESS  not-accessible
        STATUS  current
        DESCRIPTION
        "Identifies which chassis is being addressed. 
        This chassis number and slot number uniquely identify each inventory entry.
        "
    ::= { staSynceEntry 1 }

    staSynceSlot OBJECT-TYPE
        SYNTAX  INTEGER (1..20)
        MAX-ACCESS  not-accessible
        STATUS  current
        DESCRIPTION
        "Identifies which slot position is being addressed. 
        This chassis number and slot number uniquely identify each inventory entry.
        "
    ::= { staSynceEntry 2 }

    staSyncePortDirection OBJECT-TYPE
        SYNTAX  INTEGER
				{
					input (1),
					output (2)
				}
        MAX-ACCESS  read-only
        STATUS  current
        DESCRIPTION
        "Reports SyncE Port Direction to be either Output or Input. 
        The output port is a SyncE master port, and input port is a SyncE slave port.
        "
    ::= { staSynceEntry 3 }

    staSynceEthernetMode OBJECT-TYPE
        SYNTAX  INTEGER
				{
					synchronous (1),
					asynchronous (2)
				}
        MAX-ACCESS  read-only
        STATUS  current
        DESCRIPTION
        "Reports SyncE operated on Ethernet to be either synchronous or 
        asynchronous.  It is synchronous mode, when an optical SFP is detected 
        at an Ethernet port. It is an asynchronous mode, when an electrical SFP 
        is detected at an Ethernet port, or there is no SFP detected.
        "
    ::= { staSynceEntry 4 }

    staSynceRxSsm OBJECT-TYPE
        SYNTAX  INTEGER	(0..15 | 255)
        MAX-ACCESS  read-only
        STATUS  current
        DESCRIPTION
        "Reports SyncE the current rx ssm value (0 .. 15).
        If 255, SyncE does not receive ESMC messages
        "
    ::= { staSynceEntry 5 }

    staSynceTxSsm OBJECT-TYPE
        SYNTAX  INTEGER	(0..15 | 255)
        MAX-ACCESS  read-only
        STATUS  current
        DESCRIPTION
        "Reports SyncE the current tx ssm value (0 .. 15).
        If 255, SyncE does not transmit ESMC messages
        "
    ::= { staSynceEntry 6 }

    -- ******************************************
    -- PACKETIME SYNCE SETUP GROUP
    -- ******************************************

    setSynceTable OBJECT-TYPE
    SYNTAX  SEQUENCE OF SetSynceEntry
    MAX-ACCESS  not-accessible
    STATUS  current
    DESCRIPTION
        "A list of SyncE settings.
        "
    ::= { setupSynce 1 }

    setSynceEntry OBJECT-TYPE
    SYNTAX  SetSynceEntry
    MAX-ACCESS  not-accessible
    STATUS  current
    DESCRIPTION
    "The enties of the SyncE settings and attributes.
    "
    INDEX   { setSynceChassis, setSynceSlot}
    ::= { setSynceTable 1 }

    SetSynceEntry ::=
        SEQUENCE {
            setSynceChassis
                INTEGER,    
            setSynceSlot
                INTEGER,    
            setSyncePortDirection
                INTEGER,    
            setSynceEsmc
                EnaValue,    
            setSynceQl
                EnaValue,    
            setSynceOutQl
                INTEGER    
         }

 	setSynceChassis OBJECT-TYPE
        SYNTAX  INTEGER (1..5)
        MAX-ACCESS  not-accessible
        STATUS  current
        DESCRIPTION
        "Identifies which chassis is being addressed. 
        This chassis number and slot number uniquely identify each entry.
          "
    ::= { setSynceEntry 1 }

    setSynceSlot OBJECT-TYPE
        SYNTAX  INTEGER (1..20)
        MAX-ACCESS  not-accessible
        STATUS  current
        DESCRIPTION
        "Identifies which slot is being addressed. 
        This chassis number and slot number uniquely identify each entry.
          "
    ::= { setSynceEntry 2 }

     setSyncePortDirection OBJECT-TYPE
        SYNTAX  INTEGER
				{
					input (1),
					output (2)
				}
        MAX-ACCESS  read-write
        STATUS  current
        DESCRIPTION
        "Set SyncE Port Direction to be either Output or Input. 
        The output port is a SyncE master port, and input port 
        is a SyncE slave port.
        "
    ::= { setSynceEntry 3 }

     setSynceEsmc OBJECT-TYPE
        SYNTAX  EnaValue
        MAX-ACCESS  read-write
        STATUS  current
        DESCRIPTION
        "Set the Ethernet Synchronization Message Channel (ESMC) 
        state is either Enable or Disable. If ESMC is enabled, 
        the ESMC is used; otherwise, it shall not be used.
        "
    ::= { setSynceEntry 4 }

     setSynceQl OBJECT-TYPE
        SYNTAX  EnaValue
        MAX-ACCESS  read-write
        STATUS  current
        DESCRIPTION
        "Set the Quality Level (QL, i.e. SSM) in the ESMC is either 
        Enabled or Disabled. If QL is enabled, the SSM in the ESMC 
        is used; otherwise, it shall not be used.
        "
    ::= { setSynceEntry 5 }

     setSynceOutQl OBJECT-TYPE
        SYNTAX  INTEGER
				{
					bidirectional (1),
					unidirectional (2)
				}
        MAX-ACCESS  read-write
        STATUS  current
        DESCRIPTION
        "Set the Output QL mode is either unidirectional or bidirectional. 
        In the unidirectional mode, the rx ESMC from the downstream NE is 
        ignored. The tx SSM will be determined by the system clock state only. 
        In the bidirectional mode, the rx ESMC from the downstream NE is not 
        ignored but  is used for testing purposes and some interoperability cases.
        "
    ::= { setSynceEntry 6 }
    

    END
