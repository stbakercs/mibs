SYMM-SMI DEFINITIONS ::= BEGIN

IMPORTS
OBJECT-TYPE,
MODULE-IDENTITY,
OBJECT-IDENTITY
FROM RFC-1212
DisplayString
FROM RFC1213-MIB
TRAP-TYPE
FROM RFC-1215
enterprises,
Integer32, Unsigned32
FROM RFC1155-SMI;

symmetricom MODULE-IDENTITY
    LAST-UPDATED "200906111200Z"
    ORGANIZATION "Symmetricom, Inc."
    CONTACT-INFO
      "
            Symmetricom, Inc.
            2300 Orchard Parkway
            San Jose, CA 95131"
    DESCRIPTION
        "This is the MIB Module for Symmetricom's enterprise specific
        parameters."
    REVISION "200906111200Z"
    DESCRIPTION "rbb - Cleaning up errors in the mib metadata"
    ::= {enterprises 9070 } --assigned by IANA

symmNetworkManagement OBJECT-IDENTITY
    STATUS		current
    DESCRIPTION
        "This is the root object identifier for all MIBS under the
        Symmetricom tree."
    ::= { symmetricom 1 }

symmCmipManagement OBJECT-IDENTITY
    STATUS		current
    DESCRIPTION
        "This is the root object identifier for CMIP based objects."
    ::= { symmNetworkManagement 1 }

symmSnmpManagement OBJECT-IDENTITY
    STATUS		current
    DESCRIPTION
        "This is the root object identifier for SNMP based objects."
    ::= { symmNetworkManagement 2 }

symmTimePictra OBJECT-IDENTITY
    STATUS		current
    DESCRIPTION
        "This is reserved for objects related to Symmetricom's TimePictra
        products."
    ::= { symmSnmpManagement 1 }

symmBroadband OBJECT-IDENTITY
    STATUS		current
    DESCRIPTION
        "The subtree that contains objects related to Symmetricom's GoWide
        products."
    ::= { symmSnmpManagement 2 }

symmTTM OBJECT-IDENTITY
    STATUS		current
    DESCRIPTION
        "The subtree that contains objects related to Symmetricom's
        Timing, Test and Measurement products."
    ::= { symmSnmpManagement 3 }

products	OBJECT IDENTIFIER ::= {symmTTM 1}
experiment  OBJECT IDENTIFIER ::= {symmTTM 99}

ts2000		OBJECT IDENTIFIER ::= {products 1}
nts			OBJECT IDENTIFIER ::= {products 2}
ts2100		OBJECT IDENTIFIER ::= {products 3}
s100		OBJECT IDENTIFIER ::= {products 4}
syncserver	OBJECT IDENTIFIER ::= {products 5}
xli			OBJECT IDENTIFIER ::= {products 6}

version	OBJECT IDENTIFIER ::= {syncserver 1}

ntpSystem	OBJECT IDENTIFIER ::= {version 1}
tyming		OBJECT IDENTIFIER ::= {version 2}
gps			OBJECT IDENTIFIER ::= {version 3}
dialup		OBJECT IDENTIFIER ::= {version 4}
net			OBJECT IDENTIFIER ::= {version 5}
etc			OBJECT IDENTIFIER ::= {version 6}

ntpSysLeap OBJECT-TYPE
    SYNTAX INTEGER {
            noWarning(0),
            addSecond(1),
            subtractSecond(2),
            alarm(3)}
    ACCESS read-only
    STATUS current
    DESCRIPTION 
        "NTP Leap Indicator.  This is a two-bit code 
        warning of an impending leap second to be inserted
        into the NTP timescale.  The bits are set before
        23:59 on the day of insertion and reset after 00:00
        on the following day.  This causes the number of
        seconds (rollover interval) in the day of insertion
        to be increased or decreased by one.  In the case
        of primary servers the bits are set by operator 
        intervention, while in the case of secondary servers
        the bits are set by the protocol.  The two bits, 
        bit 0 and bit 1, respectively, are coded as follows:
        ===================================================
        00      no warning
        01      last minute has 61 seconds
        10      last minute has 59 seconds
        11      alarm condition(clock not synchronized)
        ===================================================
        In all except the alarm condition(11), NTP itself
        does nothing with these bits, except pass them on to
        the time-conversion routines that are not part of
        NTP.  The alarm condition occurs when, for whatever
        reason, the local clock is not synchronized, such 
        as when first coming up or after an extended period
        when no primary reference source is available."
::= {ntpSystem 1}

ntpSysStratum OBJECT-TYPE
    SYNTAX		Integer32 (0..255)
    MAX-ACCESS	read-only
    STATUS		current
    DESCRIPTION
        "Current NTP stratum level.  This is an integer
        indicating the stratum of the local clock with
        values defined as follows:
        ================================================
        0       unspecified
        1       primary reference (e.g., calibrated atomic
                    clock, radio clock)
        2-255   secondary reference (via NTP)
        ================================================"
::= {ntpSystem 2}

ntpSysPrecision OBJECT-TYPE
    SYNTAX 		Integer32
    MAX-ACCESS 	read-only
    STATUS 		current
    DESCRIPTION
        "Current NTP precision value.  This is a signed
        integer indicating the precision of the various
        clocks, in seconds to the nearest power of two.
        The value must be rounded to the next larger power
        of two; for instance, a 50-Hz (20ms) or 60-Hz (16.17ms)
        power-frequency clock would be assigned the value 
        -5 (31.25ms), while a 1000-Hz (1ms) crystal-controlled
        clock would be assigned the value -9 (1.95ms)."
::= {ntpSystem 3}

ntpSysRootDelay OBJECT-TYPE
    SYNTAX		OCTET STRING
    MAX-ACCESS	read-only
    STATUS		current
    DESCRIPTION 
        "Total roundtrip delay to the primary reference 
        source at the root of the synchronization
        subnet, in seconds. Also known as root distance."
::= {ntpSystem 4}

ntpSysRootDispersion OBJECT-TYPE
    SYNTAX		OCTET STRING
    MAX-ACCESS	read-only
    STATUS		current
    DESCRIPTION 
        "Maximum error relative to the primary reference 
        source at the root of the synchronization subnet, 
        in seconds.  Only positive values greater than 
        zero are possible."
::= {ntpSystem 5}

ntpSysRefID OBJECT-TYPE
    SYNTAX 		DisplayString (SIZE (1..40))
    MAX-ACCESS 	read-only
    STATUS 		current
    DESCRIPTION
        "NTP Reference Clock Identifier.  This is a
        32 bit code identifying the particular reference
        clock.  In the case of stratum 0 (unspecified) or
        stratum 1 (primary reference), this is a four-
        octet, left-justified, zero-padded ASCII string.
        While not enumerated as part of the NTP spec, the
        following are suggested ASCII identifiers:
        ==============================================
        DCN             DCN routing protocol
        NIST            NIST public modem
        TSP             TSP time protocol
        DTS             Digital Time Service
        ATOM            Atomic clock (calibrated)
        VLF             VLF radio (OMEGA,etc.)
        callsign        Generic radio
        LORC            LORAN-C radionavigation
        GOES            GOES UHF environment satellite
        GPS             GPS UHF satellite positioning
        ==============================================
        
        The following ref ids are used by the SyncServer:
        ==============================================
        GPS             GPS satellite)
        IRIG            IRIG B timecode
        PPS             Ext. 1 PPS input
        E10M	        Ext. 10 MHz input
        FREE            Internal Clock
        FLY             Internal Clock after the Hardware
                        Clock reference is lost
        =============================================="
::= {ntpSystem 6}

ntpSysRefTime OBJECT-TYPE
    SYNTAX 		DisplayString (SIZE(1..40))
    MAX-ACCESS 	read-only
    STATUS 		current
    DESCRIPTION
        "NTP Reference Timestamp.  This is the time,
        in timestamp format (converted to DisplayString), 
        when the local clock was last updated.  If the
        local clock has never been synchronized, the value
        is zero."
::= {ntpSystem 7}

ntpSysPoll	OBJECT-TYPE
    SYNTAX		Integer32
    MAX-ACCESS	read-only
    STATUS		current
    DESCRIPTION 
        "Minimum interval between transmitted messages, in 
        seconds as a power of two.  For instance, a value 
        of six indicates a minimum interval of 64 seconds."
::= {ntpSystem 8}

ntpSysPeer	OBJECT-TYPE
    SYNTAX 		Unsigned32
    MAX-ACCESS	read-only
    STATUS		current
    DESCRIPTION 
        "Current synchronization source.  In stratum > 1 this
        variable returns the decimal representation of the 
        IPv4 address of its current peer. In stratum = 1 this 
        variable returns the decimal representation of the
        hardware clock which is 2981759."
::= {ntpSystem 9}

ntpSysPhase OBJECT-TYPE
    SYNTAX		DisplayString (SIZE(1..40))
    MAX-ACCESS	read-only
    STATUS		current
    DESCRIPTION	
        "System clock offset from the selected source."
::= {ntpSystem 10}

ntpSysFreq OBJECT-TYPE
    SYNTAX		DisplayString (SIZE(1..40))
    MAX-ACCESS	read-only
    STATUS		current
    DESCRIPTION	
        "System clock frequency correction from ntpd."
::= {ntpSystem 11}

ntpSysError OBJECT-TYPE
    SYNTAX		DisplayString (SIZE(1..40))
    MAX-ACCESS	read-only
    STATUS		current
    DESCRIPTION	
        "Current system error from ntpd."
::= {ntpSystem 12}

ntpSysClock OBJECT-TYPE
    SYNTAX		DisplayString (SIZE(1..40))
    MAX-ACCESS	read-only
    STATUS		current
    DESCRIPTION	
        "Current system time from ntpd. This is usually 
        derived from the hardware clock but could be 
        from any other ntp source."
::= {ntpSystem 13}

ntpSysSystem OBJECT-TYPE
    SYNTAX		DisplayString (SIZE(1..80))
    MAX-ACCESS	read-only
    STATUS		current
    DESCRIPTION	
        "Description of the current system."
::= {ntpSystem 14}

ntpSysProcessor OBJECT-TYPE
    SYNTAX		DisplayString (SIZE(1..40))
    MAX-ACCESS	read-only
    STATUS		current
    DESCRIPTION	
        "Type of local processor."
::= {ntpSystem 15}

ntpSysNotrust OBJECT-TYPE
    SYNTAX INTEGER (0..1)
    ACCESS read-only
    STATUS mandatory
    DESCRIPTION
        "Force authentication."
::= {ntpSystem 16}

ntpSysPktsReceived OBJECT-TYPE        
    SYNTAX INTEGER (0..32768)
    ACCESS read-only
    STATUS mandatory
    DESCRIPTION 
        "This variable is a rollover counter which reflects 
        the number of ntp packets received by the SyncServer.
        It is valid for all versions of the SyncServer."
::= {ntpSystem 17} 

ntpSysMode OBJECT-TYPE
    SYNTAX INTEGER {
            unspecified (0),
            symactive (1),
            sympassive (2),
            client (3),
            server (4),
            broadcast (5),
            reservedctl (6),
            reservedpriv (7)}
    ACCESS read-only
    STATUS mandatory
    DESCRIPTION 
        "An integer indicating the NTP association mode  
        and are coded as follows:
        ============================================
        0       unspecified
        1       symmetric active
        2       symmetric passive
        3       client
        4       server
        5       broadcast
        6       reserved for NTP control messages
        7       reserved for private use
        ============================================"
::= {ntpSystem 18}

ntpSysVersion OBJECT-TYPE
    SYNTAX		DisplayString (SIZE(1..80))	
    MAX-ACCESS	read-only
    STATUS		current
    DESCRIPTION	"The version of the NTP daemon on the system."
::= {ntpSystem 19}

tymingStatus OBJECT-TYPE
    SYNTAX		DisplayString (SIZE(1..80))
    MAX-ACCESS	read-only
    STATUS		current
    DESCRIPTION	
        "Indicates what status the Hardware Clock considers 
        itself to be as a timing source defined as follows:
        ============================================
        Good     HW Clock has a valid time reference.
        Bad      HW Clock has no valid time reference.
        ============================================"
::= {tyming 1}

tymingSource OBJECT-TYPE
    SYNTAX 		DisplayString (SIZE(1..40))
    MAX-ACCESS 	read-only
    STATUS 		current
    DESCRIPTION 
        "The time or frequency source currently in use 
        by the Hardware Clock defined as follows:
        ============================================
         0       None
             1       GPS
             8       IRIG
        16       External 1PPS
        24       External 10 MHz
        31       Freerun
        ============================================"
::= {tyming 2}
                                                                            
tymingTime OBJECT-TYPE
    SYNTAX 		DisplayString (SIZE(1..40))
    MAX-ACCESS 	read-only
    STATUS 		current
    DESCRIPTION 
        "The time according to the Hardware Clock in 
        the format of:

        WWW MMM dd hh:mm:ss yyyy

        defined as follows:
            ============================================
            WWW              weekday
            MMM              character month
            dd               day of month
            hh:mm:ss         time
            yyyy             year

        Example          Thu Sep 21 23:46:09 2006
        ============================================"
::= {tyming 3}

tymingVersion OBJECT-TYPE
    SYNTAX 		DisplayString (SIZE(1..40))
    MAX-ACCESS 	read-only
    STATUS 		current
    DESCRIPTION 
        "The version of the software on the SyncServer's 
        Hardware Clock."
::= {tyming 4}

tymingFlyPeriod OBJECT-TYPE
    SYNTAX 		INTEGER
    MAX-ACCESS 	read-only
    STATUS 		current
    DESCRIPTION 
        "This variable is not currently used and returns zero."
    ::= {tyming 5}

gpsPosition OBJECT-TYPE
    SYNTAX		DisplayString (SIZE(1..80))
    MAX-ACCESS	read-only
    STATUS		current	
    DESCRIPTION 
        "Returns the current position in the format of:

        A BB CC DD EEE F GGG HH II JJJ KK
        
        defined as follows:
            ===============================================
        A           sign of the latitude 
                    (1 = North, -1 = South)
        BB          degrees of the latitude  
        CC          minutes of the latitude
        DD          seconds of the latitude
        EEE         milliseconds of the latitude
        F           sign of the longitude 
                    (1 = East, -1 = West)
        GGG         degrees of the longitude
        HH          minutes of the longitude
        II          seconds of the longitude
        JJJ         milliseconds of the longitude
        KK          altitude in meters
        ==============================================="
::= {gps 1}

gpsUTCOffset OBJECT-TYPE
    SYNTAX		INTEGER (0..127)
    MAX-ACCESS	read-only
    STATUS		current
        DESCRIPTION 
        "This variable is reserved for future use."
::= {gps 2}

gpsHealth OBJECT-TYPE
    SYNTAX		DisplayString (SIZE(1..80))
    MAX-ACCESS	read-only
    STATUS		current	
    DESCRIPTION 
        "This is the GPS' receiver health status defined as
        follows:
        ======================================================
        0 = Receiver Down       The Hardware Clock can't 
                                communicate with the receiver.

        1 = Unknown Mode        An undefined mode of the GPS
                                receiver.

        2 = Acquiring Signal    The receiver is attempting to
                                track a GPS signal.

        3 = Bad Geometry        The geometry of the tracked
                                satellites is unsatisfactory for
                                a position solution.

        4 = Propagate Mode      A position estimation mode used
                                in highly dynamic environments.

        5 = 2d Solution         The receiver is able to perform 
                                position fixes for latitude and 
                                longitude but does not have 
                                enough satellites for altitude.

        6 = 3d Solution         The receiver is now able to 
                                perform position fixes for 
                                latitude, longitude and altitude.

        7 = Position Hold       Position fixes are no longer 
                                attempted, and the user entered 
                                or surveyed position is used.

        8 = Time Valid          The receiver has valid timing 
                                information from GPS satellites 
                                (including current leap second 
                                information).  This is the final 
                                state for all configured GPS modes.
        ======================================================"
::= {gps 3}

gpsSatlist OBJECT-TYPE
    SYNTAX		DisplayString (SIZE(1..128))
    MAX-ACCESS	read-only
    STATUS		current	
    DESCRIPTION 
        "Displays the GPS satellite tracking information in the
        format of:

        N,X1,Y1,Z1,...,XN,YN,ZN

        defined as follows:
        ======================================================	
        N        Number of satellites. If one or more satellites 
                 are available, Xi,Yi,Zi follows N.

        Xi       Satellite vehicle number.

        Yi       Satellite signal strength in dBW where less 
                 than -200 dBW means no signal.

        Zi       Zi can be either T or C. T(racking) means the 
                 SyncServer receives the information from the 
                 satellite but the information is not used in its 
                 timing solution. C(urrent) means the SyncServer 
                 currently uses satellite information in its 
                 timing solution.
        
        Examples

        For no satellites:
        0

        For one satellite with vehicle number 16:
        1,16,C,-158

        For six satellites:
        6,12,C,-156,14,C,-155,8,T,-162,24,C,-158,18,C,161,6,C,-160	
        ======================================================"
::= {gps 4}

gpsMode OBJECT-TYPE
    SYNTAX		DisplayString (SIZE(1..80))
    MAX-ACCESS	read-only
    STATUS		current	
    DESCRIPTION 
        "The mode of the GPS receiver defined as follows:
        ======================================================
        Receiver Mode: Survey. 

        The receiver is surveying and averaging its position. 
        When it has finished surveying, the receiver switches 
        to Position Hold mode. Survey mode and Position Hold 
        mode are appropriate for static applications, such as a 
        typical server room environment. This is the default mode 
        when the SyncServer starts.

        Receiver Mode: Dynamic. 

        The GPS receiver surveys continuously to determine its 
        position and doesn't switch to another mode. This mode 
        must be initiated by a user, and is appropriate for mobile 
        applications such as ships, land vehicles, and aircraft. 
        The degree of accuracy this mode offers is fine for NTP 
        time over networks, but is less than optimal for the IRIG-B, 
        1 PPS, 10 MHz outputs available on some SyncServer models.  

        Receiver Mode: Hold. 

        The GPS receiver has completed Survey mode and switched to 
        this mode, or the user has manually entered a position and 
        forced it into this mode. The accuracy and stability of the 
        SyncServer's timing outputs are optimal when the receiver 
        has its exact position and is in this mode.
        ======================================================"
::= {gps 5}

etcVersion OBJECT-TYPE
    SYNTAX 		DisplayString (SIZE(1..80))
    MAX-ACCESS	read-only
    STATUS		current
    DESCRIPTION 
        "Version info for SyncServer system."
::= {etc 1}

etcSerialNbr OBJECT-TYPE
    SYNTAX		DisplayString (SIZE(1..40))
    MAX-ACCESS	read-only
    STATUS		current
    DESCRIPTION 
        "Unique serial number factory programmed into each unit."
::= {etc 2}

etcModel OBJECT-TYPE
    SYNTAX		DisplayString (SIZE(1..40))
    MAX-ACCESS	read-only
    STATUS		current
    DESCRIPTION 
        "Model type factory programmed into each unit."
::= {etc 3}

etcUpgrade OBJECT-TYPE
    SYNTAX		DisplayString (SIZE(1..1024))
    MAX-ACCESS	read-only
    STATUS		current
    DESCRIPTION 
        "Describes whether or not an upgrade is available from
        the upgrade server described as follows:
        ======================================================
        0       No upgrade is available.
        1       An upgrade is available.
        ======================================================"
::= {etc 4}

etcUpgradeServer OBJECT-TYPE
    SYNTAX		DisplayString (SIZE(1..1024))
    MAX-ACCESS	read-only
    STATUS		current
    DESCRIPTION 
        "Address of the server where new upgrades can be
        downloaded."
::= {etc 5}

etcAlarmString OBJECT-TYPE
    SYNTAX		DisplayString (SIZE(0..1024))
    MAX-ACCESS	read-only
    STATUS		current
    DESCRIPTION 
        "Defines the format for the system alarm traps.  This is 
        only valid embedded in a trap message."
::= {etc 6}

etcAlarm TRAP-TYPE
    ENTERPRISE	symmetricom
    VARIABLES	{etcAlarmString}
    DESCRIPTION 
        "The trap provides notification of Hardware Clock, NTP,
        system, and network alarms events.  The user can configure
        which alarms send traps on the ADMIN - Alarms page."
::= 0

END
