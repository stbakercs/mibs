GANDI-MIB DEFINITIONS ::= BEGIN

IMPORTS
	MODULE-IDENTITY, OBJECT-TYPE, Counter64, OBJECT-IDENTITY
		FROM SNMPv2-SMI
	enterprises
		FROM RFC1155-SMI
	DisplayString
		FROM SNMPv2-TC;

gandiMIB MODULE-IDENTITY
	LAST-UPDATED "201510301800Z"
	ORGANIZATION "Gandi SAS - www.gandi.net"
	CONTACT-INFO
		"63-65 Boulevard Massena
		 75013 PARIS
		 FRANCE

		 noc@gandi.net"
	DESCRIPTION
		"The MIB module describe our SNMP Objects"
	::= { enterprises 26384 }

pktjTable OBJECT IDENTIFIER ::= { gandiMIB 1 }

statTable OBJECT IDENTIFIER ::= { pktjTable 1 }

totalTable OBJECT IDENTIFIER ::= { statTable 1 }

packetsCounters OBJECT IDENTIFIER ::= { totalTable 1 }

rxCounter OBJECT-TYPE
	SYNTAX		Counter64
	MAX-ACCESS	read-only
	STATUS		current
	DESCRIPTION
		"RX packets"
	::= { packetsCounters 2 }

txCounter OBJECT-TYPE
	SYNTAX		Counter64
	MAX-ACCESS	read-only
	STATUS		current
	DESCRIPTION
		"TX packets"
	::= { packetsCounters 3 }

dropCounters OBJECT IDENTIFIER ::= { totalTable 2 }

dropCounter OBJECT-TYPE
	SYNTAX		Counter64
	MAX-ACCESS	read-only
	STATUS		current
	DESCRIPTION
		"Dropped counter"
	::= { dropCounters 2 }

acldropCounter OBJECT-TYPE
	SYNTAX		Counter64
	MAX-ACCESS	read-only
	STATUS		current
	DESCRIPTION
		"ACL Dropped counter"
	::= { dropCounters 3 }

ratedropCounter OBJECT-TYPE
	SYNTAX		Counter64
	MAX-ACCESS	read-only
	STATUS		current
	DESCRIPTION
		"Rate Dropped counter"
	::= { dropCounters 4 }

kniCounters OBJECT IDENTIFIER ::= { totalTable 3 }

kniRxCounter OBJECT-TYPE
	SYNTAX		Counter64
	MAX-ACCESS	read-only
	STATUS		current
	DESCRIPTION
		"KNI RX counter"
	::= { kniCounters 2 }

kniTxCounter OBJECT-TYPE
	SYNTAX		Counter64
	MAX-ACCESS	read-only
	STATUS		current
	DESCRIPTION
		"KNI TX counter"
	::= { kniCounters 3 }

kniDropCounter OBJECT-TYPE
	SYNTAX		Counter64
	MAX-ACCESS	read-only
	STATUS		current
	DESCRIPTION
		"KNI DROP counter"
	::= { kniCounters 4 }

END
