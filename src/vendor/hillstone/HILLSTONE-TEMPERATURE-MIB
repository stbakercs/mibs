-- **************************************************************************
-- HILLSTONE-TEMPERATURE-MIB
--
-- Copyright (c) 2009 by Hillstone Networks, Inc.
-- All rights reserved.
-- 
-- Version:      V6   
-- Description:	 Hillstone Networks TEMPERATURE MIB Object Identifier Assignments
-- **************************************************************************
--

HILLSTONE-TEMPERATURE-MIB DEFINITIONS ::= BEGIN

IMPORTS
	hillstoneTemperature
		FROM HILLSTONE-SMI
	OBJECT-TYPE
		FROM SNMPv2-SMI	
        RowStatus		
		FROM SNMPv2-TC;

          -- textual conventions

          DisplayString ::=
              OCTET STRING
          -- This data type is used to model textual information taken
          -- from the NVT ASCII character set.  By convention, objects
          -- with this syntax are declared as having
          --
          --      SIZE (0..255)

hillstoneTemperatureObjects OBJECT IDENTIFIER ::= { hillstoneTemperature 1 }

hillstoneTemperatureNumber OBJECT-TYPE
    SYNTAX INTEGER
    MAX-ACCESS read-only
    STATUS current
    DESCRIPTION
	"The number of temperatures."
    ::= { hillstoneTemperatureObjects 1 } 

HillstoneTemperatureEntry ::=
SEQUENCE { 
	hillstoneTemperatureIndex
		INTEGER,
	hillstoneTemperatureDescr
		DisplayString,
	hillstoneTemperatureValue
		INTEGER
	}
hillstoneTemperatureTable OBJECT-TYPE
	SYNTAX SEQUENCE OF HillstoneTemperatureEntry
	MAX-ACCESS not-accessible
	STATUS current
	DESCRIPTION
	    "This table contains all the TEMPERATURE data."
::= { hillstoneTemperatureObjects 2 }

hillstoneTemperatureEntry OBJECT-TYPE
	SYNTAX HillstoneTemperatureEntry
	MAX-ACCESS not-accessible
	STATUS current
	DESCRIPTION
		"Define the parameters of TEMPERATURE."
INDEX { hillstoneTemperatureIndex }
::= { hillstoneTemperatureTable 1 }
	

hillstoneTemperatureIndex OBJECT-TYPE
	SYNTAX INTEGER 
	MAX-ACCESS read-only
	STATUS current
	DESCRIPTION
	    "The TEMPERATURE index ."
::= { hillstoneTemperatureEntry 1 }

hillstoneTemperatureDescr OBJECT-TYPE
	SYNTAX DisplayString
	MAX-ACCESS read-only
	STATUS current
	DESCRIPTION
	    "The TEMPERATURE description ."
::= { hillstoneTemperatureEntry 2 }

hillstoneTemperatureValue OBJECT-TYPE
	SYNTAX INTEGER
	MAX-ACCESS read-only
	STATUS current
	DESCRIPTION
	    "The TEMPERATURE value ."
::= { hillstoneTemperatureEntry 3 }


END
