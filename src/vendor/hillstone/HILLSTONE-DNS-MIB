-- ***********************************************************************
-- HILLSTONE-DNS-MIB  
--
-- Copyright (c) 2009 by Hillstone Networks, Inc.
-- All rights reserved.
-- 
-- Version:      V3    
-- Description:	 Hillstone Networks DNS MIB Object Identifier Assignments
-- ***********************************************************************
--

HILLSTONE-DNS-MIB DEFINITIONS ::= BEGIN

IMPORTS
	hillstoneDNS
		FROM HILLSTONE-SMI
	OBJECT-TYPE
		FROM SNMPv2-SMI;	

          -- textual conventions

          DisplayString ::=
              OCTET STRING
          -- This data type is used to model textual information taken
          -- from the NVT ASCII character set.  By convention, objects
          -- with this syntax are declared as having
          --
          --      SIZE (0..255)

hillstoneDnsMibObjects OBJECT IDENTIFIER ::= { hillstoneDNS 1 }

-- dns srv group

hillstoneDnsSrvWorkMode OBJECT-TYPE
    SYNTAX INTEGER
	{
		server(0),
		client(1),
		relay(2)
	}
    MAX-ACCESS read-only
    STATUS current
    DESCRIPTION 
	"The dns server work mode"
    ::= { hillstoneDnsMibObjects 1 }

HillstoneDnsDomainEntry ::=
    SEQUENCE{
	hillstoneDnsDomainIdx
	    INTEGER,
	hillstoneDnsDomainName
	    DisplayString
	}
hillstoneDnsDomainTable OBJECT-TYPE
    SYNTAX SEQUENCE OF HillstoneDnsDomainEntry
    MAX-ACCESS not-accessible
    STATUS current
    DESCRIPTION
	"The table is used in domain informatioin of this dns server"
    ::= { hillstoneDnsMibObjects 2 }

hillstoneDnsDomainEntry OBJECT-TYPE
    SYNTAX HillstoneDnsDomainEntry
    MAX-ACCESS not-accessible
    STATUS current
    DESCRIPTION
	"The entry is used in domain informatioin of this dns server"
    INDEX { hillstoneDnsDomainIdx }
    ::= { hillstoneDnsDomainTable 1 } 


hillstoneDnsDomainIdx OBJECT-TYPE
    SYNTAX INTEGER
    MAX-ACCESS read-only
    STATUS current
    DESCRIPTION
	"The index of this table"
    ::= { hillstoneDnsDomainEntry 1 }
    
hillstoneDnsDomainName OBJECT-TYPE
    SYNTAX DisplayString
    MAX-ACCESS read-only
    STATUS current
    DESCRIPTION
	"Dns domain name."
    ::= { hillstoneDnsDomainEntry 2 }
    

-- static dns
HillstoneStaticDnsServAddressEntry ::=
    SEQUENCE{
	hillstoneStaticDnsServIdx
	    INTEGER,
	hillstoneStaticDnsIpAddr
	    IpAddress
	}
hillstoneStaticDnsServAddressTable OBJECT-TYPE
    SYNTAX SEQUENCE OF HillstoneStaticDnsServAddressEntry
    MAX-ACCESS not-accessible
    STATUS current
    DESCRIPTION
	"The table is used in static domain informatioin of this Static dns server"
    ::= { hillstoneDnsMibObjects 3 }

hillstoneStaticDnsServAddressEntry OBJECT-TYPE
    SYNTAX HillstoneStaticDnsServAddressEntry
    MAX-ACCESS not-accessible
    STATUS current
    DESCRIPTION
	"The entry is used in ip address informatioin of this Static dns server"
    INDEX { hillstoneStaticDnsServIdx }
    ::= { hillstoneStaticDnsServAddressTable 1 } 


hillstoneStaticDnsServIdx OBJECT-TYPE
    SYNTAX INTEGER
    MAX-ACCESS read-only
    STATUS current
    DESCRIPTION
	"The index of this Dns server table."
    ::= { hillstoneStaticDnsServAddressEntry 1 }
    
hillstoneStaticDnsIpAddr OBJECT-TYPE
    SYNTAX IpAddress
    MAX-ACCESS read-only
    STATUS current
    DESCRIPTION
	"Dns server ip address."
    ::= { hillstoneStaticDnsServAddressEntry 2 }
    
    
--  DDns 
HillstoneDynamicDnsServAddressEntry ::=
    SEQUENCE{
	hillstoneDynamicDnsServIdx
	    INTEGER,
	hillstoneDynamicDnsIpAddr
	    IpAddress
	}
hillstoneDynamicDnsServAddressTable OBJECT-TYPE
    SYNTAX SEQUENCE OF HillstoneDynamicDnsServAddressEntry
    MAX-ACCESS not-accessible
    STATUS current
    DESCRIPTION
	"The table is used in static domain informatioin of this Dynamic dns server"
    ::= { hillstoneDnsMibObjects 4 }

hillstoneDynamicDnsServAddressEntry OBJECT-TYPE
    SYNTAX HillstoneDynamicDnsServAddressEntry
    MAX-ACCESS not-accessible
    STATUS current
    DESCRIPTION
	"The entry is used in ip address informatioin of this Dynamic dns server"
    INDEX { hillstoneDynamicDnsServIdx }
    ::= { hillstoneDynamicDnsServAddressTable 1 } 


hillstoneDynamicDnsServIdx OBJECT-TYPE
    SYNTAX INTEGER
    MAX-ACCESS read-only
    STATUS current
    DESCRIPTION
	"The index of this Dns server table."
    ::= { hillstoneDynamicDnsServAddressEntry 1 }
    
hillstoneDynamicDnsIpAddr OBJECT-TYPE
    SYNTAX IpAddress
    MAX-ACCESS read-only
    STATUS current
    DESCRIPTION
	"Dns server ip address."
    ::= { hillstoneDynamicDnsServAddressEntry 2 }
    

END
