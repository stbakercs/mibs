-- *************************************************************************
-- HILLSTONE-IPSEC-MIB  
--
-- Copyright (c) 2009 by Hillstone Networks, Inc.
-- All rights reserved.
-- 
-- Version:      V3    
-- Description:	 Hillstone Networks IPSEC MIB Object Identifier Assignments
-- *************************************************************************
--

HILLSTONE-IPSEC-MIB DEFINITIONS ::= BEGIN

IMPORTS
	hillstoneIpsec			FROM HILLSTONE-SMI
	NetworkAddress, IpAddress, 
	Counter, Gauge, TimeTicks	FROM RFC1155-SMI
	OBJECT-TYPE			FROM SNMPv2-SMI;	

          -- textual conventions

          DisplayString ::=
              OCTET STRING
          -- This data type is used to model textual information taken
          -- from the NVT ASCII character set.  By convention, objects
          -- with this syntax are declared as having
          --
          --      SIZE (0..255)

hillstoneIpsecMibObjects OBJECT IDENTIFIER ::= { hillstoneIpsec 1 }

IpsecTunnelEntry ::=
	SEQUENCE{
		ipsecTunnelIndex
			INTEGER,
		ipsecTunnelName
			DisplayString,
		ipsecTunnelID
			INTEGER,
		ipsecTunnelType
			INTEGER,
		ipsecTunnelPeerIp
			NetworkAddress,
		ipsecTunnelExIfIndex
			INTEGER,
		ipsecTunnelLocalID
			DisplayString,
		ipsecTunnelRemoteID
			DisplayString,
		ipsecTunnelCryptAlgorithms
			DisplayString,
		ipsecTunnelAuthAlgorithms
			DisplayString,		
		ipsecTunnelLifeTime
			TimeTicks,
		ipsecTunnelStatus
			INTEGER
	}
ipsecTunnelTable OBJECT-TYPE
	SYNTAX SEQUENCE OF IpsecTunnelEntry
	MAX-ACCESS not-accessible
	STATUS current
	::= { hillstoneIpsecMibObjects 1 }

ipsecTunnelEntry OBJECT-TYPE
	SYNTAX IpsecTunnelEntry
	MAX-ACCESS not-accessible
	STATUS current
	INDEX { ipsecTunnelIndex }
	::= { ipsecTunnelTable 1}

		
ipsecTunnelIndex OBJECT-TYPE
	SYNTAX INTEGER 
	MAX-ACCESS read-only
	STATUS current
	 DESCRIPTION 
		"The index of ipsec tunnel"
	::= { ipsecTunnelEntry 1 }

ipsecTunnelName OBJECT-TYPE
	SYNTAX DisplayString
	MAX-ACCESS read-only
	STATUS current
	DESCRIPTION 
		"The name of ipsec tunnel"
	::= { ipsecTunnelEntry 2 }

ipsecTunnelID OBJECT-TYPE
	SYNTAX INTEGER 
	MAX-ACCESS read-only
	STATUS current
	 DESCRIPTION 
		"The index of ipsec tunnel"
	::= { ipsecTunnelEntry 3 }

ipsecTunnelType OBJECT-TYPE
	SYNTAX INTEGER  {
		normal (1),
		pnp (2),
		dail-up (3),
		manual (4)
	}
	MAX-ACCESS read-only
	STATUS current
	DESCRIPTION 
		"The type of tunnel"
	::= { ipsecTunnelEntry 4 }

ipsecTunnelPeerIp OBJECT-TYPE
	SYNTAX NetworkAddress
	MAX-ACCESS read-only
	STATUS current
	DESCRIPTION 
		"The peer ip of a ipsec tunnel"
	::= { ipsecTunnelEntry 5 }

ipsecTunnelExIfIndex OBJECT-TYPE
	SYNTAX INTEGER
	MAX-ACCESS read-only
	STATUS current
	DESCRIPTION 
		"The local interface of a ipsec tunnel"
	::= { ipsecTunnelEntry 6 }

ipsecTunnelLocalID OBJECT-TYPE
	SYNTAX DisplayString
	MAX-ACCESS read-only
	STATUS current
	DESCRIPTION 
		"The local id of a ipsec tunnel"
	::= { ipsecTunnelEntry 7 }

ipsecTunnelRemoteID OBJECT-TYPE
	SYNTAX DisplayString
	MAX-ACCESS read-only
	STATUS current
	DESCRIPTION 
		"The remote id of a ipsec tunnel"
	::= { ipsecTunnelEntry 8 }

ipsecTunnelCryptAlgorithms OBJECT-TYPE
	SYNTAX DisplayString
	MAX-ACCESS read-only
	STATUS current
	DESCRIPTION 
		"The crypt algorithms of a ipsec tunnel"
	::= { ipsecTunnelEntry 9 }

ipsecTunnelAuthAlgorithms OBJECT-TYPE
	SYNTAX DisplayString
	MAX-ACCESS read-only
	STATUS current
	DESCRIPTION 
		"The auth algorithms of a ipsec tunnel"
	::= { ipsecTunnelEntry 10 }

ipsecTunnelLifeTime OBJECT-TYPE
	SYNTAX TimeTicks
	MAX-ACCESS read-only
	STATUS current
	DESCRIPTION 
		"The life time of a ipsec tunnel"
	::= { ipsecTunnelEntry 11 }

ipsecTunnelStatus OBJECT-TYPE
	SYNTAX INTEGER  {
		active (1),
		inactive (2)
	}
	MAX-ACCESS read-only
	STATUS current
	DESCRIPTION 
		"The status of tunnel"
	::= { ipsecTunnelEntry 12 }

END
