--MibName=raisecomCommonManagement
-- =======================================================================
-- Version info
--
-- Version 0.1 Created 2002.5.24 by GONGGUIDONG
-- This version of MIB is created just for management of base and user.
-- Added raisecomClockGroup.raisecomClockMode sub-node by XueChaomin 20081220
-- remove UserManage and OnlineUpgrade group by guoxiaodan 20070716
-- removed keepalve group by LIAOBIN 20070709
-- raisecomEnableLogMethod add local_radius radius_local  by yjg 20070112
-- modify RaisecomUserEntry by cjy 20060616
-- add raisecomEnableLogPassword��raisecomEnableLogOldPassword by cjy 20060616
-- add rcNotificationGroup   by gongguidong 20041208
-- add raisecomUserStatus    by gongguidong 20040205
-- add online Upgrade group   by gongguidong 20040205
-- Copyright(c) 2003-2005 by RAISECOM TECH, Ltd.
-- =======================================================================

-- ===========================================================================

--
-- RAISECOM base management objects
--

RAISECOM-COMMON-MANAGEMENT-MIB DEFINITIONS ::= BEGIN

    IMPORTS
		MODULE-IDENTITY,
		OBJECT-TYPE,
		NOTIFICATION-TYPE ,
		Integer32,
		IpAddress,
		Unsigned32
			FROM SNMPv2-SMI
		DisplayString,
		TimeStamp,
		RowStatus,
		TruthValue
			FROM SNMPv2-TC
		DateAndTime,
		EnableVar
			FROM SWITCH-TC
		raisecomAgent
			FROM RAISECOM-BASE-MIB;

	raisecomCommonManagement    MODULE-IDENTITY
		LAST-UPDATED 	"200412170000Z"
		ORGANIZATION 	"RAISECOM TECH, Ltd."
		CONTACT-INFO 	"www.raisecom.com"
		DESCRIPTION
		    "The MIB module defining objects for common management"
		::= { raisecomAgent  2}

	--groups
	raisecomCommonFunctionGroup	OBJECT IDENTIFIER ::= {raisecomCommonManagement 1}

	raisecomNotificationGroup	OBJECT IDENTIFIER ::= {raisecomCommonManagement 4}

	raisecomClockGroup	OBJECT IDENTIFIER ::= {raisecomCommonManagement 5}



   -- raisecomCommonFunctionGroup


    raisecomConfigLoadOperation    OBJECT-TYPE
        SYNTAX          INTEGER{
        			ready(1),
        			saving(2),
        			erasing(3),
        			reboot(4),
        			restore(5),
        			reload(6),
        			backupsaving(7),
        			cpoyStaConf2BackConf(8),
        			cpoyBackConf2StaConf(9),
        			switStaConfBackConf(10),
        			backuperasing(11),
        			eraseStartupconfig(12),
        			eraseStartupconfigAll(13),
        			savingall(14)
        			}
        MAX-ACCESS      read-write
        STATUS          current
        DESCRIPTION     "Syetem Load Configuration .Includes to erase the start-up config,
                         or to save the running config."
    ::= { raisecomCommonFunctionGroup 1 }

    raisecomConfigLoadNotificationOnCompletion OBJECT-TYPE
    	SYNTAX TruthValue
    	MAX-ACCESS read-write
    	STATUS current
   		DESCRIPTION
		        "Specifies whether or not a  raisecomConfigLoadOnCompletion
		        notification should be issued on completion of some
		        operation . If such a notification is desired, it is the
		        responsibility of the management entity to ensure that the
		        SNMP administrative model is configured in such a way as to
		        allow the notification to be delivered."
		DEFVAL { false }
			::= {  raisecomCommonFunctionGroup 2 }

    raisecomConfigLoadState OBJECT-TYPE
		SYNTAX  INTEGER {
		        ready(1),
		        running(2),
		        successful(3),
		        failed(4)
		        }
		MAX-ACCESS read-only
		STATUS current
		DESCRIPTION
			"Specifies the state of this load configuration."
			::= {  raisecomCommonFunctionGroup 3 }

	raisecomSystemClock     OBJECT-TYPE
        SYNTAX INTEGER
        UNITS "second"
        MAX-ACCESS read-write
        STATUS obsolete
        DESCRIPTION
            "Seconds elapsed from Jan. 1,1970,same as UNIX TIME. "
        ::= { raisecomCommonFunctionGroup 4 }


  	raisecomConfigLoadMIBTraps      OBJECT IDENTIFIER ::= {raisecomCommonFunctionGroup 5}

    raisecomConfigLoadCompletion NOTIFICATION-TYPE
               		    		    OBJECTS {
		        raisecomConfigLoadOperation, raisecomConfigLoadState }
		STATUS     current
		--    mandatory
		    DESCRIPTION
		        "A raisecomConfigLoadeCompletion trap is sent when saving or erasing the configuration file. "
		    ::=  {raisecomConfigLoadMIBTraps 1}

    raisecomWatchdog    OBJECT-TYPE
        SYNTAX         EnableVar
        MAX-ACCESS    read-write
        STATUS          current
        DESCRIPTION     "Set/get watchdog status."
        DEFVAL { 1 }
		  ::= { raisecomCommonFunctionGroup 6}

    raisecomClearRunningConfig        OBJECT-TYPE
        SYNTAX	INTEGER{
                        clearAll(1)
                       }
        MAX-ACCESS  read-write
        STATUS      current
        DESCRIPTION
            "the operation to clear running-config"
          ::= { raisecomCommonFunctionGroup 7 }

    raisecomReloadStartupConfig        OBJECT-TYPE
    	SYNTAX	INTEGER{
                        clearAndReload(1)
    			       }
        MAX-ACCESS  read-write
        STATUS      current
        DESCRIPTION
            "The operation to reload startup-config file"
         ::= { raisecomCommonFunctionGroup 8 }

    raisecomCfgUpdateState OBJECT-TYPE
	    SYNTAX  INTEGER {
	                    none(0),
	                    noupdate(1),
	                    cliupdate(2),
	                    webupdate(3),
	                    mibupdate(4)
	                    }
	    MAX-ACCESS read-write
	    STATUS current
	    DESCRIPTION
		    "Specifies the state of this configuration."
		    ::= {  raisecomCommonFunctionGroup 9 }

    raisecomCfgUpdateModID OBJECT-TYPE
        SYNTAX  INTEGER
        MAX-ACCESS read-write
        STATUS current
        DESCRIPTION
            "Specifies ID of the module which has updated."
            ::= {  raisecomCommonFunctionGroup 10 }

    raisecomAutoWritecfgEnable OBJECT-TYPE
        SYNTAX       EnableVar
        MAX-ACCESS   read-write
        STATUS       current
        DESCRIPTION  "Set/get auto writing configuration status."
        DEFVAL      { 1 }
            ::= { raisecomCommonFunctionGroup 12 }

    raisecomMibCommandString OBJECT-TYPE
		SYNTAX	OCTET STRING (SIZE(0..255))
		MAX-ACCESS	read-write
		STATUS	current
		DESCRIPTION
			"comnmand string executed by mib user"
		::=	{ raisecomCommonFunctionGroup 13 }

    raisecomMibCommandMode  OBJECT-TYPE
		SYNTAX	INTEGER {
			userNode(0),
			authNode(1),
			viewNode(2),
			authEnableNode(3),
			enableNode(4),
			vlanNode(5),
			interfaceNode(6),
			interfaceRangeNode(7),
			aggregatorNode(8),
			tdmNode(9),
			ipNode(10),
			lbipNode(11),
			mplsExppathNode(12),
			tunnelNode(13),
			vlanifNode(14),
			subifNode(15),
			vrfNode(16),
			configNode(17),
			ripNode(18),
			bgpNode(19)
		}
		MAX-ACCESS	read-write
		STATUS	current
		DESCRIPTION
			"command run on specific mode"
		::=	{ raisecomCommonFunctionGroup 14 }

    raisecomMibCommandState  OBJECT-TYPE
		SYNTAX	INTEGER {
			cmdSuccess(0),
			cmdWarning(1),
			cmdErrNoMatch(2),
			cmdErrAmbiguous(3),
			cmdErrIncomplete(4),
			cmdErrExeedArgcMax(5),
			cmdErrNothingTodo(6),
			cmdCompleteFullMatch(7),
			reserved8(8),
			reserved9(9),
			reserved10(10),
			cmdNoRight(11),
			cmdErrAuthorFailure(12)
		}
		MAX-ACCESS	read-only
		STATUS	current
		DESCRIPTION
			"the state of comnmand executed"
		::=	{ raisecomCommonFunctionGroup 15 }

       raisecomAutoWritecfgInterval OBJECT-TYPE
        SYNTAX  Integer32
        MAX-ACCESS read-write
        STATUS current
        DESCRIPTION
            " Interval time of auto save  module."
            ::= {  raisecomCommonFunctionGroup 16 }

	raisecomConfigFileOperationTableGroup   OBJECT IDENTIFIER ::= {raisecomCommonFunctionGroup 17}

  	raisecomConfigFileOperationTable      OBJECT-TYPE
        SYNTAX   SEQUENCE OF RaisecomConfigFileOperationEntry
        MAX-ACCESS	 not-accessible
        STATUS   current
        DESCRIPTION
                 "Config file operation table."
        ::= { raisecomConfigFileOperationTableGroup   1 }

   	raisecomConfigFileOperationEntry      OBJECT-TYPE
        SYNTAX   RaisecomConfigFileOperationEntry
        MAX-ACCESS   not-accessible
        STATUS   current
        DESCRIPTION
                 "An entry in raisecomConfigFileOperationTable"
        INDEX { raisecomConfigFileNodeType,
                raisecomConfigFileNodeInfo}
        ::= { raisecomConfigFileOperationTable  1 }

   	RaisecomConfigFileOperationEntry ::= SEQUENCE {
		raisecomConfigFileNodeType	          INTEGER,
		raisecomConfigFileNodeInfo          OCTET STRING,
		raisecomConfigFileOperationType        INTEGER
  	}

   	raisecomConfigFileNodeType       OBJECT-TYPE
        SYNTAX   INTEGER{
                         slotType(1)
                        }
        MAX-ACCESS	 not-accessible
        STATUS   current
        DESCRIPTION
                 "Config file operation node type."
        ::= { raisecomConfigFileOperationEntry 1}

   	raisecomConfigFileNodeInfo       OBJECT-TYPE
        SYNTAX   OCTET STRING (SIZE(0..100))
        MAX-ACCESS	 not-accessible
        STATUS   current
        DESCRIPTION
                 "Config file operation node info."
        ::= { raisecomConfigFileOperationEntry 2}

   	raisecomConfigFileOperationType       OBJECT-TYPE
        SYNTAX   INTEGER{
                         erase(1)
                        }
        MAX-ACCESS	 read-write
        STATUS   current
        DESCRIPTION
                 "Config file operation type."
        ::= { raisecomConfigFileOperationEntry 3}

--raisecomNotificationGroup
	raisecomObjectStatusDesc    OBJECT-TYPE
		SYNTAX          OCTET STRING
		MAX-ACCESS      accessible-for-notify
		STATUS          current
		DESCRIPTION     "The object status description of the notification
             			currently being sent."
		::= { raisecomNotificationGroup 1 }

	raisecomNotificationDesc    OBJECT-TYPE
		SYNTAX          OCTET STRING
		MAX-ACCESS      accessible-for-notify
		STATUS          current
		DESCRIPTION     "The description of the notification
             			currently being sent."
		::= { raisecomNotificationGroup 2 }

	raisecomNotificationLevel    OBJECT-TYPE
		SYNTAX          OCTET STRING
		MAX-ACCESS      accessible-for-notify
		STATUS          current
		DESCRIPTION     "The notification severity level  of the notification
             			currently being sent."
		::= { raisecomNotificationGroup 3 }

	raisecomNotificationCategory    OBJECT-TYPE
		SYNTAX          OCTET STRING
		MAX-ACCESS      accessible-for-notify
		STATUS          current
		DESCRIPTION     "The notification category of the notification
             			currently being sent.such as Environment,Complement"
		::= { raisecomNotificationGroup 4 }

	raisecomNotificationLocation    OBJECT-TYPE
		SYNTAX          DisplayString
		MAX-ACCESS      accessible-for-notify
		STATUS          current
		DESCRIPTION     "The description of location which notification generates.
						This is a display string which can be showned on NMS such like OpenView"
		::= { raisecomNotificationGroup 101 }

--raisecomClockGroup
    raisecomClockDateAndTime OBJECT-TYPE
    SYNTAX      DateAndTime
    MAX-ACCESS  read-write
    STATUS      current
    DESCRIPTION
        "The current local date and time for the system.

        Setting this object is equivalent to setting an automated
        clock and calendar.  The value of the object will track the
        date and time from the value set.  Note that due to hardware
        limitations some systems may not be able to preserve such
        meaning across reboots of the system, as indicated by
        csyClockLostOnReboot.

        A constant value of all zeros and length 8 indicates the
        system is not aware of the present date and time.

        This object may be read-only on some systems."
    ::= { raisecomClockGroup 1 }

	raisecomClockLostOnReboot OBJECT-TYPE
    SYNTAX      TruthValue
    MAX-ACCESS  read-only
    STATUS      current
    DESCRIPTION
        "Indication of whether the system can preserve knowledge of
        current date and time across a system reboot.

        A value of 'true' indicates the clock must be reset from some
        external source each time the system reboots.

        A value of 'false' indicates the system has the ability to
        keep time across reboots."
    ::= { raisecomClockGroup 2 }

--raisecom Summer Time
raisecomSummerTime          OBJECT IDENTIFIER ::= { raisecomClockGroup 3 }

	raisecomSummerTimeEnable OBJECT-TYPE
        SYNTAX        EnableVar
        MAX-ACCESS    read-write
        STATUS        current
        DESCRIPTION
            "An indication of whether the summertime feature is enabled."
        ::= { raisecomSummerTime 1 }

	raisecomSummerTimeOffset  OBJECT-TYPE
        SYNTAX        INTEGER ( 1 .. 1440)
        UNITS         "Minutes"
        MAX-ACCESS    read-write
        STATUS        current
        DESCRIPTION
            "Minutes to add or subtract during summertime."
        ::= { raisecomSummerTime 2 }

	raisecomSummerTimeRecurringStart OBJECT-TYPE
        SYNTAX        OCTET STRING (SIZE (6))
        MAX-ACCESS    read-write
        STATUS        current
        DESCRIPTION
            "Summertime recurring start time (6 octets)."
        ::= { raisecomSummerTime 3 }

	raisecomSummerTimeRecurringEnd OBJECT-TYPE
        SYNTAX        OCTET STRING (SIZE (6))
        MAX-ACCESS    read-write
        STATUS        current
        DESCRIPTION
            "Summertime recurring end time (6 octets)."
        ::= { raisecomSummerTime 4 }

    raisecomClockMode OBJECT-TYPE
    SYNTAX      INTEGER{
        			sysclkDflt(1),
        			sysclkTs(2),
        			sysclkAux(3)
        			}
    MAX-ACCESS  read-write
    STATUS      current
    DESCRIPTION
        "System clock mode, which range from 1 to 3, stands for default mode, timestamp mode
        and auxiliary clock mode respectively. It allows network administrator to change
        system clock mechanism by setting this variable. For instance, if administrator intend
        to use auxiliary clock as system timer, whom is required to set this variable's value
        as 3, i.e SYSCLK_AUX.
        All supported values of this variable are listed as follows:
        1: SYSCLK_DFLT   default mode
        2: SYSCLK_TS     timestamp mode
        3: SYSCLK_AUX    auxiliary clock mode."
    ::= { raisecomClockGroup 4 }

    raisecomClockDisplay OBJECT-TYPE
    SYNTAX      INTEGER{
        			eraisecomClockDisplayDflt(1),
        			eraisecomClockDisplayUtc(2),
        			eraisecomClockDisplayOther(3)
        			}
    MAX-ACCESS  read-write
    STATUS      current
    DESCRIPTION
        "System clock  display mode, which range from 1 to 3, stands for default mode, UTC mode
        and other clock mode which is made to prepare for fulture respectively. It allows network administrator to change
        system clock mechanism by setting this variable. For instance, if administrator intend
        to use default display mode, the time will be shown as 'yyyy-mm-dd, hh:mm:ss'.
        else if if administrator intend to use UTC display mode,
        the time will be shown as'dd.mm.yyyy-hh:mm:ss'
        All supported values of this variable are listed as follows:
        1: EraisecomClockDisplay_DFLT    default mode
        2: EraisecomClockDisplay_UTC     UTC mode
        3: EraisecomClockDisplay_other   other mode."
    ::= { raisecomClockGroup 5 }

    raisecomClockTimezoneName OBJECT-TYPE
 	SYNTAX        OCTET STRING (SIZE (8))
    MAX-ACCESS  read-write
    STATUS      current
    DESCRIPTION
        "The name of the time zone "
    ::= { raisecomClockGroup 6 }

END
